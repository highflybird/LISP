;|*************************************************************;
软件作者: Highflybird                                          ;
软件用途: 一些作图问题的LISP解法                               ;
日期地点: 2021.05.18 深圳                                      ;
程序语言: AutoLISP,Visual LISP                                 ;
软件版本: Ver. 1.0.21.0518                                     ;
===============================================================;
================================================================
本软件为开源软件: 以下是开源申明:                               
----------------------------------------------------------------
本页面的软件遵照 GPL协议开放源代码，您可以自由传播和修改，在遵照
下面的约束条件的前提下:                                         
                                                                
一. 只要你在本开源软件的每一副本上明显和恰当地出版版权声明，保持
    此许可证的声明和没有担保的声明完整无损，并和程序一起给每个其
    他的程序接受者一份许可证的副本，你就可用任何媒体复制和发布你
    收到的原始程序的源代码。你也可以为转让副本的实际行动收取一定
    费用，但必须事先得到的同意。                                
二. 你可以修改本开源软件的一个或几个副本或程序的任何部分，以此形
    成基于程序的作品。只要你同时满足下面的所有条件，你就可以按前
    面第一款的要求复制和发布这一经过修改的程序或作品。          
  1.你必须在修改的文件中附有明确说明：你修改了这一文件及具体的修
    改日期。                                                    
  2.你必须使你发布或出版的作品（它包含程序的全部或一部分，或包含
    由程序的全部或部分衍生的作品）允许第三方作为整体按许可证条款
    免费使用。                                                  
  3.如果修改的程序在运行时以交互方式读取命令，你必须使它在开始进
    入常规的交互使用方式时打印或显示声明: 包括适当的版权声明和没
    有担保的声明（或者你提供担保的声明）；用户可以按此许可证条款
    重新发布程序的说明；并告诉用户如何看到这一许可证的副本。（例
    外的情况: 如果原始程序以交互方式工作，它并不打印这样的声明，
    你的基于程序的作品也就不用打印声明。                        
三. 只要你遵循一、二条款规定，您就可以自由使用并传播本源代码，但
    必须原封不动地保留原作者信息。                              
================================================================
**************************************************************|;

;;; 问题来源：http://bbs.mjtd.com/thread-183200-1-1.html        
;;; 输入条件输出解，并画出图形。                                
(defun c:tt (/ p q l h m i j k x y sx sy px dd an pp)
  (initget 9)
  (setq p (getpoint "\n定点O位置："))
  (initget 9)
  (setq q (getpoint p "\n射线OA的另一点："))
  (initget 15)
  (setq L (getdist q "\n输入线段AB的定长："))
  (initget 9)
  (setq h (getpoint "\n点取水平线DB位置："))
  (setq m (polar h 0 1000))
  (if (setq i (inters h m p q nil))
    (progn 
      (setq j (angle p q))
      (setq k (distance p i))
      (setq x (* k (cos j)))
      (setq y (* k (sin j)))
      (foreach s (GetSolutions x y L)
        (setq sx (car s))
        (setq sy (cadr s))
        (if (and (equal sy 0 1e-8) (> sx 0))
          (progn 
            (setq px (polar i 0 sx))
	    (setq dd (distance p px))
	    (setq an (angle p q))
	    (setq pp (polar p an dd))
	    (if (not (equal (distance px pp) L 1e-6))
	      (setq pp (polar p an (- dd)))
	    )
	    (ent:make_line (trans p 1 0) (trans q 1 0))
	    (ent:make_line (trans px 1 0) (trans pp 1 0))
	    (ent:make_Xline (trans h 1 0) (trans '(1 0 0) 1 0 T))
          )
	)
      )
    )
    (alert "你输入了无效的条件!")
  )
  (princ)
)

;;;-------------------------------------------------------------
;;; 通过定点相对坐标和定长得到一元四次方程。此方程的解为问题解。
;;; 关于一元四次方程的解及其相关函数，请参见下面的链接:         
;;; http://bbs.mjtd.com/forum.php?mod=viewthread&tid=99844&highlight=%B8%B4%CA%FD
;;;-------------------------------------------------------------
(defun GetSolutions (x y L / xx yy xy k B C D E)
  (setq xx (* x x))
  (setq yy (* y y))
  (setq xy (+ xx yy))
  (setq k (/ (* xy l l) yy))
  (setq B (+ x x))
  (setq C (- xy k))
  (setq D (* -2 x k))
  (setq E (* K (- (* 0.25 L L) xy)))
  (Math:Quartic_Equation 1 B C D E)
)

;;;-------------------------------------------------------------
;;;创建一条直线段                                       	
;;;输入: 两个三维或者二维的点                           	
;;;输出: 线段实体的图元名                               	
;;;-------------------------------------------------------------
(defun Ent:make_line (p q)
  (entmakex
    (list
      '(0 . "LINE")
      (cons 10 p)
      (cons 11 q)
    )
  )
)

;;;-------------------------------------------------------------
;;; 创建一条射线                                         	
;;; 输入: 射线通过的基点和方向矢量                              
;;; 输出: 创建后的射线图元名                               	
;;;-------------------------------------------------------------
(defun Ent:make_xline (p v)
  (entmakex
    (list
      '(0 . "XLINE")
      '(100 . "AcDbEntity")
      '(100 . "AcDbXline")
      (cons 10 p)
      (cons 11 v)
    )
  )
)

(vl-load-com)
(princ "\n运行命令: tt.")
(princ)
