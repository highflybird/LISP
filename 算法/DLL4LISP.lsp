;;;=============================================================
;;; 用DLL编写无版本限制的LISP程序                               
;;; 作者：highflybird                                           
;;; 日期：2022.8.21                                             
;;; 地点：深圳                                                  
;;;-------------------------------------------------------------
(defun c:ttt ()
  (if (> (strlen (VL-PRINC-TO-STRING +)) 19)
    (progn
      ;(load-dll "D:\\Programming\\repo\\LISP\\api64.dll")
      ;(load-dll "D:\\Programming\\repo\\DLL4LISP\\x64\\Debug\\DLL4LISP.dll")
      ;(load-dll "D:\\Programming\\repo\\DLL4LISP\\x64\\release\\DLL4LISP.dll")
      ;(load-dll "F:\\ZQY\\repo\\DLL4LISP\\x64\\Debug\\DLL4LISP.dll")
      (load-dll "F:\\ZQY\\repo\\DLL4LISP\\x64\\release\\DLL4LISP.dll")
    )
    ;(load-dll "F:\\ZQY\\repo\\DLL4LISP\\Debug\\DLL4LISP.dll")
    ;(load-dll "F:\\ZQY\\repo\\DLL4LISP\\release\\DLL4LISP.dll")
    ;(load-dll "D:\\Programming\\repo\\DLL4LISP\\Debug\\DLL4LISP.dll")
    (load-dll "D:\\Programming\\repo\\DLL4LISP\\release\\DLL4LISP.dll")
  )
)

(defun c:tttt ()
  (setq str "This is a Test:%ld,%ld,%ld,%ld,%s.\n")
  (setq n (rundll "ntdll" "mbstowcs" 0 str 0))
  (setq wstr (make-string (+ n n 2) 0))
  (setq n (rundll "ntdll" "mbstowcs" wstr str (1+ n)))
  (rundll "user32" "MessageBoxW" 0 wstr wstr 3)
  (rundll "kernel32" "LoadLibraryA" "user32")
  
  (setq p (rundll "msvcrt" "malloc" 16))
  (rundll "acdb18.dll" "acutPrintf" wstr 11 22 33 44 wstr)
  (rundll "winmm" "midiOutOpen" p 0 0 0 0)
  (setq h (_ptr64@ p))
  (rundll "winmm" "midiOutClose" h)
  (setq h (loadlibrary "user32.dll"))
  (setq a pi)
  (setq b "字符串测试:test")
  (setq c 124)
  (setq d 'sym)
  (setq e (vlax-get-acad-object))
  (setq g (entlast))
  (setq l (list 1 0.3 2))
  (setq m (cons 1 2))
  (setq s (ssget))
  (testPrintf a b c d e f g h l m s)
)

(defun c:www ()
  (setq dw (vlax-create-object "DynamicWrapper"))
  (vlax-invoke dw 'register "user32" "MessageBoxA" "I=HsSu" "f=s" "R=l")
  (vlax-invoke dw 'register "msvcrt" "malloc" "i=l" "f=c" "r=l")
  (vlax-invoke dw 'register "msvcrt" "free" "i=l" "f=c")
  (vlax-invoke dw 'register "msvcrt" "sin" "i=d" "f=8" "r=d")
  (setq r (vlax-invoke dw 'MessageBoxA 0 "Hello,设计!" "test" 3))
  (setq p (vlax-invoke dw 'malloc 12))
  (vlax-invoke dw 'free p)
  (vlax-invoke dw 'sin 1.2)
  (vlax-release-object dw)
)

(defun c:xxx ()
  (setq dw (vlax-create-object "DynamicWrapperX"))
  (setq f1 (vlax-invoke dw 'register "user32" "MessageBoxA" "i=hssu" "f=s" "r=l"))
  (setq f2 (vlax-invoke dw 'register "msvcrt" "sin" "i=d" "f=8" "r=d"))
  (setq f3 (vlax-invoke dw 'register "Kernel32" "MultiByteToWideChar" "i=uuslpl" "r=l"))
  (setq r (vlax-invoke dw 'MessageBoxA 0 "Hello,设计!" "test" 3))
  (setq s "(alert \"测试成功了!\")")
  (setq p (vlax-invoke dw 'MemAlloc 50 1))
  (vlax-invoke dw 'MultiByteToWideChar 0 0 s -1 p 44)
  (vlax-invoke dw 'strget p)
  (vlax-invoke dw 'MemFree p)
  (vlax-invoke dw 'sin 1.2)
  (vlax-release-object dw)
)

(defun c:fd ()
  (c:ttt)
  (setq fSin (register "msvcrt" "sin" "d" "d"))
  (setq fAtof (register "msvcrt" "atof" "c" "d"))
  (princ (call fSin 1.2))
  (princ "\n")
  (princ (call fAtof "1.2445"))
  (princ "\n")
  (princ)
)
  

(defun c:ggg ()
  (c:ttt)
  ;;注册API----这段没问题
  (setq nVer (substr (getvar "acadver") 1 2))
  (setq acdb (strcat "acdb" nVer ".dll"))
  (if (> (atoi nver) 18)
    (setq acorre "accore.dll")
    (setq acorre "acad.exe")
  )
  (loadlibrary "user32")
  (setq fLoad (register "kernel32" "LoadLibraryA" "s" "p"))
  (setq fMsg (register "user32" "MessageBoxA" "s" "l"))
  (setq fMsgW (register "user32" "MessageBoxW" "s" "l"))
  (setq fMalloc (register "msvcrt" "malloc" "c" "p"))
  (setq fCalloc (register "msvcrt" "calloc" "c" "p"))
  (setq fFree (register "msvcrt" "free" "c" "l"))
  (setq fMemset (register "msvcrt" "memset" "c" "l"))
  (setq fMemCpy (register "msvcrt" "memcpy" "c" "l"))
  (setq fSin (register "msvcrt" "sin" "d" "d"))
  (setq fAtof (register "msvcrt" "atof" "d" "d"))
  (setq fM2W (register "Kernel32"  "MultiByteToWideChar" "s" "l"))
  (setq fmbstowcs (register "ntdll" "mbstowcs" "c" "l"))
  (setq fAds_queueexpr (register acorre "ads_queueexpr" "c" "l"))
  (setq fPrintf (register acdb "acutPrintf" "c" "l"))
  (setq fGetAddr (register "kernel32" "GetProcAddress" "s" "p"))

  ;;内存分配----这段没问题
  (setq a (make-string 100 0))
  (setq p3 (run "msvcrt" "malloc" 200))
  (setq p1 (run "msvcrt" "calloc" 2 100))
  (setq p2 (call fCalloc 2 100))
  (setq expr "(alert \"测试成功了!\")") 
  (setq expr1 "\nThis a test:%d,%d,%d,%d,%d,%s,%f.")
  (setq expr2 "circle 0,0 12")
  
  (run "USER32" "MessageBoxA" 0 "测试成功了!" "test" 3) 
  (run "Kernel32" "MultiByteToWideChar" 0 0 expr 50 p1 100)
  (run acorre "ads_queueexpr" p1)
  (run "ntdll" "mbstowcs" p1 expr 100) 
  (run "msvcrt" "free" p1)
  (run "msvcrt" "sin" 1.2)

  (setq h (call fLoad "user32"))
  (call fGetAddr h "MessageBoxA")
  (call fMsg 0 "测试成功了!" "test" 3)
  
  (call fmbstowcs a expr 100) 
  (setq n (1+ (call fmbstowcs 0 expr 0))) 
  (call fMbstowcs p2 expr n) 
  (call fM2W 0 0 expr 50 p2 100)
  (call fAds_queueexpr p2) ;for 2006以及以下版本，可以直接用expr.
  (setq n (1+ (call fmbstowcs 0 expr1 0)))
  (call fMbstowcs p2 expr1 n)
  (call fMbstowcs a expr n)
  (call fPrintf p2 12 13 14 15 16 a PI)
  (call fMemCpy p2 expr (strlen expr))
  (call fFree p2)
  (call fSin 1.2)
  (call fAtof "1.6554")
 
  (princ "\n测试成功!")
  (princ)
)
