(defun ent:make_line (pa pb)
  (entmakex
    (list
      '(0 . "LINE")
      (cons 10 pa)
      (cons 11 pb)
    )
  )
)

(defun ent:make_circle (cen rad)
  (entmakex
    (list
      '(0 . "CIRCLE")
      (cons 10 cen)
      (cons 40 rad)
    )
  )
)
  
(defun fractal (pa pb n / an dl pc)
  (if (= n 1)
    (ent:make_line pa pb)
    (progn
      (setq an (+ (/ pi 4) (angle pa pb)))
      (setq dl (* 0.7071067811865475244 (distance pa pb)))
      (setq pc (polar pa an dl))
      (fractal pa pc (1- n))
      (fractal pc pb (1- n))
    )
  )
)

0.53589838486224541294510731698826 ;4-2*sqrt(3)
0.46410161513775458705489268301174 ;2*sqrt(3)-3
0.26794919243112270647255365849413 ;2-sqrt(3)
(defun fractal1 (cen rad n / rd rx ry cx cy)
  (ent:make_circle cen rad)
  (if (/= n 1)
    (progn
      (setq rd (* 0.53589838486224541294510731698826 rad))
      (setq rx (* 0.46410161513775458705489268301174 rad))
      (setq ry (* 0.26794919243112270647255365849413 rad))
      (setq cx (car cen))
      (setq cy (cadr cen))
      (fractal1 (list (- cx rx) (- cy ry)) rx (1- n))
      (fractal1 (list (+ cx rx) (- cy ry)) rx (1- n))
      (fractal1 (list cx (+ cy rd)) rx (1- n))
    )
  )
)

(defun c:tt(/ cen rad n)
  (initget 1)
  (setq cen (getpoint "\n中心: "))
  (initget 9)
  (setq rad (getdist cen "\n第二点: "))
  (initget 7)
  (setq n (getint "\n次数: "))
  (fractal1 (trans cen 1 0) rad  n)
  (princ)
)


(defun c:ttt(/ pa pb pc n)
  (initget 9)
  (setq pa (getpoint "\n第一点: "))
  (initget 9)
  (setq pb (getpoint pa "\n第二点: "))
  (initget 7)
  (setq n (getint "\n次数: "))
  (fractal (trans pa 1 0) (trans pb 1 0) n)
  (princ)
)
