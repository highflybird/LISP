(defun c:HappyBirthday ()
  (princ "\n开始为你播放生日歌:")
  (beep 523 200)
  (beep 523 200)
  (beep 578 400)
  (beep 523 400)
  (beep 698 400)
  (beep 659 800)

  (beep 523 200)
  (beep 523 200)
  (beep 578 400)
  (beep 523 400)
  (beep 784 400)
  (beep 698 800)

  (beep 523 200)
  (beep 523 200)
  (beep 1046 400)
  (beep 880 400)
  (beep 698 400)

  (beep 659 400)
  (beep 578 400)

  (beep 932 200)
  (beep 932 200)
  (beep 880 400)
  (beep 698 400)
  (beep 784 400)
  (beep 698 800)
  (princ "\n播放完毕！")
  (princ)
)
