;;;---------------------------------------------------------------;;;
;;;                                                               ;;;
;;;                  HIP ROOF - 2D RIDGE EDGES                    ;;;
;;;                  ALTERNATE SOLUTION FINDER                    ;;;
;;;                                                               ;;;
;;;  Author : Marko Ribar, d.i.a. (architect)                     ;;;
;;;  Autolisp routine for AutoCAD or BricsCAD                     ;;;
;;;  Copyright (C) 2021.                                          ;;;
;;;  Tested and programmed on Windows 10 OS                       ;;;
;;;  Bugs or failures may appear and aren't authors responsibility;;;
;;;  LSP file is free to be used for improvements...              ;;;
;;;  All relevant suggestions are welcomed...                     ;;;
;;;                                                               ;;;
;;;---------------------------------------------------------------;;;
(defun c:rrr() 
  (c:roof2d-new-solutions-short)
)

(defun c:roof2d-new-solutions-short ( / *error* acos angle3d 3pline unique uniquelil uniquelilident unit mid clockwise-p inside-p distp2t offsett2p removesingles removedoubles correctplanedist collinear-p unioncollinearplaneprints car-sort _vl-sort processtxtipl chksolution test chklili findlinesbetweentl chklilinlillst processipl processipll processplaa postprocessplaa process postprocessmain postprocess processing cmde s ti lw lwi lwx pl tl utl pla plao n plaa x y lil ll ip ipl ipld ipldd ipldl pla1 maxlen mode dx chk fff errlis plal ret pos errli iter dd lilo done ffff plaal ipx erripl errpts dd1 dd11 dd2 dd22 ddx iplx lilx defaultsort errlisl pass index ipl1sort case loop comb startcomb lillsto qq qqq plaalo )

  (vl-load-com)

  (defun *error* ( m )
    (if cmde
      (setvar 'cmdecho cmde)
    )
    (if (and lwi (not (vlax-erased-p lwi)))
      (entdel lwi)
    )
    (if qq
      (prompt "\nSome solution(s) was(were) founded... Note that there may be more solutions, but with some different algorithm...")
      (prompt "\nThere are no alternate solutions that could be founded at least not with this algorithm...")
    )
    (prompt "\nElapsed time : ") (princ (rtos (- (car (_vl-times)) ti) 2 16)) (prompt " milliseconds...")
    (prompt "\nExit combination : ") (princ return)
    (prompt "\nIf routine was unexpectidly terminated and you want memory clear, type (setq return nil k nil lils nil lillst nil) at command prompt... \nreturn varibable is global that is needed for continuing next time - type enter at start combination input...")
    (princ "\n")
    (if m
      (prompt m)
    )
    (princ)
  )

  (defun acos ( x )
    (cond
      ( (equal x 1.0 1e-8) 0.0 )
      ( (equal x -1.0 1e-8) pi )
      ( (and (not (minusp x)) (equal x 0.0 1e-8)) (/ pi 2.0) )
      ( (and (minusp x) (equal x 0.0 1e-8)) (* 3.0 (/ pi 2.0)) )
      ( (atan (sqrt (- 1.0 (* x x))) x) )
    )
  )

  (defun angle3d ( p1 por p2 / vec1 vec2 dd ang )
    (setq vec1 (unit (mapcar '- p1 por))
          vec2 (unit (mapcar '- p2 por))
          dd (distance vec1 vec2)
          ang (acos (- 1.0 (/ (expt dd 2) 2.0)))
    )
    (if (minusp ang) (+ ang pi) ang)
  )

  (defun 3pline ( p1 p p2 )
    (equal (distance p1 p2) (+ (distance p1 p) (distance p p2)) 1e-6)
  )

  (defun unique ( l / a ll )
    (while (setq a (car l))
      (if (vl-some (function (lambda ( x ) (equal x a 1e-6))) (cdr l))
        (setq ll (cons a ll) l (vl-remove-if (function (lambda ( x ) (equal x a 1e-6))) (cdr l)))
        (setq ll (cons a ll) l (cdr l))
      )
    )
    (reverse ll)
  )

  (defun uniquelil ( l / a ll )
    (while (setq a (car l))
      (if (vl-some (function (lambda ( x ) (or (equal x a 1e-6) (equal x (reverse a) 1e-6)))) (cdr l))
        (setq ll (cons a ll) l (vl-remove-if (function (lambda ( x ) (or (equal x a 1e-6) (equal x (reverse a) 1e-6)))) (cdr l)))
        (setq ll (cons a ll) l (cdr l))
      )
    )
    (reverse ll)
  )

  (defun uniquelilident ( l / a ll )
    (while (setq a (car l))
      (if (vl-some (function (lambda ( x ) (and (equal (car a) (car x) 1e-6) (equal (cadr a) (cadr x) 1e-6)))) (cdr l))
        (setq ll (cons a ll) l (vl-remove-if (function (lambda ( x ) (and (equal (car a) (car x) 1e-6) (equal (cadr a) (cadr x) 1e-6)))) (cdr l)))
        (setq ll (cons a ll) l (cdr l))
      )
    )
    (reverse ll)
  )

  (defun unit ( v / d )
    (if (not (equal (setq d (distance (list 0.0 0.0 0.0) v)) 0.0 1e-8))
      (mapcar (function (lambda ( x ) (/ x d))) v)
    )
  )

  (defun mid ( p1 p2 )
    (mapcar (function (lambda ( a b ) (/ (+ a b) 2.0))) p1 p2)
  )

  (defun clockwise-p ( p1 p2 p3 )
    (minusp (sin (- (angle p1 p3) (angle p1 p2))))
  )

  (defun inside-p ( pt lw lwi )
    (< (distance pt (vlax-curve-getclosestpointto lwi pt)) (distance pt (vlax-curve-getclosestpointto lw pt)))
  )

  (defun distp2t ( p tt / i )
    (if (setq i (inters p (polar p (+ (angle (car tt) (cadr tt)) (* 0.5 pi)) 1.0) (car tt) (cadr tt) nil))
      (distance p i)
    )
  )

  (defun offsett2p ( p tt d / ip v v1 )
    (setq ip (inters p (polar p (+ (angle (car tt) (cadr tt)) (* 0.5 pi)) 1.0) (car tt) (cadr tt) nil))
    (setq v (mapcar (function -) p ip))
    (setq v1 (unit v))
    (list (mapcar (function +) (car tt) (mapcar (function *) v1 (list d d))) (mapcar (function +) (cadr tt) (mapcar (function *) v1 (list d d))))
  )

  (defun removesingles ( l / a )
    (while (setq a (vl-some (function (lambda ( x ) (if (= (1- (length l)) (length (vl-remove-if (function (lambda ( y ) (equal x y 1e-6))) l))) x))) l))
      (setq l (vl-remove-if (function (lambda ( x ) (equal x a 1e-6))) l))
    )
    l
  )

  (defun removedoubles ( l / a )
    (while (setq a (vl-some (function (lambda ( x ) (if (= (- (length l) 2) (length (vl-remove-if (function (lambda ( y ) (equal x y 1e-6))) l))) x))) l))
      (setq l (vl-remove-if (function (lambda ( x ) (equal x a 1e-6))) l))
    )
    l
  )

  (defun correctplanedist ( ip / d )
    (if (and (caar ip) (caadr ip) (cadadr ip) (caaddr ip) (cadr (caddr ip)) (equal (setq d (distp2t (caar ip) (cadr ip))) (distp2t (caar ip) (caddr ip)) 1e-6) d)
      d
    )
  )

  (defun collinear-p ( p1 p2 p3 )
    (
      (lambda ( a b c )
        (or
          (equal (+ a b) c 1e-10)
          (equal (+ b c) a 1e-10)
          (equal (+ c a) b 1e-10)
        )
      )
      (distance p1 p2) (distance p2 p3) (distance p1 p3)
    )
  )

  (defun unioncollinearplaneprints ( tl / a b tll )
    (while (setq a (car tl))
      (setq b (vl-remove-if-not (function (lambda ( x ) (and (collinear-p (car a) (cadr a) (car x)) (collinear-p (car a) (cadr a) (cadr x))))) tl))
      (setq tll (cons a tll))
      (if b
        (setq tl (vl-remove-if (function (lambda ( x ) (vl-some (function (lambda ( y ) (equal x y 1e-6))) b))) tl))
        (setq tl (cdr tl))
      )
    )
    tll
  )

  (defun car-sort ( lst cmp / rtn )
    (setq rtn (car lst))
    (foreach itm (cdr lst)
      (if (apply cmp (list itm rtn))
        (setq rtn itm)
      )
    )
    rtn
  )

  (defun _vl-sort ( l f / *q* ll ff gg )
    (if (= (type f) 'sym)
      (setq f (eval f))
    )
    (while (setq *q* (car l))
      (setq ll
        (if (null ll)
          (cons *q* ll)
          (cond
            ( (apply f (list (last ll) *q*))
              (append ll (list *q*))
            )
            ( (apply f (list *q* (car ll)))
              (cons *q* ll)
            )
            ( t
              (setq ff nil)
              (setq gg (apply (function append) (append (mapcar (function (lambda ( *xxx* *yyy* ) (if (null ff) (if (apply f (list *q* *yyy*)) (progn (setq ff t) (list *xxx* *q*)) (list *xxx*)) (list *xxx*)))) ll (cdr ll)) (list (list (last ll))))))
              (if (null ff)
                (append ll (list *q*))
                gg
              )
            )
          )
        )
      )
      (setq l (cdr l))
    )
    ll
  )

  (defun processtxtipl ( tl / ipl tl1 tl2 intt )
    (setq tl1 tl tl2 tl)
    (foreach t1 tl1
      (setq tl2 (cdr tl2))
      (foreach t2 tl2
        (if (setq intt (inters (car t1) (polar (car t1) (angle (car t1) (cadr t1)) 1.0) (car t2) (polar (car t2) (angle (car t2) (cadr t2)) 1.0) nil))
          (setq ipl (cons intt ipl))
          (setq ipl (cons (angle (car t1) (cadr t1)) ipl))
        )
      )
    )
    ipl
  )

  (defun chksolution ( errli / allplanesips anglst )
    (if (and (car errli) (cadr errli))
      (progn
        (setq allplanesips (processtxtipl tl))
        (setq allplanesips (vl-remove-if (function (lambda ( x ) (vl-some (function (lambda ( y ) (equal x y 1e-6))) pl))) allplanesips))
        (setq anglst (vl-remove-if (function listp) allplanesips))
        (if (vl-some (function (lambda ( x ) (or (equal x 1e-8 1e-6) (equal x -1e-8 1e-6)))) anglst)
          (setq anglst (cons 0.0 anglst) anglst (cons pi anglst) anglst (cons (* 2 pi) anglst))
        )
        (setq allplanesips (vl-remove-if-not (function listp) allplanesips))
        (if (or
              (vl-some (function (lambda ( x ) (or
                                                 (3pline (car errli) x (cadr errli))
                                                 (3pline (car errli) (cadr errli) x)
                                                 (3pline (cadr errli) (car errli) x)
                                               )
                                 )) allplanesips
              )
              (vl-some (function (lambda ( x ) (or (equal (angle (car errli) (cadr errli)) x 1e-8) (equal (angle (cadr errli) (car errli)) x 1e-8)))) anglst)
              (vl-some (function (lambda ( x ) (collinear-p (car errli) (cadr errli) x))) pl)
            )
          t
        )
      )
      t
    )
  )

  (defun test nil
    (and
      (not (vl-some (function (lambda ( x ) (and (not (vl-some (function (lambda ( y ) (inters (car x) (cadr x) (car y) (cadr y)))) lil)) (not (vl-some (function (lambda ( y ) (3pline (car y) (polar (car x) (angle (car x) (cadr x)) 0.01) (cadr y)))) tl)) (inside-p (polar (car x) (angle (car x) (cadr x)) 0.01) lw lwi) (inside-p (polar (cadr x) (angle (cadr x) (car x)) 0.01) lw lwi)))) ll))
      (vl-every (function (lambda ( li ) (chksolution li))) lil)
      (vl-every (function (lambda ( x ) (vl-some (function (lambda ( y ) (equal x y 1e-6))) (apply (function append) lil)))) pl)
      (not (vl-some (function (lambda ( li1 ) (vl-some (function (lambda ( li2 / ip ) (and (setq ip (inters (car li1) (cadr li1) (car li2) (cadr li2))) (not (equal ip (car li1) 1e-6)) (not (equal ip (cadr li1) 1e-6)) (not (equal ip (car li2) 1e-6)) (not (equal ip (cadr li2) 1e-6))))) (vl-remove li1 lil)))) lil))
    )
  )

  (defun chklili ( lil / lilpts )
    (setq lilpts (apply (function append) lil))
    (setq lilpts (vl-remove-if-not (function (lambda ( x ) (= (length (vl-remove-if (function (lambda ( y ) (equal x y 1e-6))) lilpts)) (- (length lilpts) 2)))) lilpts))
    lilpts
  )

  (defun findlinesbetweentl ( tl / ll tl1 tl2 )
    (setq tl1 tl tl2 tl)
    (foreach t1 tl1
      (setq tl2 (cdr tl2))
      (foreach t2 tl2
        (setq ll (cons (list (mid (car t1) (cadr t1)) (mid (car t2) (cadr t2))) ll))
      )
    )
    ll
  )

  (defun chklilinlillst ( l lst / l1 l2 )
    (setq l1 (apply (function append) l))
    (setq l2 (apply (function append) (apply (function append) lst)))
    (vl-every (function (lambda ( x ) (vl-some (function (lambda ( y ) (equal x y 5e-2))) l2))) l1)
  )

  (defun processipl ( pla / pla1 pla2 intt xx xxx xxxx uu ipl )
    (setq pla (vl-remove nil pla))
    (setq pla1 pla pla2 pla)
    (foreach p1 pla1
      (setq pla2 (cdr pla2))
      (foreach p2 pla2
        (setq intt (inters (caar p1) (polar (caar p1) (cadar p1) 1.0) (caar p2) (polar (caar p2) (cadar p2) 1.0) nil))
        (if (or (equal intt (caar p1) 1e-6) (equal intt (caar p2) 1e-6))
          (setq intt nil)
        )
        (if intt
          (if (setq xxx (vl-some (function (lambda ( x ) (if (= (length (vl-remove x (append (list (cadr p1) (caddr p1)) (list (cadr p2) (caddr p2))))) 2) x))) (append (list (cadr p1) (caddr p1)) (list (cadr p2) (caddr p2)))))
            (if (or (and (caadr p1) (cadadr p1) (caaddr p1) (cadr (caddr p1)) (or (equal (angle (caadr p1) (cadadr p1)) (angle (caaddr p1) (cadr (caddr p1))) 1e-6) (equal (angle (cadadr p1) (caadr p1)) (angle (caaddr p1) (cadr (caddr p1))) 1e-6)) (setq xx (vl-some (function (lambda ( x ) (if (equal x (mapcar (function +) intt (mapcar (function -) intt (caar p2))) 1e-6) x))) pl)) (or (equal (angle xx intt) (cadar (vl-some (function (lambda ( x ) (if (equal xx (caar x) 1e-6) x))) pla)) 1e-6) (equal (angle intt xx) (cadar (vl-some (function (lambda ( x ) (if (equal xx (caar x) 1e-6) x))) pla)) 1e-6))) (and (caadr p2) (cadadr p2) (caaddr p2) (cadr (caddr p2)) (or (equal (angle (caadr p2) (cadadr p2)) (angle (caaddr p2) (cadr (caddr p2))) 1e-6) (equal (angle (cadadr p2) (caadr p2)) (angle (caaddr p2) (cadr (caddr p2))) 1e-6)) (setq xx (vl-some (function (lambda ( x ) (if (equal x (mapcar (function +) intt (mapcar (function -) intt (caar p1))) 1e-6) x))) pl)) (or (equal (angle xx intt) (cadar (vl-some (function (lambda ( x ) (if (equal xx (caar x) 1e-6) x))) pla)) 1e-6) (equal (angle intt xx) (cadar (vl-some (function (lambda ( x ) (if (equal xx (caar x) 1e-6) x))) pla)) 1e-6))))
              (cond
                ( (and (caadr p1) (cadadr p1) (caaddr p1) (cadr (caddr p1)) (or (equal (angle (caadr p1) (cadadr p1)) (angle (caaddr p1) (cadr (caddr p1))) 1e-6) (equal (angle (cadadr p1) (caadr p1)) (angle (caaddr p1) (cadr (caddr p1))) 1e-6)))
                  (setq ipl (cons (list (list intt (if (setq xx (vl-remove xxx (list (cadr p2) (caddr p2)))) (angle (caar xx) (cadar xx)) (cadar p2))) (car xx) (if (and (caar xx) (cadar xx) (distp2t intt (car xx))) (offsett2p intt (car xx) (* (distp2t intt (car xx)) 2.0))) nil p1 p2) ipl))
                )
                ( t
                  (setq ipl (cons (list (list intt (if (setq xx (vl-remove xxx (list (cadr p1) (caddr p1)))) (angle (caar xx) (cadar xx)) (cadar p1))) (car xx) (if (and (caar xx) (cadar xx) (distp2t intt (car xx))) (offsett2p intt (car xx) (* (distp2t intt (car xx)) 2.0))) nil p1 p2) ipl))
                )
              )
              (setq ipl (cons (list (list intt (if (setq xxxx (if (and (setq xx (vl-remove xxx (append (list (cadr p1) (caddr p1)) (list (cadr p2) (caddr p2))))) (= (length xx) 2)) (inters (caar xx) (cadar xx) (caadr xx) (cadadr xx) nil))) (angle xxxx intt) (angle (caar xx) (cadar xx)))) (car xx) (cadr xx) xxx p1 p2) ipl))
            )
            (cond
              ( (or (and (caadr p1) (cadadr p1) (caaddr p1) (cadr (caddr p1)) (or (equal (angle (caadr p1) (cadadr p1)) (angle (caaddr p1) (cadr (caddr p1))) 1e-6) (equal (angle (cadadr p1) (caadr p1)) (angle (caaddr p1) (cadr (caddr p1))) 1e-6)) (setq xx (vl-some (function (lambda ( x ) (if (equal x (mapcar (function +) intt (mapcar (function -) intt (caar p2))) 1e-6) x))) pl)) (or (equal (angle xx intt) (cadar (vl-some (function (lambda ( x ) (if (equal xx (caar x) 1e-6) x))) pla)) 1e-6) (equal (angle intt xx) (cadar (vl-some (function (lambda ( x ) (if (equal xx (caar x) 1e-6) x))) pla)) 1e-6))) (and (caadr p2) (cadadr p2) (caaddr p2) (cadr (caddr p2)) (or (equal (angle (caadr p2) (cadadr p2)) (angle (caaddr p2) (cadr (caddr p2))) 1e-6) (equal (angle (cadadr p2) (caadr p2)) (angle (caaddr p2) (cadr (caddr p2))) 1e-6)) (setq xx (vl-some (function (lambda ( x ) (if (equal x (mapcar (function +) intt (mapcar (function -) intt (caar p1))) 1e-6) x))) pl)) (or (equal (angle xx intt) (cadar (vl-some (function (lambda ( x ) (if (equal xx (caar x) 1e-6) x))) pla)) 1e-6) (equal (angle intt xx) (cadar (vl-some (function (lambda ( x ) (if (equal xx (caar x) 1e-6) x))) pla)) 1e-6))))
                (cond
                  ( (and (caadr p1) (cadadr p1) (caaddr p1) (cadr (caddr p1)) (or (equal (angle (caadr p1) (cadadr p1)) (angle (caaddr p1) (cadr (caddr p1))) 1e-6) (equal (angle (cadadr p1) (caadr p1)) (angle (caaddr p1) (cadr (caddr p1))) 1e-6)))
                    (setq ipl (cons (list (list intt (if (setq xx (vl-remove xxx (list (cadr p2) (caddr p2)))) (angle (caar xx) (cadar xx)) (cadar p2))) (car xx) (if (and (caar xx) (cadar xx) (distp2t intt (car xx))) (offsett2p intt (car xx) (* (distp2t intt (car xx)) 2.0))) nil p1 p2) ipl))
                  )
                  ( t
                    (setq ipl (cons (list (list intt (if (setq xx (vl-remove xxx (list (cadr p1) (caddr p1)))) (angle (caar xx) (cadar xx)) (cadar p1))) (car xx) (if (and (caar xx) (cadar xx) (distp2t intt (car xx))) (offsett2p intt (car xx) (* (distp2t intt (car xx)) 2.0))) nil p1 p2) ipl))
                  )
                )
              )
              ( (= (length (setq uu (unioncollinearplaneprints (append (list (cadr p1) (caddr p1)) (list (cadr p2) (caddr p2)))))) 3)
                (foreach pp uu
                  (if (= (length (vl-remove-if-not (function (lambda ( x ) (or (equal pp x) (and (3pline (if (> (distance (car pp) (car x)) (distance (cadr pp) (car x))) (car pp) (cadr pp)) (if (> (distance (car pp) (car x)) (distance (cadr pp) (car x))) (cadr pp) (car pp)) (car x)) (3pline (if (> (distance (car pp) (cadr x)) (distance (cadr pp) (cadr x))) (car pp) (cadr pp)) (if (> (distance (car pp) (cadr x)) (distance (cadr pp) (cadr x))) (cadr pp) (car pp)) (cadr x)))))) (append (list (cadr p1) (caddr p1)) (list (cadr p2) (caddr p2))))) 2)
                    (setq xxx pp)
                  )
                )
                (setq ipl (cons (list (list intt (if (setq xxxx (if (and (setq xx (vl-remove xxx uu)) (= (length xx) 2)) (inters (caar xx) (cadar xx) (caadr xx) (cadadr xx) nil))) (angle xxxx intt) (angle (caar xx) (cadar xx)))) (car xx) (cadr xx) nil p1 p2) ipl))
              )
              ( t
                (setq ipl (cons (list (list intt nil) nil nil nil p1 p2) ipl))
              )
            )
          )
        )
      )
    )
    (setq ipl (vl-remove-if-not (function (lambda ( p / d1 d2 ) (and (inside-p (caar p) lw lwi) (removedoubles (removesingles (vl-remove nil (mapcar (function (lambda ( tt ) (distp2t (caar p) tt))) utl)))) (if (and (caadr p) (cadadr p) (caaddr p) (cadr (caddr p))) (or (and (setq d1 (distance (caar p) (vlax-curve-getclosestpointto lw (caar p)))) (setq d2 (correctplanedist p)) (> d1 d2)) (and d1 d2 (equal d1 d2 1e-6))) t)))) ipl))
  )

  (defun processipll ( / makeipll ipl1l errx err ipl1 lst ipll ipllx dd d )

    (defun makeipll nil
      (if
        (cond
          ( (= case 0)
            (setq lst (vl-remove-if-not (function (lambda ( x ) (and (equal (caar ipl1) (caar x) 1e-6) (not (vl-some (function (lambda ( y ) (or (and (not (equal (caaar (cddddr x)) (caar y) 1e-6)) (not (equal (caar x) (caar y) 1e-6)) (3pline (caaar (cddddr x)) (caar y) (caar x))) (and (not (equal (caaadr (cddddr x)) (caar y) 1e-6)) (not (equal (caar x) (caar y) 1e-6)) (3pline (caaadr (cddddr x)) (caar y) (caar x)))))) (vl-remove x ipl)))))) ipl))
          )
          ( (= case 1)
            (setq lst (vl-remove-if-not (function (lambda ( x ) (equal (caar ipl1) (caar x) 1e-6))) (vl-remove-if (function (lambda ( x ) (vl-some (function (lambda ( y ) (and (equal (caar x) (caar y) 1e-6) (vl-some (function (lambda ( q ) (or (and (not (equal (caar x) (caar q) 1e-6)) (not (equal (caaar (cddddr x)) (caar q) 1e-6)) (3pline (caar x) (caar q) (caaar (cddddr x)))) (and (not (equal (caar x) (caar q) 1e-6)) (not (equal (caaadr (cddddr x)) (caar q) 1e-6)) (3pline (caar x) (caar q) (caaadr (cddddr x))))))) ipl)))) errx))) ipl)))
          )
          ( (= case 2)
            (setq lst (vl-remove-if-not (function (lambda ( x ) (equal (caar ipl1) (caar x) 1e-6))) ipl))
          )
        )
        (setq ipll (cons (_vl-sort lst (if (/= case 2) (function (lambda ( a b / aa bb n m ) (if (or (null (cadddr a)) (null (cadddr b))) (if (or (not (vl-some (function (lambda ( x ) (or (equal x (caaar (cddddr a)) 1e-6) (equal x (caaadr (cddddr a)) 1e-6)))) pl)) (not (vl-some (function (lambda ( x ) (or (equal x (caaar (cddddr b)) 1e-6) (equal x (caaadr (cddddr b)) 1e-6)))) pl))) (< (max (distance (caar a) (caaar (cddddr a))) (distance (caar a) (caaadr (cddddr a)))) (max (distance (caar b) (caaar (cddddr b))) (distance (caar b) (caaadr (cddddr b))))) (progn (setq aa (cond ( (and (setq a1 (vl-some (function (lambda ( x ) (if (equal x (caaar (cddddr a)) 1e-6) x))) pl)) (setq a2 (vl-some (function (lambda ( x ) (if (equal x (caaadr (cddddr a)) 1e-6) x))) pl))) (car-sort (list a1 a2) (function (lambda ( c d ) (< (vl-some (function (lambda ( q ) (setq nn (if (null nn) 0 (1+ nn))) (if (equal q c 1e-6) nn))) (append pl pl)) (vl-some (function (lambda ( q ) (setq mm (if (null mm) 0 (1+ mm))) (if (equal q d 1e-6) mm))) (append pl pl)))))) ) ( (vl-some (function (lambda ( x ) (if (equal x (caaar (cddddr a)) 1e-6) x))) pl) ) ( (vl-some (function (lambda ( x ) (if (equal x (caaadr (cddddr a)) 1e-6) x))) pl) ) )) (setq bb (cond ( (and (setq b1 (vl-some (function (lambda ( x ) (if (equal x (caaar (cddddr b)) 1e-6) x))) pl)) (setq b2 (vl-some (function (lambda ( x ) (if (equal x (caaadr (cddddr b)) 1e-6) x))) pl))) (car-sort (list b1 b2) (function (lambda ( c d ) (< (vl-some (function (lambda ( q ) (setq gg (if (null gg) 0 (1+ gg))) (if (equal q c 1e-6) gg))) (append pl pl)) (vl-some (function (lambda ( q ) (setq hh (if (null hh) 0 (1+ hh))) (if (equal q d 1e-6) hh))) (append pl pl)))))) ) ( (vl-some (function (lambda ( x ) (if (equal x (caaar (cddddr b)) 1e-6) x))) pl) ) ( (vl-some (function (lambda ( x ) (if (equal x (caaadr (cddddr b)) 1e-6) x))) pl) ) )) (setq a1 nil a2 nil nn nil mm nil b1 nil b2 nil gg nil hh nil) (< (vl-some (function (lambda ( q ) (setq n (if (null n) 0 (1+ n))) (if (equal q aa 1e-6) n))) (append pl pl)) (vl-some (function (lambda ( q ) (setq m (if (null m) 0 (1+ m))) (if (equal q bb 1e-6) m))) (append pl pl))))) (< (vl-some (function (lambda ( q ) (setq n (if (null n) 0 (1+ n))) (if (equal q (cadddr a) 1e-6) n))) (append tl tl)) (vl-some (function (lambda ( q ) (setq m (if (null m) 0 (1+ m))) (if (equal q (cadddr b) 1e-6) m))) (append tl tl)))))) (function (lambda ( a b ) (< (max (distance (caar a) (caaar (cddddr a))) (distance (caar a) (caaadr (cddddr a)))) (max (distance (caar b) (caaar (cddddr b))) (distance (caar b) (caaadr (cddddr b))))))))) ipll))
      )
    )

    (setq d (car-sort (removedoubles (removesingles (vl-remove nil (mapcar (function (lambda ( tt ) (distp2t (cadar lil) tt))) utl)))) (function <)))
    (setq ipl (vl-remove-if (function (lambda ( x ) (or (null (cadr x)) (vl-some (function (lambda ( y ) (equal (caar x) y 1e-6))) errpts)))) ipl))
    (if (= case 1)
      (progn
        (foreach pla1 pla
          (setq ipl1l (vl-remove-if-not (function (lambda ( z ) (or (equal (angle (caar z) (caar pla1)) (cadar pla1) 1e-6) (equal (angle (caar pla1) (caar z)) (cadar pla1) 1e-6)))) ipl))
          (foreach ipl1 ipl1l
            (if (vl-some (function (lambda ( x ) (or (and (not (equal (caar x) (caar ipl1) 1e-6)) (not (equal (caar x) (caaar (cddddr ipl1)) 1e-6)) (3pline (caar ipl1) (caar x) (caaar (cddddr ipl1)))) (and (not (equal (caar x) (caar ipl1) 1e-6)) (not (equal (caar x) (caaadr (cddddr ipl1)) 1e-6)) (3pline (caar ipl1) (caar x) (caaadr (cddddr ipl1))))))) ipl1l)
              (setq errx (cons ipl1 errx))
            )
          )
        )
        (setq err (vl-remove-if (function (lambda ( x ) (> (length (vl-remove-if (function (lambda ( y ) (vl-some (function (lambda ( z ) (and (not (equal (caar x) (caar z) 1e-6)) (3pline (caar x) (caar z) (caar y))))) ipl))) (vl-remove-if-not (function (lambda ( y ) (and (or (equal (angle (caar y) (caar x)) (cadar y) 1e-6) (equal (angle (caar x) (caar y)) (cadar y) 1e-6))))) pla))) 1))) errx))
      )
    )
    (foreach pla1 pla
      (setq ipl1l (vl-remove-if-not (function (lambda ( z ) (or (equal (angle (caar z) (caar pla1)) (cadar pla1) 1e-6) (equal (angle (caar pla1) (caar z)) (cadar pla1) 1e-6)))) ipl))
      (cond
        ( (= case 1)
          (if (setq dd (vl-remove-if (function (lambda ( x ) (vl-some (function (lambda ( y ) (equal (caar x) (caar y) 1e-6))) err))) ipl1l))
            (setq ipl1l dd)
          )
        )
        ( (= case 2)
          (if (and lils (setq dd (vl-remove-if (function (lambda ( x ) (vl-some (function (lambda ( y ) (equal (caar x) (cadr y) 1e-6))) lils))) ipl1l)))
            (setq ipl1l dd)
          )
        )
      )
      (setq ipl1
        (cond
          ( (= ipl1sort 0)
            (car-sort ipl1l (function (lambda ( a b ) (if (equal (car-sort (list (distance (caaar (cddddr a)) (caar a)) (distance (caaadr (cddddr a)) (caar a)) (distance (vlax-curve-getclosestpointto lw (caar a)) (caar a))) (function <)) (car-sort (list (distance (caaar (cddddr b)) (caar b)) (distance (caaadr (cddddr b)) (caar b)) (distance (vlax-curve-getclosestpointto lw (caar b)) (caar b))) (function <)) 1e-6) (< (distance (caaar (cddddr a)) (caaadr (cddddr a))) (distance (caaar (cddddr b)) (caaadr (cddddr b)))) (< (car-sort (list (distance (caaar (cddddr a)) (caar a)) (distance (caaadr (cddddr a)) (caar a)) (distance (vlax-curve-getclosestpointto lw (caar a)) (caar a))) (function <)) (car-sort (list (distance (caaar (cddddr b)) (caar b)) (distance (caaadr (cddddr b)) (caar b)) (distance (vlax-curve-getclosestpointto lw (caar b)) (caar b))) (function <)))))))
          )
          ( (= ipl1sort 1)
            (car-sort ipl1l (function (lambda ( a b ) (if (equal (angle3d (append (caaar (cddddr a)) (list 0.0)) (append (caar a) (list 0.0)) (append (caaadr (cddddr a)) (list 0.0))) (angle3d (append (caaar (cddddr b)) (list 0.0)) (append (caar b) (list 0.0)) (append (caaadr (cddddr b)) (list 0.0))) 1e-6) (if (equal (car-sort (list (distance (caaar (cddddr a)) (caar a)) (distance (caaadr (cddddr a)) (caar a)) (distance (vlax-curve-getclosestpointto lw (caar a)) (caar a))) (function <)) (car-sort (list (distance (caaar (cddddr b)) (caar b)) (distance (caaadr (cddddr b)) (caar b)) (distance (vlax-curve-getclosestpointto lw (caar b)) (caar b))) (function <)) 1e-6) (< (distance (caaar (cddddr a)) (caaadr (cddddr a))) (distance (caaar (cddddr b)) (caaadr (cddddr b)))) (< (car-sort (list (distance (caaar (cddddr a)) (caar a)) (distance (caaadr (cddddr a)) (caar a)) (distance (vlax-curve-getclosestpointto lw (caar a)) (caar a))) (function <)) (car-sort (list (distance (caaar (cddddr b)) (caar b)) (distance (caaadr (cddddr b)) (caar b)) (distance (vlax-curve-getclosestpointto lw (caar b)) (caar b))) (function <)))) (> (angle3d (append (caaar (cddddr a)) (list 0.0)) (append (caar a) (list 0.0)) (append (caaadr (cddddr a)) (list 0.0))) (angle3d (append (caaar (cddddr b)) (list 0.0)) (append (caar b) (list 0.0)) (append (caaadr (cddddr b)) (list 0.0))))))))
          )
          ( (= ipl1sort 2)
            (car-sort ipl1l (function (lambda ( a b ) (< (distance (vlax-curve-getclosestpointto lw (caar a)) (caar a)) (distance (vlax-curve-getclosestpointto lw (caar b)) (caar b))))))
          )
          ( (= ipl1sort 3)
            (car-sort ipl1l (function (lambda ( a b ) (< (abs (- d (car-sort (removedoubles (removesingles (vl-remove nil (mapcar (function (lambda ( tt ) (distp2t (caar a) tt))) utl)))) (function <)))) (abs (- d (car-sort (removedoubles (removesingles (vl-remove nil (mapcar (function (lambda ( tt ) (distp2t (caar b) tt))) utl)))) (function <))))))))
          )
          ( (= ipl1sort 4)
            (car-sort ipl1l (function (lambda ( a b ) (< (distance (cadar lil) (caar a)) (distance (cadar lil) (caar b))))))
          )
          ( (= ipl1sort 5)
            (car-sort ipl1l (function (lambda ( a b ) (< (min (distance (caar a) (caaar (cddddr a))) (distance (caar a) (caaadr (cddddr a)))) (min (distance (caar b) (caaar (cddddr b))) (distance (caar b) (caaadr (cddddr b))))))))
          )
          ( (= ipl1sort 6)
            (car-sort ipl1l (function (lambda ( a b ) (> (min (distance (caar a) (caaar (cddddr a))) (distance (caar a) (caaadr (cddddr a)))) (min (distance (caar b) (caaar (cddddr b))) (distance (caar b) (caaadr (cddddr b))))))))
          )
          ( (= ipl1sort 7)
            (car-sort ipl1l (function (lambda ( a b ) (< (max (distance (caar a) (caaar (cddddr a))) (distance (caar a) (caaadr (cddddr a)))) (max (distance (caar b) (caaar (cddddr b))) (distance (caar b) (caaadr (cddddr b))))))))
          )
          ( (= ipl1sort 8)
            (car-sort ipl1l (function (lambda ( a b ) (> (max (distance (caar a) (caaar (cddddr a))) (distance (caar a) (caaadr (cddddr a)))) (max (distance (caar b) (caaar (cddddr b))) (distance (caar b) (caaadr (cddddr b))))))))
          )
          ( (= ipl1sort 9)
            (car-sort ipl1l (function (lambda ( a b ) (> (distance (caar a) (caar pla1)) (distance (caar b) (caar pla1))))))
          )
          ( (= ipl1sort 10)
            (car-sort ipl1l (function (lambda ( a b ) (< (distance (caar a) (caar pla1)) (distance (caar b) (caar pla1))))))
          )
        )
      )
      (if (= case 2)
        (if (and ipl1 (if (and (setq zzz (vl-some (function (lambda ( x ) (vl-some (function (lambda ( y ) (if (and (not (equal (caar x) (caar y) 1e-6)) (not (equal (caar x) (caar ipl1) 1e-6)) (not (equal (caar y) (caar ipl1) 1e-6)) (or (and (not (equal (caar y) (caaar (cddddr ipl1)) 1e-6)) (not (equal (caar x) (caaar (cddddr ipl1)) 1e-6)) (and (or (inters (caar y) (polar (caar y) (cadar y) 1e+6) (caaar (cddddr ipl1)) (caar ipl1)) (inters (caar y) (polar (caar y) (cadar y) -1e+6) (caaar (cddddr ipl1)) (caar ipl1))) (equal (caar x) (inters (caar y) (polar (caar y) (cadar y) 1.0) (caaar (cddddr ipl1)) (caar ipl1) nil) 1e-6))) (and (not (equal (caar y) (caaadr (cddddr ipl1)) 1e-6)) (not (equal (caar x) (caaadr (cddddr ipl1)) 1e-6)) (and (or (inters (caar y) (polar (caar y) (cadar y) 1e+6) (caaadr (cddddr ipl1)) (caar ipl1)) (inters (caar y) (polar (caar y) (cadar y) -1e+6) (caaadr (cddddr ipl1)) (caar ipl1))) (equal (caar x) (inters (caar y) (polar (caar y) (cadar y) 1.0) (caaadr (cddddr ipl1)) (caar ipl1) nil) 1e-6))))) (list x y)))) (vl-remove-if (function (lambda ( x ) (null (cadar x)))) (append pla ipl))))) (vl-remove-if (function (lambda ( x ) (null (cadar x)))) (append pla ipl)))) (vl-some (function (lambda ( x ) (and (not (equal (caar x) (caaar zzz) 1e-6)) (not (equal (caar x) (caaadr zzz) 1e-6)) (equal (distance (caaar zzz) (caaadr zzz)) (+ (distance (caaar zzz) (caar x)) (distance (caar x) (caaadr zzz))) 1e-6)))) (append pla ipl))) t (not zzz)))
          (makeipll)
        )
        (makeipll)
      )
    )
    (if mode
      (setq iplx (append (vl-remove nil ipl) (if errpts (mapcar (function (lambda ( x ) (list (list x nil) nil nil nil nil nil))) errpts))))
    )
    (if (and (/= case 2) lils (setq dd (vl-remove-if (function (lambda ( x ) (vl-some (function (lambda ( y ) (equal (caaar x) y 1e-6))) (mapcar (function cadr) lils)))) (vl-remove nil ipll))))
      (setq ipll dd)
    )
    (if (and plaalo (setq dd (vl-remove-if (function (lambda ( x ) (vl-some (function (lambda ( y ) (equal (caaar x) (caaar y) 1e-6))) plaalo))) (vl-remove nil ipll))))
      (setq ipll dd)
    )
    (if (setq dd (vl-remove-if (function (lambda ( x ) (vl-every (function (lambda ( y ) (null (cadar y)))) x))) (vl-remove nil ipll)))
      (setq ipll dd)
    )
    (cond
      ( (= defaultsort 0)
        (car-sort (vl-remove nil ipll) (function (lambda ( a b ) (if (equal (car-sort (list (distance (caaar (cddddr (car a))) (caar (car a))) (distance (caaadr (cddddr (car a))) (caar (car a))) (distance (vlax-curve-getclosestpointto lw (caaar a)) (caaar a))) (function <)) (car-sort (list (distance (caaar (cddddr (car b))) (caar (car b))) (distance (caaadr (cddddr (car b))) (caar (car b))) (distance (vlax-curve-getclosestpointto lw (caaar b)) (caaar b))) (function <)) 1e-6) (< (distance (caaar (cddddr (car a))) (caaadr (cddddr (car a)))) (distance (caaar (cddddr (car b))) (caaadr (cddddr (car b))))) (< (car-sort (list (distance (caaar (cddddr (car a))) (caar (car a))) (distance (caaadr (cddddr (car a))) (caar (car a))) (distance (vlax-curve-getclosestpointto lw (caaar a)) (caaar a))) (function <)) (car-sort (list (distance (caaar (cddddr (car b))) (caar (car b))) (distance (caaadr (cddddr (car b))) (caar (car b))) (distance (vlax-curve-getclosestpointto lw (caaar b)) (caaar b))) (function <)))))))
      )
      ( (= defaultsort 1)
        (car-sort (vl-remove nil ipll) (function (lambda ( a b ) (if (equal (angle3d (append (caaar (cddddr (car a))) (list 0.0)) (append (caaar a) (list 0.0)) (append (caaadr (cddddr (car a))) (list 0.0))) (angle3d (append (caaar (cddddr (car b))) (list 0.0)) (append (caaar b) (list 0.0)) (append (caaadr (cddddr (car b))) (list 0.0))) 1e-6) (if (equal (car-sort (list (distance (caaar (cddddr (car a))) (caar (car a))) (distance (caaadr (cddddr (car a))) (caar (car a))) (distance (vlax-curve-getclosestpointto lw (caaar a)) (caaar a))) (function <)) (car-sort (list (distance (caaar (cddddr (car b))) (caar (car b))) (distance (caaadr (cddddr (car b))) (caar (car b))) (distance (vlax-curve-getclosestpointto lw (caaar b)) (caaar b))) (function <)) 1e-6) (< (distance (caaar (cddddr (car a))) (caaadr (cddddr (car a)))) (distance (caaar (cddddr (car b))) (caaadr (cddddr (car b))))) (< (car-sort (list (distance (caaar (cddddr (car a))) (caar (car a))) (distance (caaadr (cddddr (car a))) (caar (car a))) (distance (vlax-curve-getclosestpointto lw (caaar a)) (caaar a))) (function <)) (car-sort (list (distance (caaar (cddddr (car b))) (caar (car b))) (distance (caaadr (cddddr (car b))) (caar (car b))) (distance (vlax-curve-getclosestpointto lw (caaar b)) (caaar b))) (function <)))) (> (angle3d (append (caaar (cddddr (car a))) (list 0.0)) (append (caaar a) (list 0.0)) (append (caaadr (cddddr (car a))) (list 0.0))) (angle3d (append (caaar (cddddr (car b))) (list 0.0)) (append (caaar b) (list 0.0)) (append (caaadr (cddddr (car b))) (list 0.0))))))))
      )
      ( (= defaultsort 2)
        (car-sort (vl-remove nil ipll) (function (lambda ( a b ) (< (distance (vlax-curve-getclosestpointto lw (caaar a)) (caaar a)) (distance (vlax-curve-getclosestpointto lw (caaar b)) (caaar b))))))
      )
      ( (= defaultsort 3)
        (car-sort (vl-remove nil ipll) (function (lambda ( a b ) (< (abs (- d (car-sort (removedoubles (removesingles (vl-remove nil (mapcar (function (lambda ( tt ) (distp2t (caaar a) tt))) utl)))) (function <)))) (abs (- d (car-sort (removedoubles (removesingles (vl-remove nil (mapcar (function (lambda ( tt ) (distp2t (caaar b) tt))) utl)))) (function <))))))))
      )
      ( (= defaultsort 4)
        (car-sort (vl-remove nil ipll) (function (lambda ( a b ) (< (distance (cadar lil) (caaar a)) (distance (cadar lil) (caaar b))))))
      )
      ( (= defaultsort 5)
        (car-sort (vl-remove nil ipll) (function (lambda ( a b ) (< (min (distance (caaar a) (caaar (cddddr (car a)))) (distance (caaar a) (caaadr (cddddr (car a))))) (min (distance (caaar b) (caaar (cddddr (car b)))) (distance (caaar b) (caaadr (cddddr (car b)))))))))
      )
      ( (= defaultsort 6)
        (car-sort (vl-remove nil ipll) (function (lambda ( a b ) (> (min (distance (caaar a) (caaar (cddddr (car a)))) (distance (caaar a) (caaadr (cddddr (car a))))) (min (distance (caaar b) (caaar (cddddr (car b)))) (distance (caaar b) (caaadr (cddddr (car b)))))))))
      )
      ( (= defaultsort 7)
        (car-sort (vl-remove nil ipll) (function (lambda ( a b ) (< (max (distance (caaar a) (caaar (cddddr (car a)))) (distance (caaar a) (caaadr (cddddr (car a))))) (max (distance (caaar b) (caaar (cddddr (car b)))) (distance (caaar b) (caaadr (cddddr (car b)))))))))
      )
      ( (= defaultsort 8)
        (car-sort (vl-remove nil ipll) (function (lambda ( a b ) (> (max (distance (caaar a) (caaar (cddddr (car a)))) (distance (caaar a) (caaadr (cddddr (car a))))) (max (distance (caaar b) (caaar (cddddr (car b)))) (distance (caaar b) (caaadr (cddddr (car b)))))))))
      )
      ( (= defaultsort 9)
        (if (vl-some (function (lambda ( x ) (equal (caar x) (cadar lil) 1e-6))) pla)
          (if (setq ipllx (car-sort (vl-remove-if (function (lambda ( x ) (vl-some (function (lambda ( y ) (equal (caar x) y 1e-6))) (append (apply (function append) errlis) (mapcar (function caar) plaal))))) (vl-remove nil ipll)) (function (lambda ( a b / c d ) (if (and (setq c (correctplanedist (car a))) (setq d (correctplanedist (car b))) (equal c d 1e-6)) (< (distance (cadar lil) (caaar a)) (distance (cadar lil) (caaar b))) (if (or (null c) (null d)) (< (distance (cadar lil) (caaar a)) (distance (cadar lil) (caaar b))) (< c d)))))))
            (setq ipll ipllx)
            (if (setq ipllx (car-sort (vl-remove-if (function (lambda ( x ) (vl-some (function (lambda ( y ) (equal (caar x) y 1e-6))) (apply (function append) errlis)))) (vl-remove nil ipll)) (function (lambda ( a b / c d ) (if (and (setq c (correctplanedist (car a))) (setq d (correctplanedist (car b))) (equal c d 1e-6)) (< (distance (cadar lil) (caaar a)) (distance (cadar lil) (caaar b))) (if (or (null c) (null d)) (< (distance (cadar lil) (caaar a)) (distance (cadar lil) (caaar b))) (< c d)))))))
              (setq ipll ipllx)
              (if (setq ipllx (car-sort (vl-remove-if (function (lambda ( x ) (vl-some (function (lambda ( y ) (equal (caar x) y 1e-6))) (mapcar (function caar) plaal)))) (vl-remove nil ipll)) (function (lambda ( a b / c d ) (if (and (setq c (correctplanedist (car a))) (setq d (correctplanedist (car b))) (equal c d 1e-6)) (< (distance (cadar lil) (caaar a)) (distance (cadar lil) (caaar b))) (if (or (null c) (null d)) (< (distance (cadar lil) (caaar a)) (distance (cadar lil) (caaar b))) (< c d)))))))
                (setq ipll ipllx)
                (setq ipll (car-sort (vl-remove nil ipll) (function (lambda ( a b / c d ) (if (and (setq c (correctplanedist (car a))) (setq d (correctplanedist (car b))) (equal c d 1e-6)) (< (distance (cadar lil) (caaar a)) (distance (cadar lil) (caaar b))) (if (or (null c) (null d)) (< (distance (cadar lil) (caaar a)) (distance (cadar lil) (caaar b))) (< c d)))))))
              )
            )
          )
          (if lil
            (if (setq ipllx (car-sort (vl-remove-if (function (lambda ( x ) (vl-some (function (lambda ( y ) (equal (caar x) y 1e-6))) (append (apply (function append) errlis) (mapcar (function caar) plaal))))) (vl-remove nil ipll)) (function (lambda ( a b / c d ) (if (and (setq c (correctplanedist (car a))) (setq d (correctplanedist (car b))) (equal c d 1e-6)) (> (distance (cadar lil) (caaar a)) (distance (cadar lil) (caaar b))) (if (or (null c) (null d)) (> (distance (cadar lil) (caaar a)) (distance (cadar lil) (caaar b))) (< c d)))))))
              (setq ipll ipllx)
              (if (setq ipllx (car-sort (vl-remove-if (function (lambda ( x ) (vl-some (function (lambda ( y ) (equal (caar x) y 1e-6))) (apply (function append) errlis)))) (vl-remove nil ipll)) (function (lambda ( a b / c d ) (if (and (setq c (correctplanedist (car a))) (setq d (correctplanedist (car b))) (equal c d 1e-6)) (> (distance (cadar lil) (caaar a)) (distance (cadar lil) (caaar b))) (if (or (null c) (null d)) (> (distance (cadar lil) (caaar a)) (distance (cadar lil) (caaar b))) (< c d)))))))
                (setq ipll ipllx)
                (if (setq ipllx (car-sort (vl-remove-if (function (lambda ( x ) (vl-some (function (lambda ( y ) (equal (caar x) y 1e-6))) (mapcar (function caar) plaal)))) (vl-remove nil ipll)) (function (lambda ( a b / c d ) (if (and (setq c (correctplanedist (car a))) (setq d (correctplanedist (car b))) (equal c d 1e-6)) (> (distance (cadar lil) (caaar a)) (distance (cadar lil) (caaar b))) (if (or (null c) (null d)) (> (distance (cadar lil) (caaar a)) (distance (cadar lil) (caaar b))) (< c d)))))))
                  (setq ipll ipllx)
                  (setq ipll (car-sort (vl-remove nil ipll) (function (lambda ( a b / c d ) (if (and (setq c (correctplanedist (car a))) (setq d (correctplanedist (car b))) (equal c d 1e-6)) (> (distance (cadar lil) (caaar a)) (distance (cadar lil) (caaar b))) (if (or (null c) (null d)) (> (distance (cadar lil) (caaar a)) (distance (cadar lil) (caaar b))) (< c d)))))))
                )
              )
            )
            (setq ipll (car-sort (vl-remove nil ipll) (function (lambda ( a b / c d ) (if (and (setq c (correctplanedist (car a))) (setq d (correctplanedist (car b)))) (< c d) (< (distance (caaar a) (vlax-curve-getclosestpointto lw (caaar a))) (distance (caaar b) (vlax-curve-getclosestpointto lw (caaar b)))))))))
          )
        )
        ipll
      )
    )
  )

  (defun processplaa ( pla / processerrli errlis errip erripl ip dd pos errli iter )

    (defun processerrli nil
      (if (not (vl-some (function (lambda ( x ) (equal x errlis 1e-6))) errlisl))
        (progn
          (setq errlisl (cons errlis errlisl))
          (setq pos (car-sort (mapcar (function (lambda ( x ) (vl-position x (reverse lil)))) errlis) (function <)))
          (setq errli (nth pos (reverse lil)))
          (setq iter (fix (/ pos 2.0)))
          (setq lil (cdr (member (nth (* 2 iter) (reverse lil)) lil)))
          (setq pla (nth iter (reverse plal)))
          (setq plal (cdr (member (nth iter (reverse plal)) plal)))
          (setq plaalo (vl-remove nil plaal))
          (setq plaal (cdr (member (nth iter (reverse plaal)) plaal)))
          (setq ipl (processipl pla))
          (setq ipl (vl-remove-if (function (lambda ( x ) (vl-some (function (lambda ( y ) (equal (caar x) y 1e-6))) (mapcar (function cadr) lil)))) ipl))
          (setq ipl (vl-remove-if (function (lambda ( x ) (vl-some (function (lambda ( y ) (or (setq ip (inters (polar (car y) (angle (car y) (cadr y)) 1e-3) (polar (cadr y) (angle (cadr y) (car y)) 1e-3) (caaar (cddddr x)) (caar x))) (setq ip (inters (polar (car y) (angle (car y) (cadr y)) 1e-3) (polar (cadr y) (angle (cadr y) (car y)) 1e-3) (caaadr (cddddr x)) (caar x)))))) tl))) ipl))
          (setq ipl (vl-remove-if (function (lambda ( x ) (vl-some (function (lambda ( y ) (equal (caar x) (cadr y) 1e-6))) (mapcar (function cadr) erripl)))) ipl))
          (setq ipl (vl-remove-if (function (lambda ( x ) (vl-some (function (lambda ( y ) (equal (caar x) (caar y) 1e-6))) plaa))) ipl))
        )
        (if (< (length pass) index)
          (progn
            (setq pass (cons t pass))
            (setq pos (car-sort (mapcar (function (lambda ( x ) (vl-position x (reverse lil)))) errlis) (function <)))
            (setq errli (nth pos (reverse lil)))
            (setq iter (fix (/ pos 2.0)))
            (setq lil (cdr (member (nth (* 2 iter) (reverse lil)) lil)))
            (setq pla (nth iter (reverse plal)))
            (setq plal (cdr (member (nth iter (reverse plal)) plal)))
            (setq plaalo (vl-remove nil plaal))
            (setq plaal (cdr (member (nth iter (reverse plaal)) plaal)))
            (setq ipl (processipl pla))
            (setq ipl (vl-remove-if (function (lambda ( x ) (vl-some (function (lambda ( y ) (equal (caar x) y 1e-6))) (mapcar (function cadr) lil)))) ipl))
            (setq ipl (vl-remove-if (function (lambda ( x ) (vl-some (function (lambda ( y ) (or (setq ip (inters (polar (car y) (angle (car y) (cadr y)) 1e-3) (polar (cadr y) (angle (cadr y) (car y)) 1e-3) (caaar (cddddr x)) (caar x))) (setq ip (inters (polar (car y) (angle (car y) (cadr y)) 1e-3) (polar (cadr y) (angle (cadr y) (car y)) 1e-3) (caaadr (cddddr x)) (caar x)))))) tl))) ipl))
            (setq ipl (vl-remove-if (function (lambda ( x ) (vl-some (function (lambda ( y ) (equal (caar x) (cadr y) 1e-6))) (mapcar (function cadr) erripl)))) ipl))
            (setq ipl (vl-remove-if (function (lambda ( x ) (vl-some (function (lambda ( y ) (equal (caar x) (caar y) 1e-6))) plaa))) ipl))
          )
          (progn
            (setq pass nil)
            (if (and (null qqq) lil (test) (not (chklili lil)) (<= n (length lil)))
              (progn
                (if (not (chklilinlillst lil lillst))
                  (setq lillst (cons lil lillst) qqq t lilo lil n 0)
                  (setq lillst (cons nil lillst) lilo lil n 0)
                )
                (list nil pla)
              )
              (list nil pla)
            )
          )
        )
      )
    )

    (setq ipl (processipl pla))
    (if (and (null ipl) (null qqq) lil (test) (not (chklili lil)) (<= n (length lil)))
      (progn
        (if (not (chklilinlillst lil lillst))
          (setq lillst (cons lil lillst) qqq t lilo lil n 0)
          (setq lillst (cons nil lillst) lilo lil n 0)
        )
        (list nil pla)
      )
      (if (null ipl)
        (list nil pla)
        (progn
          (setq ipl (vl-remove-if (function (lambda ( x ) (null (cadr x)))) ipl))
          (setq ipl (vl-remove-if (function (lambda ( x ) (vl-some (function (lambda ( y ) (equal (caar x) y 1e-6))) (mapcar (function cadr) lil)))) ipl))
          (setq ipl (vl-remove-if (function (lambda ( x ) (vl-some (function (lambda ( y ) (or (setq ip (inters (polar (car y) (angle (car y) (cadr y)) 1e-3) (polar (cadr y) (angle (cadr y) (car y)) 1e-3) (caaar (cddddr x)) (caar x))) (setq ip (inters (polar (car y) (angle (car y) (cadr y)) 1e-3) (polar (cadr y) (angle (cadr y) (car y)) 1e-3) (caaadr (cddddr x)) (caar x)))))) tl))) ipl))
          (foreach li lil
            (if (setq errip (vl-some (function (lambda ( x ) (if (and (setq ip (inters (caar x) (caaar (cddddr x)) (car li) (cadr li))) (not (equal (caar x) ip 1e-6)) (not (equal (caaar (cddddr x)) ip 1e-6)) (not (equal (car li) ip 1e-6)) (not (equal (cadr li) ip 1e-6))) x))) ipl))
              (setq errlis (cons li errlis) erripl (cons (list ip li errip) erripl))
            )
            (if (setq errip (vl-some (function (lambda ( x ) (if (and (setq ip (inters (caar x) (caaadr (cddddr x)) (car li) (cadr li))) (not (equal (caar x) ip 1e-6)) (not (equal (caaadr (cddddr x)) ip 1e-6)) (not (equal (car li) ip 1e-6)) (not (equal (cadr li) ip 1e-6))) x))) ipl))
              (setq errlis (cons li errlis) erripl (cons (list ip li errip) erripl))
            )
          )
          (if errlis
            (setq errlis (vl-remove-if-not (function (lambda ( x ) (vl-some (function (lambda ( y ) (equal (cadr x) y 1e-6))) (mapcar (function cadr) errlis)))) lil))
          )
          (if errlis
            (if (setq dd (vl-remove-if (function (lambda ( x ) (vl-some (function (lambda ( y ) (equal x y 1e-6))) (mapcar (function caddr) erripl)))) ipl))
              (if (null dd11)
                (setq ipl dd dd11 dd)
                (if (null dd2)
                  (setq ipl dd dd22 dd)
                  (if (setq ddx (vl-remove-if-not (function (lambda ( x ) (vl-some (function (lambda ( y ) (equal x y 1e-6))) dd11))) dd22))
                    (setq ipl ddx dd11 nil dd22 nil)
                    (setq ipl dd)
                  )
                )
              )
              (processerrli)
            )
          )
          (list (processipll) pla)
        )
      )
    )
  )

  (defun process ( processplafun )
    (while (> n 0)
      (if (null plaa)
        (progn
          (setq ipl (processipl pla))
          (setq ipl (vl-remove-if (function (lambda ( x ) (null (cadar x)))) ipl))
          (setq ipldl (mapcar (function (lambda ( x ) (list (correctplanedist x) x))) ipl))
          (setq ipld (mapcar (function cadr) (vl-remove-if (function (lambda ( x ) (null (car x)))) ipldl)))
          (while (setq pla1 (car ipld))
            (setq ipldd (cons (vl-remove-if-not (function (lambda ( x ) (equal (caar pla1) (caar x) 1e-6))) ipld) ipldd))
            (setq ipld (vl-remove-if (function (lambda ( x ) (equal (caar pla1) (caar x) 1e-6))) ipld))
          )
          (setq maxlen (length (car-sort ipldd (function (lambda ( a b ) (> (length a) (length b)))))))
          (if (> maxlen 1)
            (setq mode t)
          )
          (setq pla1 (cadr (car-sort (vl-remove-if (function (lambda ( x ) (null (car x)))) ipldl) (function (lambda ( a b ) (if (equal (car a) (car b) 1e-6) (< (length (vl-remove-if-not (function (lambda ( x ) (equal (caaadr a) (caaadr x) 1e-6))) (vl-remove-if (function (lambda ( x ) (null (car x)))) ipldl))) (length (vl-remove-if-not (function (lambda ( x ) (equal (caaadr b) (caaadr x) 1e-6))) (vl-remove-if (function (lambda ( x ) (null (car x)))) ipldl)))) (< (car a) (car b))))))))
          (setq plaa (_vl-sort (mapcar (function cadr) (vl-remove-if-not (function (lambda ( x ) (equal (caar pla1) (caaadr x) 1e-6))) (vl-remove-if (function (lambda ( x ) (null (car x)))) ipldl))) (function (lambda ( a b / aa bb n m ) (if (or (null (cadddr a)) (null (cadddr b))) (if (or (not (vl-some (function (lambda ( x ) (or (equal x (caaar (cddddr a)) 1e-6) (equal x (caaadr (cddddr a)) 1e-6)))) pl)) (not (vl-some (function (lambda ( x ) (or (equal x (caaar (cddddr b)) 1e-6) (equal x (caaadr (cddddr b)) 1e-6)))) pl))) (< (max (distance (caar a) (caaar (cddddr a))) (distance (caar a) (caaadr (cddddr a)))) (max (distance (caar b) (caaar (cddddr b))) (distance (caar b) (caaadr (cddddr b))))) (progn (setq aa (cond ( (and (setq a1 (vl-some (function (lambda ( x ) (if (equal x (caaar (cddddr a)) 1e-6) x))) pl)) (setq a2 (vl-some (function (lambda ( x ) (if (equal x (caaadr (cddddr a)) 1e-6) x))) pl))) (car-sort (list a1 a2) (function (lambda ( c d ) (< (vl-some (function (lambda ( q ) (setq nn (if (null nn) 0 (1+ nn))) (if (equal q c 1e-6) nn))) (append pl pl)) (vl-some (function (lambda ( q ) (setq mm (if (null mm) 0 (1+ mm))) (if (equal q d 1e-6) mm))) (append pl pl)))))) ) ( (vl-some (function (lambda ( x ) (if (equal x (caaar (cddddr a)) 1e-6) x))) pl) ) ( (vl-some (function (lambda ( x ) (if (equal x (caaadr (cddddr a)) 1e-6) x))) pl) ) )) (setq bb (cond ( (and (setq b1 (vl-some (function (lambda ( x ) (if (equal x (caaar (cddddr b)) 1e-6) x))) pl)) (setq b2 (vl-some (function (lambda ( x ) (if (equal x (caaadr (cddddr b)) 1e-6) x))) pl))) (car-sort (list b1 b2) (function (lambda ( c d ) (< (vl-some (function (lambda ( q ) (setq gg (if (null gg) 0 (1+ gg))) (if (equal q c 1e-6) gg))) (append pl pl)) (vl-some (function (lambda ( q ) (setq hh (if (null hh) 0 (1+ hh))) (if (equal q d 1e-6) hh))) (append pl pl)))))) ) ( (vl-some (function (lambda ( x ) (if (equal x (caaar (cddddr b)) 1e-6) x))) pl) ) ( (vl-some (function (lambda ( x ) (if (equal x (caaadr (cddddr b)) 1e-6) x))) pl) ) )) (setq a1 nil a2 nil nn nil mm nil b1 nil b2 nil gg nil hh nil) (< (vl-some (function (lambda ( q ) (setq n (if (null n) 0 (1+ n))) (if (equal q aa 1e-6) n))) (append pl pl)) (vl-some (function (lambda ( q ) (setq m (if (null m) 0 (1+ m))) (if (equal q bb 1e-6) m))) (append pl pl))))) (< (vl-some (function (lambda ( q ) (setq n (if (null n) 0 (1+ n))) (if (equal q (cadddr a) 1e-6) n))) (append tl tl)) (vl-some (function (lambda ( q ) (setq m (if (null m) 0 (1+ m))) (if (equal q (cadddr b) 1e-6) m))) (append tl tl))))))))
          (if (not (vl-every (function (lambda ( x ) (equal (caar x) (caaar plaa) 1e-6))) plaa))
            (setq plaa (list (car plaa)))
          )
        )
        (if (equal plaa (setq plaa (unique (car (setq ret (apply processplafun (list (unique pla))))))) 1e-6)
          (setq n 0)
        )
      )
      (postprocessplaa)
    )
  )

  (defun postprocessplaa ( / xxx xxxx x1 x2 xxxx1 xxx1 xxx2 xx )
    (setq plal (cons (if (null plal) pla (setq pla (cadr ret))) plal))
    (setq plaal (cons plaa plaal))
    (if (and (car plaa) (vl-every (function (lambda ( x ) (cadar x))) plaa))
      (foreach pla1 (reverse plaa)
        (if (not (vl-some (function (lambda ( x ) (equal pla1 x 1e-6))) pla))
          (setq pla (cons pla1 pla))
        )
      )
      (progn
        (setq n (length utl))
        (if (and (test) (not (chklili lil)) (<= n (length lil)))
          (setq n 0)
          (progn
            (foreach pla1 pla
              (if (setq ip (vl-some (function (lambda ( x ) (if (or (equal (angle (caar pla1) x) (cadar pla1) 1e-6) (equal (angle x (caar pla1)) (cadar pla1) 1e-6)) x))) (mapcar (function cadr) lil)))
                (if (and (not (vl-some (function (lambda ( z ) (equal z (list (caar pla1) ip) 1e-6))) lil)) (not (vl-some (function (lambda ( z ) (equal z (list ip (caar pla1)) 1e-6))) lil)))
                  (setq lil (cons (list (caar pla1) ip) lil))
                )
              )
            )
            (if (and (test) (not (chklili lil)) (<= n (length lil)))
              (setq n 0)
              (postprocess)
            )
          )
        )
      )
    )
    (if plaa
      (if (= (length plaa) 1)
        (progn
          (setq x (caaar (cddddr (car plaa))))
          (setq y (caaadr (cddddr (car plaa))))
          (if (and x y (caaar plaa) (not (or (vl-some (function (lambda ( z ) (equal z (list x (caaar plaa)) 1e-6))) lil) (vl-some (function (lambda ( z ) (equal z (list (caaar plaa) x) 1e-6))) lil))))
            (if (not (equal x (caaar plaa) 1e-6))
              (progn
                (if (and mode (setq ip (cond ( (vl-some (function (lambda ( z ) (if (and (3pline x (caar z) (caaar plaa)) (not (equal x (caar z) 1e-6)) (not (equal (caaar plaa) (caar z) 1e-6))) (caar z)))) iplx) ) ( (vl-some (function (lambda ( q ) (if (and (3pline x q (caaar plaa)) (not (equal x q 1e-6)) (not (equal (caaar plaa) q 1e-6))) q))) (apply (function append) lil)) ))))
                  (cond
                    ( (and ip (not (vl-some (function (lambda ( z ) (or (equal z (list x ip) 1e-6) (equal z (list ip x) 1e-6)))) lil)) (not (vl-some (function (lambda ( z ) (or (equal z (list ip (caaar plaa)) 1e-6) (equal z (list (caaar plaa) ip) 1e-6)))) lil)))
                      (setq lil (cons (list x ip) lil) lil (cons (list ip (caaar plaa)) lil))
                    )
                    ( (and ip (not (vl-some (function (lambda ( z ) (or (equal z (list x ip) 1e-6) (equal z (list ip x) 1e-6)))) lil)))
                      (setq lil (cons (list x ip) lil))
                    )
                    ( (and ip (not (vl-some (function (lambda ( z ) (or (equal z (list ip (caaar plaa)) 1e-6) (equal z (list (caaar plaa) ip) 1e-6)))) lil)))
                      (setq lil (cons (list ip (caaar plaa)) lil))
                    )
                    ( (not ip)
                      (setq lil (cons (list x (caaar plaa)) lil))
                    )
                  )
                  (setq lil (cons (list x (caaar plaa)) lil))
                )
                (setq pla (vl-remove-if (function (lambda ( z ) (equal x (caar z) 1e-6))) pla))
              )
            )
          )
          (if (and x y (caaar plaa) (not (or (vl-some (function (lambda ( z ) (equal z (list y (caaar plaa)) 1e-6))) lil) (vl-some (function (lambda ( z ) (equal z (list (caaar plaa) y) 1e-6))) lil))))
            (if (not (equal y (caaar plaa) 1e-6))
              (progn
                (if (and mode (setq ip (cond ( (vl-some (function (lambda ( z ) (if (and (3pline y (caar z) (caaar plaa)) (not (equal y (caar z) 1e-6)) (not (equal (caaar plaa) (caar z) 1e-6))) (caar z)))) iplx) ) ( (vl-some (function (lambda ( q ) (if (and (3pline y q (caaar plaa)) (not (equal y q 1e-6)) (not (equal (caaar plaa) q 1e-6))) q))) (apply (function append) lil)) ))))
                  (cond
                    ( (and ip (not (vl-some (function (lambda ( z ) (or (equal z (list y ip) 1e-6) (equal z (list ip y) 1e-6)))) lil)) (not (vl-some (function (lambda ( z ) (or (equal z (list ip (caaar plaa)) 1e-6) (equal z (list (caaar plaa) ip) 1e-6)))) lil)))
                      (setq lil (cons (list y ip) lil) lil (cons (list ip (caaar plaa)) lil))
                    )
                    ( (and ip (not (vl-some (function (lambda ( z ) (or (equal z (list y ip) 1e-6) (equal z (list ip y) 1e-6)))) lil)))
                      (setq lil (cons (list y ip) lil))
                    )
                    ( (and ip (not (vl-some (function (lambda ( z ) (or (equal z (list ip (caaar plaa)) 1e-6) (equal z (list (caaar plaa) ip) 1e-6)))) lil)))
                      (setq lil (cons (list ip (caaar plaa)) lil))
                    )
                    ( (not ip)
                      (setq lil (cons (list y (caaar plaa)) lil))
                    )
                  )
                  (setq lil (cons (list y (caaar plaa)) lil))
                )
                (setq pla (vl-remove-if (function (lambda ( z ) (equal y (caar z) 1e-6))) pla))
              )
            )
          )
        )
        (progn
          (foreach pla1 plaa
            (setq x (caaar (cddddr pla1)))
            (setq y (caaadr (cddddr pla1)))
            (if (and x y (caar pla1) (not (or (vl-some (function (lambda ( z ) (equal z (list x (caar pla1)) 1e-6))) lil) (vl-some (function (lambda ( z ) (equal z (list (caar pla1) x) 1e-6))) lil))))
              (if (not (equal x (caar pla1) 1e-6))
                (progn
                  (if (and mode (setq ip (cond ( (vl-some (function (lambda ( z ) (if (and (3pline x (caar z) (caar pla1)) (not (equal x (caar z) 1e-6)) (not (equal (caar pla1) (caar z) 1e-6))) (caar z)))) iplx) ) ( (vl-some (function (lambda ( q ) (if (and (3pline x q (caar pla1)) (not (equal x q 1e-6)) (not (equal (caar pla1) q 1e-6))) q))) (apply (function append) lil)) ))))
                    (cond
                      ( (and ip (not (vl-some (function (lambda ( z ) (or (equal z (list x ip) 1e-6) (equal z (list ip x) 1e-6)))) lil)) (not (vl-some (function (lambda ( z ) (or (equal z (list ip (caar pla1)) 1e-6) (equal z (list (caar pla1) ip) 1e-6)))) lil)))
                        (setq lil (cons (list x ip) lil) lil (cons (list ip (caar pla1)) lil))
                      )
                      ( (and ip (not (vl-some (function (lambda ( z ) (or (equal z (list x ip) 1e-6) (equal z (list ip x) 1e-6)))) lil)))
                        (setq lil (cons (list x ip) lil))
                      )
                      ( (and ip (not (vl-some (function (lambda ( z ) (or (equal z (list ip (caar pla1)) 1e-6) (equal z (list (caar pla1) ip) 1e-6)))) lil)))
                        (setq lil (cons (list ip (caar pla1)) lil))
                      )
                      ( (not ip)
                        (setq lil (cons (list x (caar pla1)) lil))
                      )
                    )
                    (setq lil (cons (list x (caar pla1)) lil))
                  )
                  (setq pla (vl-remove-if (function (lambda ( z ) (equal x (caar z) 1e-6))) pla))
                )
              )
            )
            (if (and x y (caar pla1) (not (or (vl-some (function (lambda ( z ) (equal z (list y (caar pla1)) 1e-6))) lil) (vl-some (function (lambda ( z ) (equal z (list (caar pla1) y) 1e-6))) lil))))
              (if (not (equal y (caar pla1) 1e-6))
                (progn
                  (if (and mode (setq ip (cond ( (vl-some (function (lambda ( z ) (if (and (3pline y (caar z) (caar pla1)) (not (equal y (caar z) 1e-6)) (not (equal (caar pla1) (caar z) 1e-6))) (caar z)))) iplx) ) ( (vl-some (function (lambda ( q ) (if (and (3pline y q (caar pla1)) (not (equal y q 1e-6)) (not (equal (caar pla1) q 1e-6))) q))) (apply (function append) lil)) ))))
                    (cond
                      ( (and ip (not (vl-some (function (lambda ( z ) (or (equal z (list y ip) 1e-6) (equal z (list ip y) 1e-6)))) lil)) (not (vl-some (function (lambda ( z ) (or (equal z (list ip (caar pla1)) 1e-6) (equal z (list (caar pla1) ip) 1e-6)))) lil)))
                        (setq lil (cons (list y ip) lil) lil (cons (list ip (caar pla1)) lil))
                      )
                      ( (and ip (not (vl-some (function (lambda ( z ) (or (equal z (list y ip) 1e-6) (equal z (list ip y) 1e-6)))) lil)))
                        (setq lil (cons (list y ip) lil))
                      )
                      ( (and ip (not (vl-some (function (lambda ( z ) (or (equal z (list ip (caar pla1)) 1e-6) (equal z (list (caar pla1) ip) 1e-6)))) lil)))
                        (setq lil (cons (list ip (caar pla1)) lil))
                      )
                      ( (not ip)
                        (setq lil (cons (list y (caar pla1)) lil))
                      )
                    )
                    (setq lil (cons (list y (caar pla1)) lil))
                  )
                  (setq pla (vl-remove-if (function (lambda ( z ) (equal y (caar z) 1e-6))) pla))
                )
              )
            )
          )
          (if (< 2 (length (unioncollinearplaneprints (unique (apply (function append) (mapcar (function (lambda ( x ) (list (list (caar x) (caaar (cddddr x))) (list (caar x) (caaadr (cddddr x)))))) plaa))))))
            (if (not (vl-every (function (lambda ( x ) (vl-some (function (lambda ( y ) (or (equal y (caaar (cddddr x)) 1e-6) (equal y (caaadr (cddddr x)) 1e-6)))) pl))) plaa))
              (setq pla (vl-remove-if (function (lambda ( z ) (vl-some (function (lambda ( x ) (equal (caar x) (caar z) 1e-6))) plaa))) pla))
              (cond
                ( (and (= 3 (length (unique (apply (function append) (mapcar (function (lambda ( x ) (list (list (caar x) (caaar (cddddr x))) (list (caar x) (caaadr (cddddr x)))))) plaa))))) (vl-some (function (lambda ( x ) (null (cadddr x)))) plaa))
                  (setq pla (vl-remove-if (function (lambda ( z ) (vl-some (function (lambda ( x ) (equal (caar x) (caar z) 1e-6))) plaa))) pla))
                )
                ( (= 3 (length (unique (apply (function append) (mapcar (function (lambda ( x ) (list (list (caar x) (caaar (cddddr x))) (list (caar x) (caaadr (cddddr x)))))) plaa)))))
                  nil
                )
                ( t
                  (setq pla (vl-remove-if (function (lambda ( z ) (vl-some (function (lambda ( x ) (equal (caar x) (caar z) 1e-6))) plaa))) pla))
                  (setq x1 (car plaa))
                  (setq x2 (last plaa))
                  (if (vl-some (function (lambda ( x ) (not (vl-position (caar x) pl)))) (cddddr (vl-some (function (lambda ( y ) (if (or (not (vl-position (caaar (cddddr y)) pl)) (not (vl-position (caaadr (cddddr y)) pl))) y))) plaa)))
                    (progn
                      (setq pla (append pla (apply (function append) (mapcar (function cddddr) plaa))))
                      (setq errpts (cons (caaar plaa) errpts))
                    )
                  )
                  (setq xx (list (list (caar x1) (if (setq ip (inters (car (cadr x1)) (cadr (cadr x1)) (car (caddr x2)) (cadr (caddr x2)) nil)) (angle (caar x1) ip) (angle (car (cadr x1)) (cadr (cadr x1))))) (cadr x1) (caddr x2) nil (car (cddddr x1)) (cadr (cddddr x2))))
                  (setq pla (cons xx pla))
                )
              )
            )
            (if (= 3 (length (unique (apply (function append) (mapcar (function (lambda ( x ) (list (list (caar x) (caaar (cddddr x))) (list (caar x) (caaadr (cddddr x)))))) plaa)))))
              (if (setq xxx (vl-some (function (lambda ( x ) (if (= (length (vl-remove-if (function (lambda ( y ) (equal x y 1e-6))) (apply (function append) (mapcar (function (lambda ( x ) (list (list (caar x) (caaar (cddddr x))) (list (caar x) (caaadr (cddddr x)))))) plaa)))) 2) x))) (apply (function append) (mapcar (function (lambda ( x ) (list (list (caar x) (caaar (cddddr x))) (list (caar x) (caaadr (cddddr x)))))) plaa))))
                (setq pla (cons (car (vl-remove-if (function (lambda ( x ) (equal (caar x) (car (vl-remove (caaar plaa) xxx)) 1e-6))) (append (cddddr (car plaa)) (cddddr (cadr plaa))))) pla))
              )
            )
          )
        )
      )
    )
  )

  (defun postprocessmain nil
    (setq pos (car-sort (mapcar (function (lambda ( x ) (vl-position x (reverse lil)))) errlis) (function <)))
    (setq errli (nth pos (reverse lil)))
    (setq ip (car-sort (vl-remove nil (mapcar (function (lambda ( x ) (if (and (setq ip (inters (car errli) (cadr errli) (car x) (cadr x))) (not (equal (car errli) ip 1e-6)) (not (equal (cadr errli) ip 1e-6)) (not (equal (car x) ip 1e-6)) (not (equal (cadr x) ip 1e-6))) ip))) lil)) (function (lambda ( a b ) (< (distance (car errli) a) (distance (car errli) b))))))
    (setq iter (fix (/ pos 2.0)))
    (setq lil (cdr (member (nth (* 2 iter) (reverse lil)) lil)))
    (setq pla (nth iter (reverse plal)))
    (setq ipl (processipl pla))
    (setq plal (cdr (member (nth iter (reverse plal)) plal)))
    (setq plaalo (vl-remove nil plaal))
    (setq plaal (cdr (member (nth iter (reverse plaal)) plaal)))
    (setq ipl (vl-remove-if (function (lambda ( x ) (vl-some (function (lambda ( y ) (equal (caar x) y 1e-6))) (mapcar (function cadr) lil)))) ipl))
    (setq ipl (vl-remove-if (function (lambda ( x ) (vl-some (function (lambda ( y ) (or (setq ipx (inters (polar (car y) (angle (car y) (cadr y)) 1e-3) (polar (cadr y) (angle (cadr y) (car y)) 1e-3) (caaar (cddddr x)) (caar x))) (setq ipx (inters (polar (car y) (angle (car y) (cadr y)) 1e-3) (polar (cadr y) (angle (cadr y) (car y)) 1e-3) (caaadr (cddddr x)) (caar x)))))) tl))) ipl))
    (if (and ip (setq dd (vl-remove-if (function (lambda ( x ) (or (3pline (caar x) ip (caaar (cddddr x))) (3pline (caar x) ip (caaadr (cddddr x)))))) ipl)))
      (if (null dd1)
        (setq ipl dd dd1 dd)
        (if (null dd2)
          (setq ipl dd dd2 dd)
          (if (setq ddx (vl-remove-if-not (function (lambda ( x ) (vl-some (function (lambda ( y ) (equal x y 1e-6))) dd1))) dd2))
            (setq ipl ddx dd1 nil dd2 nil)
            (setq ipl dd)
          )
        )
      )
    )
    (if (setq dd (vl-some (function (lambda ( x ) (if (or (equal (car errli) (caaar (cddddr x)) 1e-6) (equal (car errli) (caaadr (cddddr x)) 1e-6)) x))) ipl))
      (setq plaa (list dd))
      (progn
        (setq errlis nil)
        (foreach li lil
          (if (vl-some (function (lambda ( x ) (and (setq ip (inters (caar x) (caaar (cddddr x)) (car li) (cadr li))) (not (equal (caar x) ip 1e-6)) (not (equal (caaar (cddddr x)) ip 1e-6)) (not (equal (car li) ip 1e-6)) (not (equal (cadr li) ip 1e-6))))) ipl)
            (setq errlis (cons li errlis))
          )
          (if (vl-some (function (lambda ( x ) (and (setq ip (inters (caar x) (caaadr (cddddr x)) (car li) (cadr li))) (not (equal (caar x) ip 1e-6)) (not (equal (caaadr (cddddr x)) ip 1e-6)) (not (equal (car li) ip 1e-6)) (not (equal (cadr li) ip 1e-6))))) ipl)
            (setq errlis (cons li errlis))
          )
        )
        (if errlis
          (setq errlis (vl-remove-if-not (function (lambda ( x ) (vl-some (function (lambda ( y ) (equal (cadr x) y 1e-6))) (mapcar (function cadr) errlis)))) lil))
        )
        (if errlis
          (if (setq dd (vl-remove-if (function (lambda ( x ) (vl-some (function (lambda ( y ) (equal x y 1e-6))) (mapcar (function caddr) erripl)))) ipl))
            (setq ipl dd)
          )
        )
        (setq plaa (unique (processipll)))
      )
    )
    (setq ret (list plaa pla))
    (setq n (length utl))
    (postprocessplaa)
    (setq n (length utl))
    (process (function processplaa))
    (setq lil (uniquelil (vl-remove-if (function (lambda ( x ) (equal (car x) (cadr x) 1e-6))) lil)))
    (setq n (length utl))
    (if (car lillst)
      (if (and (null qqq) lil (test) (not (chklili lil)) (<= n (length lil)))
        (progn
          (if (not (chklilinlillst lil lillst))
            (setq lillst (cons lil lillst) qqq t)
            (setq lillst (cons nil lillst))
          )
          (setq loop nil)
        )
        (if (and (= (length lil) (length lilo)) (vl-every (function (lambda ( x ) (vl-some (function (lambda ( y ) (equal x y 1e-6))) lil))) lilo))
          (progn
            (setq lillst (cons nil lillst))
            (setq loop nil)
          )
          (if ffff
            (progn
              (setq lillst (cons nil lillst))
              (setq loop nil)
            )
            (setq ffff t)
          )
        )
      )
    )
  )

  (defun postprocess nil
    (setq loop t)
    (while (and loop (not (and (= (length lil) (length lilo)) (vl-every (function (lambda ( x ) (vl-some (function (lambda ( y ) (equal x y 1e-6))) lil))) lilo))))
      (setq lilo lil)
      (if (and (setq lil (uniquelil lil)) (setq errlis (vl-remove-if-not (function (lambda ( x ) (vl-some (function (lambda ( y ) (and (setq ip (inters (car x) (cadr x) (car y) (cadr y))) (not (equal (car x) ip 1e-6)) (not (equal (cadr x) ip 1e-6)) (not (equal (car y) ip 1e-6)) (not (equal (cadr y) ip 1e-6))))) (vl-remove-if (function (lambda ( z ) (equal z x 1e-6))) lil)))) lil)))
        (postprocessmain)
        (setq loop nil)
      )
    )
    (setq lilx lil n 0)
  )

  (defun processing ( casex ipl1sortx defaultsortx )
    (setq case casex ipl1sort ipl1sortx defaultsort defaultsortx)
    (setq n (length utl))
    (setq lil nil plal nil errl nil lilo nil plaal nil erripl nil mode nil errpts nil errlisl nil pass nil lilx nil qqq nil ppp nil plaalo nil pla plao)
    (process (function processplaa))
    (setq lil (uniquelil (vl-remove-if (function (lambda ( x ) (equal (car x) (cadr x) 1e-6))) lil)))
    (setq n (length utl))
    (if (and (null qqq) lil (test) (not (chklili lil)) (<= n (length lil)))
      (if (not (chklilinlillst lil lillst))
        (setq lillst (cons lil lillst) qqq t)
        (setq lillst (cons nil lillst))
      )
      (postprocess)
    )
    ;|
    (setq n (length utl))
    (if lilx
      (setq lil lilx)
    )
    (if (and lil (test) (not (chklili lil)) (<= n (length lil)))
      (progn
        (setq return (list case ipl1sort defaultsort))
        (princ "\n")
        (princ return)
        nil
      )
      (progn
        (setq return (list case ipl1sort defaultsort))
        (princ "\n")
        (princ return)
        t
      )
    )
    |;
    (setq return (list case ipl1sort defaultsort))
    (princ "\n")
    (princ return)
  )

  (setq cmde (getvar 'cmdecho))
  (setvar 'cmdecho 0)
  (vl-cmdf "_.UNDO" "_BE")
  (prompt "\nPick a closed polygonal LWPOLYLINE...")
  (if (setq s (ssget "_+.:E:S" '((0 . "LWPOLYLINE") (-4 . "&=") (70 . 1) (-4 . "<not") (-4 . "<>") (42 . 0.0) (-4 . "not>"))))
    (progn
      (while (null lils)
        (prompt "\nSelect initial solution...")
        (setq lils (ssget '((0 . "LINE"))))
        (if lils
          (progn
            (setq lils (mapcar (function (lambda ( x ) (mapcar (function (lambda ( y ) (mapcar (function +) (list 0.0 0.0) (cdr y)))) (vl-remove-if-not (function (lambda ( z ) (vl-position (car z) (list 10 11)))) (entget x))))) (vl-remove-if (function listp) (mapcar (function cadr) (ssnamex lils)))))
            (setq lillst (cons lils lillst))
          )
        )
      )
      (initget 4)
      (setq index (getint "\nSpecify solutions search index - greater number (slower/more solutions); smaller number (faster/less solutions) <0> : "))
      (if (null index)
        (setq index 0)
      )
      (setq startcomb (getpoint "\nEnter start combination (case,ipl1sort,defaultsort) - ENTER FOR LAST EXIT COMBINATION +1 - FOR FRESH START JUST TYPE 0,0,0 : "))
      (if startcomb
        (setq startcomb (mapcar (function fix) startcomb))
        (if return
          (if (= (1+ (caddr return)) 10)
            (if (= (1+ (cadr return)) 11)
              (if (= (1+ (car return)) 3)
                (progn
                  (prompt "\nYou can't start from last exit combination... Quitting...")
                  (exit)
                )
                (setq startcomb (list (1+ (car return)) 0 0))
              )
              (setq startcomb (list (car return) (1+ (cadr return)) 0))
            )
            (setq startcomb (list (car return) (cadr return) (1+ (caddr return))))
          )
          (setq startcomb (list 0 0 0))
        )
      )
      (if (null startcomb)
        (setq startcomb (list 0 0 0))
      )
      (if startcomb
        (while (and startcomb (or (/= (length startcomb) 3) (not (< -1 (car startcomb) 3)) (not (< -1 (cadr startcomb) 11)) (not (< -1 (caddr startcomb) 10))))
          (prompt "\nInvalid specification of start combination (case must be between -1 and 3), (ipl1sort must be between -1 and 11), (defaultsort must be between -1 and 10)...")
          (setq startcomb (getpoint "\nEnter start combination (case ipl1sort defaultsort) - ENTER FOR LAST EXIT COMBINATION +1 - FOR FRESH START JUST TYPE 0,0,0 : "))
          (if startcomb
            (setq startcomb (mapcar (function fix) startcomb))
            (if return
              (if (= (1+ (caddr return)) 10)
                (if (= (1+ (cadr return)) 11)
                  (if (= (1+ (car return)) 3)
                    (progn
                      (prompt "\nYou can't start from last exit combination... Quitting...")
                      (exit)
                    )
                    (setq startcomb (list (1+ (car return)) 0 0))
                  )
                  (setq startcomb (list (car return) (1+ (cadr return)) 0))
                )
                (setq startcomb (list (car return) (cadr return) (1+ (caddr return))))
              )
              (setq startcomb (list 0 0 0))
            )
          )
        )
      )
      (if (null startcomb)
        (setq startcomb (list 0 0 0))
      )
      (setq comb (getpoint "\nEnter exit combination (case,ipl1sort,defaultsort) - ENTER FOR COMPLETE SEARCH : "))
      (if comb
        (setq comb (mapcar (function fix) comb))
      )
      (if comb
        (while (and comb (or (/= (length comb) 3) (< (car comb) (car startcomb)) (and (>= (car comb) (car startcomb)) (< (caddr comb) (caddr startcomb))) (and (>= (car comb) (car startcomb)) (>= (caddr comb) (caddr startcomb)) (< (caddr comb) (caddr startcomb))) (not (< -1 (car comb) 3)) (not (< -1 (cadr comb) 11)) (not (< -1 (caddr comb) 10))))
          (prompt "\nInvalid specification of exit combination [(case must be between -1 and 3),(ipl1sort must be between -1 and 11),(defaultsort must be between -1 and 10)] - also combination list must be greater than start combination list...")
          (setq comb (getpoint "\nEnter exit combination (case,ipl1sort,defaultsort) : "))
          (if comb
            (setq comb (mapcar (function fix) comb))
          )
        )
      )
      (setq ti (car (_vl-times)))
      (if (= 0 (getvar 'worlducs))
        (vl-cmdf "_.UCS" "_W")
      )
      (setq lwx (entget (setq lw (ssname s 0))))
      (setq lwi (vlax-vla-object->ename (car (vlax-invoke (vlax-ename->vla-object lw) 'offset 0.001))))
      (if (< (vlax-curve-getarea lw) (vlax-curve-getarea lwi))
        (progn
          (entdel lwi)
          (setq lwi (vlax-vla-object->ename (car (vlax-invoke (vlax-ename->vla-object lw) 'offset -0.001))))
        )
      )
      (setq pl (mapcar (function (lambda ( p ) (mapcar (function +) (list 0 0) (trans p lw 0)))) (mapcar (function cdr) (vl-remove-if (function (lambda ( x ) (/= (car x) 10))) lwx))))
      (setq pl (append pl (list (car pl))))
      (setq tl (mapcar (function (lambda ( a b ) (list a b))) (reverse (cdr (reverse pl))) (cdr pl)))
      (setq pla (mapcar (function (lambda ( p mp ) (list p (angle p mp)))) pl (mapcar (function (lambda ( a b ) (cond ( (3pline (car a) (car b) (cadr b)) (vlax-curve-getclosestpointto lwi (car b)) ) ( t (if (clockwise-p (car a) (car b) (cadr b)) (mid (polar (cadr a) (angle (cadr a) (car a)) -1.0) (polar (car b) (angle (car b) (cadr b)) -1.0)) (mid (polar (cadr a) (angle (cadr a) (car a)) 1.0) (polar (car b) (angle (car b) (cadr b)) 1.0))) )))) (cons (last tl) tl) tl)))
      (setq pla (mapcar (function (lambda ( a pla b ) (list pla a b))) (cons (last tl) tl) pla tl))
      (setq plao pla)
      (setq dx (- (car (car-sort pl (function (lambda ( a b ) (> (car a) (car b)))))) (car (car-sort pl (function (lambda ( a b ) (< (car a) (car b))))))))
      (setq ll (findlinesbetweentl tl))
      (setq n (length (setq utl (unioncollinearplaneprints tl))))
      (while (null done)
        (setq lillsto lillst)
        (if (and (null case) (null ipl1sort) (null defaultsort))
          (setq case (car startcomb) ipl1sort (cadr startcomb) defaultsort (caddr startcomb))
        )
        (processing case ipl1sort defaultsort)
        (if (cdr (vl-remove nil lillst))
          (if (chklilinlillst (car (vl-remove nil lillst)) (cdr (vl-remove nil lillst)))
            (setq lillst (cdr (vl-remove nil lillst)))
          )
        )
        (if (null (car lillst))
          (setq lillst (vl-remove nil lillst))
        )
        (if (and comb (= case (car comb)) (= ipl1sort (cadr comb)) (= defaultsort (caddr comb)))
          (setq done t)
        )
        (setq defaultsort (1+ defaultsort))
        (if (= defaultsort 10)
          (progn
            (setq defaultsort 0 ipl1sort (1+ ipl1sort))
            (if (= ipl1sort 11)
              (setq ipl1sort 0 case (1+ case))
            )
          )
        )
        (if (not (equal lillsto lillst 1e-6))
          (progn
            (setq k (if (null k) 1 (1+ k)))
            (entupd (vlax-vla-object->ename (vla-copy (vlax-ename->vla-object lw))))
            (vla-move (vlax-ename->vla-object (entlast)) (vlax-3d-point (list 0.0 0.0 0.0)) (vlax-3d-point (list (* k dx) 0.0 0.0)))
            (setq lil (reverse (car lillst)))
            (foreach li lil
              (entupd (entmakex (list (cons 0 "LINE") (cons 10 (mapcar (function +) (list (* k dx) 0.0) (car li))) (cons 11 (mapcar (function +) (list (* k dx) 0.0) (cadr li))) (cons 62 (1+ k)))))
            )
            (setq lils (uniquelilident (apply (function append) lillst)))
          )
        )
        (if (= case 3)
          (progn
            (if (cdr lillst)
              (setq qq t)
            )
            (setq done t return nil k nil lils nil lillst nil)
          )
        )
      )
    )
  )
  (vl-cmdf "_.UNDO" "_E")
  (*error* nil)
)
