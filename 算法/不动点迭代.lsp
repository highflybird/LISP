;;;利用不动点迭代法求解非线性方程
(defun c:bdd (/ EPS EXPR I X X0 X1 X2)
  (setq expr (getstring "\n输入字符串表达式:" ))
  (CAL:Expr2Func expr 'func '(x))
  (initget 1)
  (setq x1 (getreal "\n下:"))
  (initget 1)
  (setq x2 (getreal "\n上:"))
  (setq i 0)
  (setq eps 1e-14)
  (if (> x1 x2)
    (setq x0 x2)
    (setq x0 x1)
  )
  (setq x (func x0))
  (while (and (< i 100) (> (abs (- x x0)) eps))
    (setq x0 x)
    (setq x (func x0))
    (setq i (1+ i))
  )
  (princ "\n方程的解是: ")
  (princ (rtos x0 2 20))
  (princ "\t方程的值是: ")
  (princ (rtos x 2 20))
  (princ "\t迭代次数: ")
  (princ i)
  (princ)
)

; x-0.556*(sin(x)-x*cos(x)-pi/2)
