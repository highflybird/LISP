(defun cir:fy( p c r)
  (polar c (angle c p) (/ (* r r) (distance p c)))
)

(defun c:xzy()
  (setq cir1 (car (entsel "\n圆1：")))
  (setq cir2 (car (entsel "\n圆2：")))
  (setq cir3 (car (entsel "\n圆3：")))
  (setq cir4 (car (entsel "\n圆4：")))
  (setq dxf1 (entget cir1))
  (setq dxf2 (entget cir2))
  (setq dxf3 (entget cir3))
  (setq dxf4 (entget cir4))
  (setq cen1 (cdr (assoc 10 dxf1)))
  (setq rad1 (cdr (assoc 40 dxf1)))
  (setq cen2 (cdr (assoc 10 dxf2)))
  (setq rad2 (cdr (assoc 40 dxf2)))
  (setq cen3 (cdr (assoc 10 dxf3)))
  (setq rad3 (cdr (assoc 40 dxf3)))
  (setq cen4 (cdr (assoc 10 dxf4)))
  (setq rad4 (cdr (assoc 40 dxf4)))
  (setq lst1 (list (list cen1 rad1) (list cen2 rad2) (list cen3 rad3) (list cen4 rad4)))
)

(defun ent:make_color_point (p c)
  (entmakex
    (list
      '(0 . "POINT")
      (cons 10 p)
      (cons 62 c)
    ) 
  )
)

(defun c:tt()
  (initget 1)
  (setq p (getpoint "\n请输入点:"))
  (initget 7)
  (setq c (getint "\n请输入颜色号:"))
  (setq p (trans p 1 0))
  (ent:make_color_point p c)
  (setq p1 p)
  (foreach n lst1
    (setq pt (cir:fy p1 (car n) (cadr n)))
    (ent:make_color_point pt c)
    (setq p1 pt)
  )
  (setq p1 p)
  (foreach n (reverse lst1)
    (setq pt (cir:fy p1 (car n) (cadr n)))
    (ent:make_color_point pt (1+ c))
    (setq p1 pt)
  )
  (princ)
)
