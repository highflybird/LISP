;;;==========SubFunction==========
;;;def descr-ht-fill 2
(00000002 20 4 2 2 0)
(00000007 5 1		UnVar1)
(00000009 8 2		UnVar2)
(0000000B 100 3		UNVar3)
(0000000D 15 37 0		JMP 00000035)
(00000010 5 2		UnVar2)
(00000012 40		car)
(00000013 8 3		UnVar3)
(00000015 5 2		UnVar2)
(00000017 41		cdr)
(00000018 8 2		UnVar2)
(0000001A 5 3		UnVar3)
(0000001C 40		car)
(0000001D 81 1 245 0 1 0		string)
(00000023 5 0		UnVar0)
(00000025 81 2 244 0 1 0		intern)
(0000002B 5 3		UnVar3)
(0000002D 41		cdr)
(0000002E 81 2 243 0 1 0		set)
(00000034 10)
(00000035 5 2		UnVar2)
(00000037 60 214 255		T->JMP 00000010)
(0000003A 1		nil)
(0000003B 22		ret)
;;;def descr-ht-get? 60
(0000003C 20 2 2 2 0)
(00000041 5 1		UnVar1)
(00000043 81 1 245 0 1 0		string)
(00000049 5 0		UnVar0)
(0000004B 81 2 242 0 1 0		find-symbol)
(00000051 11)
(00000052 8 1		UnVar1)
(00000054 63		nil->ret)
(00000055 5 1		UnVar1)
(00000057 81 1 241 0 1 0		symbol-value)
(0000005D 22		ret)
;;;def al-sys-fun-exist-p 94
(0000005E 20 1 1 1 0)
(00000063 5 0		UnVar0)
(00000065 9 240 0		':AUTOLISP)
(00000068 81 2 242 0 1 0		find-symbol)
(0000006E 11)
(0000006F 8 0		UnVar0)
(00000071 63		nil->ret)
(00000072 5 0		UnVar0)
(00000074 9 239 0		':sys-fun)
(00000077 81 2 238 0 1 0		get)
(0000007D 22		ret)
;;;def al-sys-protected-p 126
(0000007E 20 1 1 1 0)
(00000083 5 0		UnVar0)
(00000085 3 237 0		*al-init-protected*)
(00000088 81 2 236 0 1 0		memq)
(0000008E 22		ret)
;;;def al-form-descr? 143
(0000008F 20 4 1 3 0)
(00000094 100 3		UNVar3)
(00000096 5 1		UnVar1)
(00000098 13 26 0		nil->JMP 000000B5)
(0000009B 5 1		UnVar1)
(0000009D 5 0		UnVar0)
(0000009F 95 2 60 0 0 0		descr-ht-get?)
(000000A5 11)
(000000A6 8 3		UnVar3)
(000000A8 63		nil->ret)
(000000A9 5 2		UnVar2)
(000000AB 14 3 0		T->JMP 000000B1)
(000000AE 9 235 0		':USER)
(000000B1 5 3		UnVar3)
(000000B3 42		cons)
(000000B4 22		ret)
(000000B5 5 0		UnVar0)
(000000B7 3 234 0		*al-spec-form-descr-ht*)
(000000BA 9 233 0		':SPEC)
(000000BD 95 3 143 0 0 0		al-form-descr?)
(000000C3 62		T->ret)
(000000C4 5 0		UnVar0)
(000000C6 3 232 0		*al-sys-fun-descr-ht*)
(000000C9 9 231 0		':INIT-FUN)
(000000CC 97 3 148 0 0 0		offset 00000094)
;;;def al-spec-form-descr? 210
(000000D2 20 1 1 1 0)
(000000D7 3 234 0		*al-spec-form-descr-ht*)
(000000DA 5 0		UnVar0)
(000000DC 96 2 60 0 0 0		descr-ht-get?)
;;;def al-sys-fun-descr? 226
(000000E2 20 1 1 1 0)
(000000E7 3 232 0		*al-sys-fun-descr-ht*)
(000000EA 5 0		UnVar0)
(000000EC 96 2 60 0 0 0		descr-ht-get?)
;;;def al-not-fit-p 242
(000000F2 20 5 2 3 0)
(000000F7 100 3		UNVar3)
(000000F9 100 4		UNVar4)
(000000FB 5 0		UnVar0)
(000000FD 40		car)
(000000FE 8 4		UnVar4)
(00000100 5 1		UnVar1)
(00000102 5 4		UnVar4)
(00000104 81 2 230 0 1 0		=&)
(0000010A 13 2 0		nil->JMP 0000010F)
(0000010D 1		nil)
(0000010E 22		ret)
(0000010F 5 1		UnVar1)
(00000111 5 4		UnVar4)
(00000113 76		<)
(00000114 13 3 0		nil->JMP 0000011A)
(00000117 50 0		0)
(00000119 22		ret)
(0000011A 5 0		UnVar0)
(0000011C 41		cdr)
(0000011D 40		car)
(0000011E 11)
(0000011F 8 3		UnVar3)
(00000121 61 25 0		nil->JMP 0000013D)
(00000124 2		T)
(00000125 5 3		UnVar3)
(00000127 38		=)
(00000128 13 13 0		nil->JMP 00000138)
(0000012B 5 1		UnVar1)
(0000012D 5 2		UnVar2)
(0000012F 95 2 179 26 0 0		func 00001AB3)
(00000135 15 5 0		JMP 0000013D)
(00000138 5 1		UnVar1)
(0000013A 5 3		UnVar3)
(0000013C 78		<=)
(0000013D 13 2 0		nil->JMP 00000142)
(00000140 1		nil)
(00000141 22		ret)
(00000142 50 1		1)
(00000144 22		ret)
;;;def nil 325
(00000145 20 7 4 4 0)
(0000014A 100 4		UNVar4)
(0000014C 100 5		UNVar5)
(0000014E 100 6		UNVar6)
(00000150 5 3		UnVar3)
(00000152 53 1 229 0 1 32		show-item-cntx-id)
(00000158 53 1 228 0 1 32		rep-cntx-by-id)
(0000015E 8 5		UnVar5)
(00000160 3 227 0		*analyse-output*)
(00000163 14 17 0		T->JMP 00000177)
(00000166 5 5		UnVar5)
(00000168 9 226 0		'ostm)
(0000016B 81 2 225 0 1 0		slot-value)
(00000171 14 3 0		T->JMP 00000177)
(00000174 3 224 0		*error-output*)
(00000177 8 4		UnVar4)
(00000179 5 3		UnVar3)
(0000017B 53 1 223 0 1 32		show-item-instantiate)
(00000181 8 6		UnVar6)
(00000183 5 4		UnVar4)
(00000185 81 1 222 0 1 0		fresh-line)
(0000018B 10)
(0000018C 9 221 0		'*print-length*)
(0000018F 50 4		4)
(00000191 9 220 0		'*print-level*)
(00000194 50 2		2)
(00000196 9 219 0		'*msg-default-title*)
(00000199 9 218 0		"VLMSG.DLL")
(0000019C 51 236 69 0 0		17900)
(000001A1 81 2 217 0 1 0		string-resource)
(000001A7 9 216 0		'*msg-default-prompt*)
(000001AA 9 218 0		"VLMSG.DLL")
(000001AD 51 246 69 0 0		17910)
(000001B2 81 2 217 0 1 0		string-resource)
(000001B8 24 8 0)
(000001BB 5 4		UnVar4)
(000001BD 5 6		UnVar6)
(000001BF 9 218 0		"VLMSG.DLL")
(000001C2 51 0 70 0 0		17920)
(000001C7 81 2 217 0 1 0		string-resource)
(000001CD 5 2		UnVar2)
(000001CF 40		car)
(000001D0 5 2		UnVar2)
(000001D2 41		cdr)
(000001D3 13 6 0		nil->JMP 000001DC)
(000001D6 9 215 0		" ~s")
(000001D9 15 3 0		JMP 000001DF)
(000001DC 9 214 0		"~*")
(000001DF 5 2		UnVar2)
(000001E1 41		cdr)
(000001E2 53 6 213 0 1 32		prinf-msg)
(000001E8 10)
(000001E9 25 4 0)
(000001EC 5 4		UnVar4)
(000001EE 81 1 212 0 1 0		terpri)
(000001F4 22		ret)
;;;def nil 501
(000001F5 20 7 4 4 0)
(000001FA 100 4		UNVar4)
(000001FC 100 5		UNVar5)
(000001FE 100 6		UNVar6)
(00000200 5 3		UnVar3)
(00000202 53 1 229 0 1 32		show-item-cntx-id)
(00000208 53 1 228 0 1 32		rep-cntx-by-id)
(0000020E 8 6		UnVar6)
(00000210 3 227 0		*analyse-output*)
(00000213 14 17 0		T->JMP 00000227)
(00000216 5 6		UnVar6)
(00000218 9 226 0		'ostm)
(0000021B 81 2 225 0 1 0		slot-value)
(00000221 14 3 0		T->JMP 00000227)
(00000224 3 224 0		*error-output*)
(00000227 8 4		UnVar4)
(00000229 5 3		UnVar3)
(0000022B 53 1 223 0 1 32		show-item-instantiate)
(00000231 8 5		UnVar5)
(00000233 5 4		UnVar4)
(00000235 81 1 222 0 1 0		fresh-line)
(0000023B 10)
(0000023C 9 221 0		'*print-length*)
(0000023F 50 4		4)
(00000241 9 220 0		'*print-level*)
(00000244 50 2		2)
(00000246 9 219 0		'*msg-default-title*)
(00000249 9 218 0		"VLMSG.DLL")
(0000024C 51 10 70 0 0		17930)
(00000251 81 2 217 0 1 0		string-resource)
(00000257 9 216 0		'*msg-default-prompt*)
(0000025A 9 218 0		"VLMSG.DLL")
(0000025D 51 246 69 0 0		17910)
(00000262 81 2 217 0 1 0		string-resource)
(00000268 24 8 0)
(0000026B 5 4		UnVar4)
(0000026D 5 5		UnVar5)
(0000026F 9 218 0		"VLMSG.DLL")
(00000272 51 20 70 0 0		17940)
(00000277 81 2 217 0 1 0		string-resource)
(0000027D 5 2		UnVar2)
(0000027F 40		car)
(00000280 5 2		UnVar2)
(00000282 41		cdr)
(00000283 13 6 0		nil->JMP 0000028C)
(00000286 9 215 0		" ~s")
(00000289 15 3 0		JMP 0000028F)
(0000028C 9 214 0		"~*")
(0000028F 5 2		UnVar2)
(00000291 41		cdr)
(00000292 53 6 213 0 1 32		prinf-msg)
(00000298 10)
(00000299 25 4 0)
(0000029C 3 211 0		*vill-warn-cnt*)
(0000029F 81 1 210 0 1 0		fixnump)
(000002A5 13 7 0		nil->JMP 000002AF)
(000002A8 3 211 0		*vill-warn-cnt*)
(000002AB 79		1+)
(000002AC 6 211 0		*vill-warn-cnt*)
(000002AF 5 4		UnVar4)
(000002B1 81 1 212 0 1 0		terpri)
(000002B7 22		ret)
;;;def nil 696
(000002B8 20 8 2 2 0)
(000002BD 100 2		UNVar2)
(000002BF 100 3		UNVar3)
(000002C1 100 4		UNVar4)
(000002C3 100 5		UNVar5)
(000002C5 100 6		UNVar6)
(000002C7 100 7		UNVar7)
(000002C9 50 0		0)
(000002CB 50 0		0)
(000002CD 42		cons)
(000002CE 8 7		UnVar7)
(000002D0 3 209 0		_%rdr-cons-pos-stack%)
(000002D3 13 17 0		nil->JMP 000002E7)
(000002D6 3 208 0		*comp-S-expr*)
(000002D9 3 207 0		_%src-sk%)
(000002DC 3 209 0		_%rdr-cons-pos-stack%)
(000002DF 53 3 206 0 1 32		localise-expr-in-rdr-stacks)
(000002E5 8 7		UnVar7)
(000002E7 9 205 0		':SYNTAX-ERROR)
(000002EA 95 1 32 5 0 0		AL-symbol)
(000002F0 3 208 0		*comp-S-expr*)
(000002F3 5 0		UnVar0)
(000002F5 5 1		UnVar1)
(000002F7 57 2 0		list)
(000002FA 3 204 0		*usubr-source-reference*)
(000002FD 5 7		UnVar7)
(000002FF 40		car)
(00000300 14 2 0		T->JMP 00000305)
(00000303 50 0		0)
(00000305 5 7		UnVar7)
(00000307 41		cdr)
(00000308 14 2 0		T->JMP 0000030D)
(0000030B 50 0		0)
(0000030D 53 3 203 0 1 32		create-show-item)
(00000313 95 4 102 6 0 0		func 00000666)
(00000319 10)
(0000031A 3 202 0		*check-throw*)
(0000031D 1		nil)
(0000031E 81 2 201 0 1 0		throw)
(00000324 22		ret)
;;;def make-fly-err-hook-fn 805
(00000325 21 2 2 2 0)
(0000032A 15 74 0		JMP 00000377)
(0000032D 20 3 1 1 0)
(00000332 100 1		UNVar1)
(00000334 100 2		UNVar2)
(00000336 3 204 0		*usubr-source-reference*)
(00000339 8 2		UnVar2)
(0000033B 9 200 0		'((:SYNTAX-ERROR)))
(0000033E 5 0		UnVar0)
(00000340 4 1 1		UpVar1-1)
(00000343 1		nil)
(00000344 53 4 199 0 1 32		make-tsf-info)
(0000034A 8 1		UnVar1)
(0000034C 9 198 0		':ERROR-BREAK)
(0000034F 5 1		UnVar1)
(00000351 50 0		0)
(00000353 53 3 197 0 1 32		tsf-info<-)
(00000359 10)
(0000035A 3 196 0		*error-trace-stack*)
(0000035D 37 5		stackp)
(0000035F 13 10 0		nil->JMP 0000036C)
(00000362 3 196 0		*error-trace-stack*)
(00000365 81 1 195 0 1 0		_trace-stack)
(0000036B 10)
(0000036C 4 1 0		UpVar1-0)
(0000036F 63		nil->ret)
(00000370 5 0		UnVar0)
(00000372 4 1 0		UpVar1-0)
(00000375 46 1		invoke+ret)
(00000377 12 8 1		'(813 nil))
(0000037A 22		ret)
;;;def nil 891
(0000037B 20 6 2 2 0)
(00000380 100 2		UNVar2)
(00000382 100 3		UNVar3)
(00000384 100 4		UNVar4)
(00000386 100 5		UNVar5)
(00000388 50 0		0)
(0000038A 50 0		0)
(0000038C 42		cons)
(0000038D 8 5		UnVar5)
(0000038F 3 209 0		_%rdr-cons-pos-stack%)
(00000392 13 17 0		nil->JMP 000003A6)
(00000395 3 208 0		*comp-S-expr*)
(00000398 3 207 0		_%src-sk%)
(0000039B 3 209 0		_%rdr-cons-pos-stack%)
(0000039E 53 3 206 0 1 32		localise-expr-in-rdr-stacks)
(000003A4 8 5		UnVar5)
(000003A6 3 194 0		_%sys-error-hook%)
(000003A9 8 4		UnVar4)
(000003AB 9 240 0		':AUTOLISP)
(000003AE 53 1 228 0 1 32		rep-cntx-by-id)
(000003B4 8 3		UnVar3)
(000003B6 3 204 0		*usubr-source-reference*)
(000003B9 5 5		UnVar5)
(000003BB 41		cdr)
(000003BC 14 2 0		T->JMP 000003C1)
(000003BF 50 0		0)
(000003C1 5 5		UnVar5)
(000003C3 40		car)
(000003C4 14 2 0		T->JMP 000003C9)
(000003C7 50 0		0)
(000003C9 53 3 193 0 1 32		instantiate-show-item)
(000003CF 8 2		UnVar2)
(000003D1 9 194 0		'_%sys-error-hook%)
(000003D4 5 4		UnVar4)
(000003D6 5 2		UnVar2)
(000003D8 53 2 192 0 1 32		make-fly-err-hook-fn)
(000003DE 24 2 0)
(000003E1 5 0		UnVar0)
(000003E3 5 1		UnVar1)
(000003E5 81 2 191 0 1 0		_msg-err)
(000003EB 25 1 0)
(000003EE 22		ret)
;;;def nil 1007
(000003EF 20 1 1 1 0)
(000003F4 5 0		UnVar0)
(000003F6 9 190 0		'(:rt-eval :pragma :bad-fun :built-sym :arg-lst :arg-num :spec-form :READ))
(000003F9 81 2 236 0 1 0		memq)
(000003FF 9 189 0		"unrecognized warning keyword:")
(00000402 5 0		UnVar0)
(00000404 53 3 188 0 1 32		assert)
(0000040A 10)
(0000040B 3 187 0		_%msglevel%)
(0000040E 81 1 210 0 1 0		fixnump)
(00000414 63		nil->ret)
(00000415 3 187 0		_%msglevel%)
(00000418 50 0		0)
(0000041A 75		>)
(0000041B 63		nil->ret)
(0000041C 5 0		UnVar0)
(0000041E 9 186 0		'(:built-sym :arg-lst :arg-num :spec-form))
(00000421 81 2 236 0 1 0		memq)
(00000427 62		T->ret)
(00000428 3 185 0		*check-warning*)
(0000042B 61 11 0		nil->JMP 00000439)
(0000042E 5 0		UnVar0)
(00000430 9 184 0		'(:bad-fun))
(00000433 81 2 236 0 1 0		memq)
(00000439 62		T->ret)
(0000043A 3 185 0		*check-warning*)
(0000043D 13 2 0		nil->JMP 00000442)
(00000440 1		nil)
(00000441 22		ret)
(00000442 5 0		UnVar0)
(00000444 9 183 0		'(:READ :rt-eval :pragma :bad-fun))
(00000447 81 2 236 0 1 0		memq)
(0000044D 22		ret)
;;;def nil 1102
(0000044E 20 4 3 3 0)
(00000453 100 3		UNVar3)
(00000455 5 2		UnVar2)
(00000457 95 1 239 3 0 0		func 000003EF)
(0000045D 63		nil->ret)
(0000045E 50 0		0)
(00000460 50 0		0)
(00000462 42		cons)
(00000463 8 3		UnVar3)
(00000465 3 209 0		_%rdr-cons-pos-stack%)
(00000468 13 17 0		nil->JMP 0000047C)
(0000046B 3 208 0		*comp-S-expr*)
(0000046E 3 207 0		_%src-sk%)
(00000471 3 209 0		_%rdr-cons-pos-stack%)
(00000474 53 3 206 0 1 32		localise-expr-in-rdr-stacks)
(0000047A 8 3		UnVar3)
(0000047C 5 2		UnVar2)
(0000047E 95 1 32 5 0 0		AL-symbol)
(00000484 3 208 0		*comp-S-expr*)
(00000487 5 0		UnVar0)
(00000489 5 1		UnVar1)
(0000048B 57 2 0		list)
(0000048E 3 204 0		*usubr-source-reference*)
(00000491 5 3		UnVar3)
(00000493 40		car)
(00000494 14 2 0		T->JMP 00000499)
(00000497 50 0		0)
(00000499 5 3		UnVar3)
(0000049B 41		cdr)
(0000049C 14 2 0		T->JMP 000004A1)
(0000049F 50 0		0)
(000004A1 53 3 203 0 1 32		create-show-item)
(000004A7 96 4 245 1 0 0		func 000001F5)
;;;def nil 1197
(000004AD 20 3 3 3 0)
(000004B2 5 0		UnVar0)
(000004B4 13 2 0		nil->JMP 000004B9)
(000004B7 2		T)
(000004B8 22		ret)
(000004B9 5 1		UnVar1)
(000004BB 5 2		UnVar2)
(000004BD 97 2 200 4 0 0		offset 000004C8)
;;;def nil 1219
(000004C3 20 2 2 2 0)
(000004C8 3 182 0		*syntax-error-break*)
(000004CB 13 10 0		nil->JMP 000004D8)
(000004CE 5 0		UnVar0)
(000004D0 5 1		UnVar1)
(000004D2 96 2 123 3 0 0		func 0000037B)
(000004D8 5 0		UnVar0)
(000004DA 5 1		UnVar1)
(000004DC 96 2 184 2 0 0		func 000002B8)
;;;def nil 1250
(000004E2 20 3 3 3 0)
(000004E7 3 182 0		*syntax-error-break*)
(000004EA 13 2 0		nil->JMP 000004EF)
(000004ED 1		nil)
(000004EE 22		ret)
(000004EF 5 0		UnVar0)
(000004F1 5 1		UnVar1)
(000004F3 5 2		UnVar2)
(000004F5 96 3 78 4 0 0		func 0000044E)
;;;def nil 1275
(000004FB 20 1 1 1 0)
(00000500 5 0		UnVar0)
(00000502 22		ret)
;;;def nil 1283
(00000503 20 1 1 1 0)
(00000508 5 0		UnVar0)
(0000050A 3 181 0		*bind-list*)
(0000050D 42		cons)
(0000050E 22		ret)
;;;def nil 1295
(0000050F 20 1 1 1 0)
(00000514 5 0		UnVar0)
(00000516 3 181 0		*bind-list*)
(00000519 81 2 180 0 1 0		posq)
(0000051F 22		ret)
;;;def AL-symbol 1312
(00000520 20 2 1 2 0)
(00000525 5 0		UnVar0)
(00000527 81 1 245 0 1 0		string)
(0000052D 8 0		UnVar0)
(0000052F 5 1		UnVar1)
(00000531 13 12 0		nil->JMP 00000540)
(00000534 5 0		UnVar0)
(00000536 9 240 0		':AUTOLISP)
(00000539 81 2 242 0 1 0		find-symbol)
(0000053F 22		ret)
(00000540 5 0		UnVar0)
(00000542 9 240 0		':AUTOLISP)
(00000545 81 2 244 0 1 0		intern)
(0000054B 22		ret)
;;;def nil 1356
(0000054C 20 0 0 0 0)
(00000551 50 0		0)
(00000553 22		ret)
;;;def nil 1364
(00000554 20 0 0 0 0)
(00000559 1		nil)
(0000055A 22		ret)
;;;def nil 1371
(0000055B 20 0 0 0 0)
(00000560 1		nil)
(00000561 22		ret)
;;;def nil 1378
(00000562 20 0 0 0 0)
(00000567 1		nil)
(00000568 22		ret)
;;;def nil 1385
(00000569 20 0 0 0 0)
(0000056E 1		nil)
(0000056F 22		ret)
;;;def nil 1392
(00000570 20 0 0 0 0)
(00000575 1		nil)
(00000576 22		ret)
;;;def nil 1399
(00000577 20 0 0 0 0)
(0000057C 1		nil)
(0000057D 22		ret)
;;;def nil 1406
(0000057E 20 0 0 0 0)
(00000583 1		nil)
(00000584 22		ret)
;;;def nil 1413
(00000585 20 0 0 0 0)
(0000058A 1		nil)
(0000058B 22		ret)
;;;def nil 1420
(0000058C 20 0 0 0 0)
(00000591 1		nil)
(00000592 22		ret)
;;;def nil 1427
(00000593 20 0 0 0 0)
(00000598 1		nil)
(00000599 22		ret)
;;;def nil 1434
(0000059A 20 0 0 0 0)
(0000059F 1		nil)
(000005A0 22		ret)
;;;def nil 1441
(000005A1 20 0 0 0 0)
(000005A6 1		nil)
(000005A7 22		ret)
;;;def nil 1448
(000005A8 20 0 0 0 0)
(000005AD 1		nil)
(000005AE 22		ret)
;;;def nil 1455
(000005AF 20 0 0 0 0)
(000005B4 1		nil)
(000005B5 22		ret)
;;;def nil 1462
(000005B6 20 1 1 1 0)
(000005BB 5 0		UnVar0)
(000005BD 3 179 0		*stream-link*)
(000005C0 81 2 178 0 1 0		adjoin)
(000005C6 11)
(000005C7 6 179 0		*stream-link*)
(000005CA 22		ret)
;;;def nil 1483
(000005CB 20 2 1 1 0)
(000005D0 100 1		UNVar1)
(000005D2 5 0		UnVar0)
(000005D4 3 179 0		*stream-link*)
(000005D7 81 2 177 0 1 0		delq)
(000005DD 11)
(000005DE 6 179 0		*stream-link*)
(000005E1 22		ret)
;;;def nil 1506
(000005E2 20 1 1 1 0)
(000005E7 5 0		UnVar0)
(000005E9 3 176 0		*stream-not-link*)
(000005EC 81 2 178 0 1 0		adjoin)
(000005F2 11)
(000005F3 6 176 0		*stream-not-link*)
(000005F6 22		ret)
;;;def nil 1527
(000005F7 20 2 1 1 0)
(000005FC 100 1		UNVar1)
(000005FE 5 0		UnVar0)
(00000600 3 176 0		*stream-not-link*)
(00000603 81 2 177 0 1 0		delq)
(00000609 11)
(0000060A 6 176 0		*stream-not-link*)
(0000060D 22		ret)
;;;def nil 1550
(0000060E 20 1 1 1 0)
(00000613 5 0		UnVar0)
(00000615 3 175 0		*stream-local*)
(00000618 81 2 178 0 1 0		adjoin)
(0000061E 11)
(0000061F 6 175 0		*stream-local*)
(00000622 22		ret)
;;;def nil 1571
(00000623 20 2 1 1 0)
(00000628 100 1		UNVar1)
(0000062A 5 0		UnVar0)
(0000062C 3 175 0		*stream-local*)
(0000062F 81 2 177 0 1 0		delq)
(00000635 11)
(00000636 6 175 0		*stream-local*)
(00000639 22		ret)
;;;def nil 1594
(0000063A 20 1 1 1 0)
(0000063F 5 0		UnVar0)
(00000641 3 174 0		*stream-not-local*)
(00000644 81 2 178 0 1 0		adjoin)
(0000064A 11)
(0000064B 6 174 0		*stream-not-local*)
(0000064E 22		ret)
;;;def nil 1615
(0000064F 20 2 1 1 0)
(00000654 100 1		UNVar1)
(00000656 5 0		UnVar0)
(00000658 3 174 0		*stream-not-local*)
(0000065B 81 2 177 0 1 0		delq)
(00000661 11)
(00000662 6 174 0		*stream-not-local*)
(00000665 22		ret)
;;;def nil 1638
(00000666 20 4 4 4 0)
(0000066B 5 0		UnVar0)
(0000066D 5 1		UnVar1)
(0000066F 5 2		UnVar2)
(00000671 5 3		UnVar3)
(00000673 95 4 69 1 0 0		func 00000145)
(00000679 10)
(0000067A 3 173 0		*pdb-error-list*)
(0000067D 79		1+)
(0000067E 11)
(0000067F 6 173 0		*pdb-error-list*)
(00000682 22		ret)
;;;def nil 1667
(00000683 20 2 2 2 0)
(00000688 5 0		UnVar0)
(0000068A 5 1		UnVar1)
(0000068C 42		cons)
(0000068D 3 172 0		*top-fcall-num*)
(00000690 42		cons)
(00000691 11)
(00000692 6 172 0		*top-fcall-num*)
(00000695 22		ret)
;;;def nil 1686
(00000696 20 1 1 1 0)
(0000069B 5 0		UnVar0)
(0000069D 3 171 0		*top-quoted-sym*)
(000006A0 42		cons)
(000006A1 11)
(000006A2 6 171 0		*top-quoted-sym*)
(000006A5 22		ret)
;;;def nil 1702
(000006A6 20 1 1 1 0)
(000006AB 5 0		UnVar0)
(000006AD 3 170 0		*top-non-loc-val-ref*)
(000006B0 42		cons)
(000006B1 11)
(000006B2 6 170 0		*top-non-loc-val-ref*)
(000006B5 22		ret)
;;;def nil 1718
(000006B6 20 1 1 1 0)
(000006BB 5 0		UnVar0)
(000006BD 3 169 0		*top-non-loc-assign*)
(000006C0 42		cons)
(000006C1 11)
(000006C2 6 169 0		*top-non-loc-assign*)
(000006C5 22		ret)
;;;def nil 1734
(000006C6 20 1 1 1 0)
(000006CB 5 0		UnVar0)
(000006CD 3 168 0		*top-call-by-name*)
(000006D0 42		cons)
(000006D1 11)
(000006D2 6 168 0		*top-call-by-name*)
(000006D5 22		ret)
;;;def nil 1750
(000006D6 20 1 1 1 0)
(000006DB 5 0		UnVar0)
(000006DD 3 167 0		*top-val-ref*)
(000006E0 42		cons)
(000006E1 11)
(000006E2 6 167 0		*top-val-ref*)
(000006E5 22		ret)
;;;def nil 1766
(000006E6 20 1 1 1 0)
(000006EB 5 0		UnVar0)
(000006ED 3 166 0		*top-assign*)
(000006F0 42		cons)
(000006F1 11)
(000006F2 6 166 0		*top-assign*)
(000006F5 22		ret)
;;;def nil 1782
(000006F6 20 2 2 2 0)
(000006FB 5 0		UnVar0)
(000006FD 5 1		UnVar1)
(000006FF 42		cons)
(00000700 3 165 0		*top-def-arg-num*)
(00000703 42		cons)
(00000704 11)
(00000705 6 165 0		*top-def-arg-num*)
(00000708 22		ret)
;;;def nil 1801
(00000709 20 1 1 1 0)
(0000070E 5 0		UnVar0)
(00000710 3 164 0		*top-bind-param*)
(00000713 42		cons)
(00000714 11)
(00000715 6 164 0		*top-bind-param*)
(00000718 22		ret)
;;;def nil 1817
(00000719 20 1 1 1 0)
(0000071E 5 0		UnVar0)
(00000720 3 163 0		*top-bind-aux*)
(00000723 42		cons)
(00000724 11)
(00000725 6 163 0		*top-bind-aux*)
(00000728 22		ret)
;;;def nil 1833
(00000729 20 0 0 0 0)
(0000072E 1		nil)
(0000072F 22		ret)
;;;def nil 1840
(00000730 20 1 1 1 0)
(00000735 5 0		UnVar0)
(00000737 9 162 0		'_addr<)
(0000073A 81 2 161 0 1 0		sort)
(00000740 22		ret)
;;;def nil 1857
(00000741 20 2 2 2 0)
(00000746 5 1		UnVar1)
(00000748 63		nil->ret)
(00000749 5 0		UnVar0)
(0000074B 95 1 32 5 0 0		AL-symbol)
(00000751 5 1		UnVar1)
(00000753 42		cons)
(00000754 57 1 0		list)
(00000757 22		ret)
;;;def nil 1880
(00000758 20 2 2 2 0)
(0000075D 9 160 0		':pos)
(00000760 5 0		UnVar0)
(00000762 5 1		UnVar1)
(00000764 42		cons)
(00000765 95 2 65 7 0 0		func 00000741)
(0000076B 9 159 0		':bind-param)
(0000076E 3 164 0		*top-bind-param*)
(00000771 95 1 48 7 0 0		func 00000730)
(00000777 11)
(00000778 6 164 0		*top-bind-param*)
(0000077B 95 2 65 7 0 0		func 00000741)
(00000781 9 158 0		':bind-aux)
(00000784 3 163 0		*top-bind-aux*)
(00000787 95 1 48 7 0 0		func 00000730)
(0000078D 11)
(0000078E 6 163 0		*top-bind-aux*)
(00000791 95 2 65 7 0 0		func 00000741)
(00000797 9 157 0		':def-arg-num)
(0000079A 3 165 0		*top-def-arg-num*)
(0000079D 95 2 65 7 0 0		func 00000741)
(000007A3 9 156 0		':assign)
(000007A6 3 166 0		*top-assign*)
(000007A9 95 1 48 7 0 0		func 00000730)
(000007AF 11)
(000007B0 6 166 0		*top-assign*)
(000007B3 95 2 65 7 0 0		func 00000741)
(000007B9 9 155 0		':val-ref)
(000007BC 3 167 0		*top-val-ref*)
(000007BF 95 1 48 7 0 0		func 00000730)
(000007C5 11)
(000007C6 6 167 0		*top-val-ref*)
(000007C9 95 2 65 7 0 0		func 00000741)
(000007CF 9 154 0		':non-loc-assign)
(000007D2 3 169 0		*top-non-loc-assign*)
(000007D5 95 1 48 7 0 0		func 00000730)
(000007DB 11)
(000007DC 6 169 0		*top-non-loc-assign*)
(000007DF 95 2 65 7 0 0		func 00000741)
(000007E5 9 153 0		':non-loc-val-ref)
(000007E8 3 170 0		*top-non-loc-val-ref*)
(000007EB 95 1 48 7 0 0		func 00000730)
(000007F1 11)
(000007F2 6 170 0		*top-non-loc-val-ref*)
(000007F5 95 2 65 7 0 0		func 00000741)
(000007FB 9 152 0		':quoted)
(000007FE 3 171 0		*top-quoted-sym*)
(00000801 95 1 48 7 0 0		func 00000730)
(00000807 11)
(00000808 6 171 0		*top-quoted-sym*)
(0000080B 95 2 65 7 0 0		func 00000741)
(00000811 9 151 0		':fcall-num)
(00000814 3 172 0		*top-fcall-num*)
(00000817 95 2 65 7 0 0		func 00000741)
(0000081D 9 150 0		':call-by-name)
(00000820 3 168 0		*top-call-by-name*)
(00000823 95 1 48 7 0 0		func 00000730)
(00000829 11)
(0000082A 6 168 0		*top-call-by-name*)
(0000082D 95 2 65 7 0 0		func 00000741)
(00000833 9 149 0		':link)
(00000836 3 179 0		*stream-link*)
(00000839 95 2 65 7 0 0		func 00000741)
(0000083F 9 148 0		':not-link)
(00000842 3 176 0		*stream-not-link*)
(00000845 95 2 65 7 0 0		func 00000741)
(0000084B 9 147 0		':local)
(0000084E 3 175 0		*stream-local*)
(00000851 95 2 65 7 0 0		func 00000741)
(00000857 9 146 0		':not-local)
(0000085A 3 174 0		*stream-not-local*)
(0000085D 95 2 65 7 0 0		func 00000741)
(00000863 81 15 145 0 1 0		nconc)
(00000869 3 144 0		*integral-pdb-info*)
(0000086C 42		cons)
(0000086D 11)
(0000086E 6 144 0		*integral-pdb-info*)
(00000871 22		ret)
;;;def nil 2162
(00000872 20 1 1 1 0)
(00000877 9 143 0		':inp-stream)
(0000087A 95 1 32 5 0 0		AL-symbol)
(00000880 5 0		UnVar0)
(00000882 53 1 142 0 1 32		_istream-source)
(00000888 42		cons)
(00000889 9 141 0		':ERROR)
(0000088C 95 1 32 5 0 0		AL-symbol)
(00000892 3 173 0		*pdb-error-list*)
(00000895 42		cons)
(00000896 9 140 0		':stream-info)
(00000899 95 1 32 5 0 0		AL-symbol)
(0000089F 3 144 0		*integral-pdb-info*)
(000008A2 81 1 139 0 1 0		nreverse)
(000008A8 42		cons)
(000008A9 57 3 0		list)
(000008AC 22		ret)
;;;def read-top-with-pos 2221
(000008AD 21 6 3 3 0)
(000008B2 100 3		UNVar3)
(000008B4 100 4		UNVar4)
(000008B6 100 5		UNVar5)
(000008B8 3 196 0		*error-trace-stack*)
(000008BB 8 3		UnVar3)
(000008BD 9 138 0		':check-read)
(000008C0 81 1 137 0 1 0		box)
(000008C6 11)
(000008C7 8 4		UnVar4)
(000008C9 57 1 0		list)
(000008CC 15 173 0		JMP 0000097C)
(000008CF 20 0 0 0 0)
(000008D4 9 196 0		'*error-trace-stack*)
(000008D7 1		nil)
(000008D8 9 136 0		'%rdr-cons-stack%)
(000008DB 3 207 0		_%src-sk%)
(000008DE 81 1 135 0 1 0		stack-empty)
(000008E4 9 134 0		'%rdr-cons-pos-stack%)
(000008E7 3 209 0		_%rdr-cons-pos-stack%)
(000008EA 81 1 135 0 1 0		stack-empty)
(000008F0 9 133 0		'%al-rdr-sym8-stack%)
(000008F3 3 132 0		_%al-rdr-sym8-stack%)
(000008F6 37 5		stackp)
(000008F8 61 9 0		nil->JMP 00000904)
(000008FB 3 132 0		_%al-rdr-sym8-stack%)
(000008FE 81 1 135 0 1 0		stack-empty)
(00000904 9 194 0		'_%sys-error-hook%)
(00000907 15 85 0		JMP 0000095F)
(0000090A 20 1 1 1 0)
(0000090F 9 131 0		':READ-ERROR)
(00000912 95 1 32 5 0 0		AL-symbol)
(00000918 1		nil)
(00000919 5 0		UnVar0)
(0000091B 57 1 0		list)
(0000091E 4 2 0		UpVar2-0)
(00000921 53 1 142 0 1 32		_istream-source)
(00000927 9 240 0		':AUTOLISP)
(0000092A 53 2 130 0 1 32		register-istream)
(00000930 81 0 129 0 1 0		_as:reader-sexp-start)
(00000936 4 2 0		UpVar2-0)
(00000939 81 1 128 0 1 0		_istream-position)
(0000093F 53 3 203 0 1 32		create-show-item)
(00000945 95 4 102 6 0 0		func 00000666)
(0000094B 10)
(0000094C 4 2 3		UpVar2-3)
(0000094F 6 196 0		*error-trace-stack*)
(00000952 4 2 4		UpVar2-4)
(00000955 4 2 2		UpVar2-2)
(00000958 81 2 201 0 1 0		throw)
(0000095E 22		ret)
(0000095F 12 7 1		'(2314 nil))
(00000962 24 10 0)
(00000965 4 1 0		UpVar1-0)
(00000968 4 1 1		UpVar1-1)
(0000096B 4 1 2		UpVar1-2)
(0000096E 81 3 127 0 1 0		as:read)
(00000974 11)
(00000975 7 1 1		UpVar1-1)
(00000978 25 5 0)
(0000097B 22		ret)
(0000097C 12 6 1		'(2255 -catch-))
(0000097F 1		nil)
(00000980 81 3 126 0 1 0		_catched-apply)
(00000986 22		ret)
;;;def collect-top 2439
(00000987 21 5 3 3 0)
(0000098C 100 3		UNVar3)
(0000098E 100 4		UNVar4)
(00000990 1		nil)
(00000991 81 1 137 0 1 0		box)
(00000997 11)
(00000998 8 3		UnVar3)
(0000099A 57 1 0		list)
(0000099D 15 164 0		JMP 00000A44)
(000009A0 20 0 0 0 0)
(000009A5 9 202 0		'*check-throw*)
(000009A8 4 1 3		UpVar1-3)
(000009AB 9 164 0		'*top-bind-param*)
(000009AE 95 0 112 5 0 0		func 00000570)
(000009B4 9 163 0		'*top-bind-aux*)
(000009B7 95 0 119 5 0 0		func 00000577)
(000009BD 9 165 0		'*top-def-arg-num*)
(000009C0 95 0 126 5 0 0		func 0000057E)
(000009C6 9 166 0		'*top-assign*)
(000009C9 95 0 133 5 0 0		func 00000585)
(000009CF 9 167 0		'*top-val-ref*)
(000009D2 95 0 140 5 0 0		func 0000058C)
(000009D8 9 169 0		'*top-non-loc-assign*)
(000009DB 95 0 147 5 0 0		func 00000593)
(000009E1 9 170 0		'*top-non-loc-val-ref*)
(000009E4 95 0 154 5 0 0		func 0000059A)
(000009EA 9 171 0		'*top-quoted-sym*)
(000009ED 95 0 161 5 0 0		func 000005A1)
(000009F3 9 172 0		'*top-fcall-num*)
(000009F6 95 0 168 5 0 0		func 000005A8)
(000009FC 9 168 0		'*top-call-by-name*)
(000009FF 95 0 175 5 0 0		func 000005AF)
(00000A05 9 181 0		'*bind-list*)
(00000A08 1		nil)
(00000A09 95 1 251 4 0 0		func 000004FB)
(00000A0F 9 125 0		'*in-proc-body*)
(00000A12 1		nil)
(00000A13 24 26 0)
(00000A16 4 1 0		UpVar1-0)
(00000A19 2		T)
(00000A1A 95 2 5 12 0 0		func 00000C05)
(00000A20 10)
(00000A21 4 1 1		UpVar1-1)
(00000A24 4 1 2		UpVar1-2)
(00000A27 95 2 88 7 0 0		func 00000758)
(00000A2D 10)
(00000A2E 4 1 1		UpVar1-1)
(00000A31 4 1 2		UpVar1-2)
(00000A34 95 2 138 37 0 0		func 0000258A)
(00000A3A 10)
(00000A3B 2		T)
(00000A3C 11)
(00000A3D 7 1 4		UpVar1-4)
(00000A40 25 13 0)
(00000A43 22		ret)
(00000A44 12 5 1		'(2464 -catch-))
(00000A47 1		nil)
(00000A48 81 3 126 0 1 0		_catched-apply)
(00000A4E 10)
(00000A4F 5 4		UnVar4)
(00000A51 22		ret)
;;;def nil 2642
(00000A52 20 2 2 2 0)
(00000A57 9 181 0		'*bind-list*)
(00000A5A 5 1		UnVar1)
(00000A5C 95 1 251 4 0 0		func 000004FB)
(00000A62 9 125 0		'*in-proc-body*)
(00000A65 2		T)
(00000A66 24 4 0)
(00000A69 5 0		UnVar0)
(00000A6B 95 1 145 26 0 0		func 00001A91)
(00000A71 25 2 0)
(00000A74 22		ret)
;;;def nil 2677
(00000A75 20 6 1 2 0)
(00000A7A 100 2		UNVar2)
(00000A7C 100 3		UNVar3)
(00000A7E 100 4		UNVar4)
(00000A80 5 0		UnVar0)
(00000A82 81 1 124 0 1 0		list-length)
(00000A88 11)
(00000A89 8 2		UnVar2)
(00000A8B 60 23 0		T->JMP 00000AA5)
(00000A8E 9 218 0		"VLMSG.DLL")
(00000A91 51 42 68 0 0		17450)
(00000A96 81 2 217 0 1 0		string-resource)
(00000A9C 5 0		UnVar0)
(00000A9E 95 2 195 4 0 0		func 000004C3)
(00000AA4 10)
(00000AA5 5 0		UnVar0)
(00000AA7 40		car)
(00000AA8 8 4		UnVar4)
(00000AAA 5 0		UnVar0)
(00000AAC 41		cdr)
(00000AAD 8 3		UnVar3)
(00000AAF 5 2		UnVar2)
(00000AB1 80		1-)
(00000AB2 8 2		UnVar2)
(00000AB4 5 4		UnVar4)
(00000AB6 81 1 123 0 1 0		lpp-sym?)
(00000ABC 8 5		UnVar5)
(00000ABE 5 5		UnVar5)
(00000AC0 9 122 0		'setq)
(00000AC3 38		=)
(00000AC4 13 8 0		nil->JMP 00000ACF)
(00000AC7 5 3		UnVar3)
(00000AC9 97 1 8 23 0 0		offset 00001708)
(00000ACF 5 5		UnVar5)
(00000AD1 9 121 0		'cond)
(00000AD4 38		=)
(00000AD5 13 8 0		nil->JMP 00000AE0)
(00000AD8 5 3		UnVar3)
(00000ADA 97 1 149 22 0 0		offset 00001695)
(00000AE0 5 5		UnVar5)
(00000AE2 9 120 0		'defun)
(00000AE5 38		=)
(00000AE6 13 8 0		nil->JMP 00000AF1)
(00000AE9 5 3		UnVar3)
(00000AEB 97 1 218 23 0 0		offset 000017DA)
(00000AF1 5 5		UnVar5)
(00000AF3 9 119 0		'DEFUN-Q)
(00000AF6 38		=)
(00000AF7 13 8 0		nil->JMP 00000B02)
(00000AFA 5 3		UnVar3)
(00000AFC 97 1 153 24 0 0		offset 00001899)
(00000B02 5 5		UnVar5)
(00000B04 9 118 0		'lambda)
(00000B07 38		=)
(00000B08 13 8 0		nil->JMP 00000B13)
(00000B0B 5 3		UnVar3)
(00000B0D 97 1 62 22 0 0		offset 0000163E)
(00000B13 5 5		UnVar5)
(00000B15 9 117 0		'function)
(00000B18 38		=)
(00000B19 13 8 0		nil->JMP 00000B24)
(00000B1C 5 3		UnVar3)
(00000B1E 97 1 31 13 0 0		offset 00000D1F)
(00000B24 5 5		UnVar5)
(00000B26 9 116 0		'quote)
(00000B29 38		=)
(00000B2A 13 8 0		nil->JMP 00000B35)
(00000B2D 5 3		UnVar3)
(00000B2F 97 1 220 12 0 0		offset 00000CDC)
(00000B35 5 5		UnVar5)
(00000B37 9 115 0		'foreach)
(00000B3A 38		=)
(00000B3B 13 8 0		nil->JMP 00000B46)
(00000B3E 5 3		UnVar3)
(00000B40 97 1 6 21 0 0		offset 00001506)
(00000B46 5 5		UnVar5)
(00000B48 9 114 0		'VLAX-FOR)
(00000B4B 38		=)
(00000B4C 13 8 0		nil->JMP 00000B57)
(00000B4F 5 3		UnVar3)
(00000B51 97 1 162 21 0 0		offset 000015A2)
(00000B57 5 5		UnVar5)
(00000B59 9 113 0		'PRAGMA)
(00000B5C 38		=)
(00000B5D 13 10 0		nil->JMP 00000B6A)
(00000B60 5 3		UnVar3)
(00000B62 5 1		UnVar1)
(00000B64 96 2 206 17 0 0		func 000011CE)
(00000B6A 5 5		UnVar5)
(00000B6C 9 112 0		'eval)
(00000B6F 38		=)
(00000B70 13 12 0		nil->JMP 00000B7F)
(00000B73 5 4		UnVar4)
(00000B75 5 3		UnVar3)
(00000B77 5 2		UnVar2)
(00000B79 97 3 215 14 0 0		offset 00000ED7)
(00000B7F 5 5		UnVar5)
(00000B81 9 111 0		'mapcar)
(00000B84 38		=)
(00000B85 13 12 0		nil->JMP 00000B94)
(00000B88 5 4		UnVar4)
(00000B8A 5 3		UnVar3)
(00000B8C 5 2		UnVar2)
(00000B8E 97 3 164 13 0 0		offset 00000DA4)
(00000B94 5 5		UnVar5)
(00000B96 9 110 0		'apply)
(00000B99 38		=)
(00000B9A 13 12 0		nil->JMP 00000BA9)
(00000B9D 5 4		UnVar4)
(00000B9F 5 3		UnVar3)
(00000BA1 5 2		UnVar2)
(00000BA3 97 3 196 13 0 0		offset 00000DC4)
(00000BA9 5 5		UnVar5)
(00000BAB 9 109 0		'ACTION_TILE)
(00000BAE 38		=)
(00000BAF 13 12 0		nil->JMP 00000BBE)
(00000BB2 5 4		UnVar4)
(00000BB4 5 3		UnVar3)
(00000BB6 5 2		UnVar2)
(00000BB8 97 3 192 15 0 0		offset 00000FC0)
(00000BBE 5 5		UnVar5)
(00000BC0 9 108 0		'NEW_DIALOG)
(00000BC3 38		=)
(00000BC4 13 12 0		nil->JMP 00000BD3)
(00000BC7 5 4		UnVar4)
(00000BC9 5 3		UnVar3)
(00000BCB 5 2		UnVar2)
(00000BCD 97 3 87 15 0 0		offset 00000F57)
(00000BD3 5 5		UnVar5)
(00000BD5 9 107 0		'trace)
(00000BD8 38		=)
(00000BD9 13 10 0		nil->JMP 00000BE6)
(00000BDC 5 4		UnVar4)
(00000BDE 5 3		UnVar3)
(00000BE0 97 2 154 12 0 0		offset 00000C9A)
(00000BE6 5 5		UnVar5)
(00000BE8 9 106 0		'untrace)
(00000BEB 38		=)
(00000BEC 13 10 0		nil->JMP 00000BF9)
(00000BEF 5 4		UnVar4)
(00000BF1 5 3		UnVar3)
(00000BF3 97 2 154 12 0 0		offset 00000C9A)
(00000BF9 5 4		UnVar4)
(00000BFB 5 3		UnVar3)
(00000BFD 5 2		UnVar2)
(00000BFF 97 3 221 26 0 0		offset 00001ADD)
;;;def nil 3077
(00000C05 20 2 1 2 0)
(00000C0A 5 0		UnVar0)
(00000C0C 37 3		symbolp)
(00000C0E 13 12 0		nil->JMP 00000C1D)
(00000C11 5 0		UnVar0)
(00000C13 95 1 90 12 0 0		func 00000C5A)
(00000C19 10)
(00000C1A 15 59 0		JMP 00000C58)
(00000C1D 5 0		UnVar0)
(00000C1F 37 2		consp)
(00000C21 13 43 0		nil->JMP 00000C4F)
(00000C24 3 105 0		*read-eval-from-string*)
(00000C27 13 12 0		nil->JMP 00000C36)
(00000C2A 5 0		UnVar0)
(00000C2C 95 1 117 10 0 0		func 00000A75)
(00000C32 10)
(00000C33 15 22 0		JMP 00000C4C)
(00000C36 9 208 0		'*comp-S-expr*)
(00000C39 5 0		UnVar0)
(00000C3B 24 2 0)
(00000C3E 5 0		UnVar0)
(00000C40 5 1		UnVar1)
(00000C42 95 2 117 10 0 0		func 00000A75)
(00000C48 10)
(00000C49 25 1 0)
(00000C4C 15 9 0		JMP 00000C58)
(00000C4F 5 0		UnVar0)
(00000C51 95 1 206 23 0 0		func 000017CE)
(00000C57 10)
(00000C58 2		T)
(00000C59 22		ret)
;;;def nil 3162
(00000C5A 20 1 1 1 0)
(00000C5F 5 0		UnVar0)
(00000C61 95 1 214 6 0 0		func 000006D6)
(00000C67 10)
(00000C68 5 0		UnVar0)
(00000C6A 95 1 15 5 0 0		func 0000050F)
(00000C70 13 6 0		nil->JMP 00000C79)
(00000C73 3 104 0		*run-time-evaluation*)
(00000C76 15 1 0		JMP 00000C7A)
(00000C79 2		T)
(00000C7A 61 15 0		nil->JMP 00000C8C)
(00000C7D 5 0		UnVar0)
(00000C7F 81 1 123 0 1 0		lpp-sym?)
(00000C85 95 1 126 0 0 0		al-sys-protected-p)
(00000C8B 35		not)
(00000C8C 63		nil->ret)
(00000C8D 5 0		UnVar0)
(00000C8F 97 1 171 6 0 0		offset 000006AB)
;;;def nil 3221
(00000C95 20 4 2 2 0)
(00000C9A 100 2		UNVar2)
(00000C9C 15 49 0		JMP 00000CD0)
(00000C9F 5 1		UnVar1)
(00000CA1 40		car)
(00000CA2 8 3		UnVar3)
(00000CA4 5 1		UnVar1)
(00000CA6 41		cdr)
(00000CA7 8 1		UnVar1)
(00000CA9 5 3		UnVar3)
(00000CAB 11)
(00000CAC 8 2		UnVar2)
(00000CAE 37 3		symbolp)
(00000CB0 9 218 0		"VLMSG.DLL")
(00000CB3 51 62 68 0 0		17470)
(00000CB8 81 2 217 0 1 0		string-resource)
(00000CBE 5 0		UnVar0)
(00000CC0 95 3 173 4 0 0		func 000004AD)
(00000CC6 10)
(00000CC7 5 2		UnVar2)
(00000CC9 95 1 90 12 0 0		func 00000C5A)
(00000CCF 10)
(00000CD0 5 1		UnVar1)
(00000CD2 60 202 255		T->JMP 00000C9F)
(00000CD5 2		T)
(00000CD6 22		ret)
;;;def nil 3287
(00000CD7 20 2 1 1 0)
(00000CDC 100 1		UNVar1)
(00000CDE 5 0		UnVar0)
(00000CE0 61 4 0		nil->JMP 00000CE7)
(00000CE3 5 0		UnVar0)
(00000CE5 41		cdr)
(00000CE6 35		not)
(00000CE7 9 218 0		"VLMSG.DLL")
(00000CEA 51 72 68 0 0		17480)
(00000CEF 81 2 217 0 1 0		string-resource)
(00000CF5 5 0		UnVar0)
(00000CF7 95 3 173 4 0 0		func 000004AD)
(00000CFD 10)
(00000CFE 5 0		UnVar0)
(00000D00 40		car)
(00000D01 11)
(00000D02 8 1		UnVar1)
(00000D04 37 3		symbolp)
(00000D06 13 9 0		nil->JMP 00000D12)
(00000D09 5 1		UnVar1)
(00000D0B 95 1 150 6 0 0		func 00000696)
(00000D11 10)
(00000D12 5 1		UnVar1)
(00000D14 97 1 211 23 0 0		offset 000017D3)
;;;def nil 3354
(00000D1A 20 2 1 1 0)
(00000D1F 100 1		UNVar1)
(00000D21 5 0		UnVar0)
(00000D23 61 4 0		nil->JMP 00000D2A)
(00000D26 5 0		UnVar0)
(00000D28 41		cdr)
(00000D29 35		not)
(00000D2A 9 218 0		"VLMSG.DLL")
(00000D2D 51 82 68 0 0		17490)
(00000D32 81 2 217 0 1 0		string-resource)
(00000D38 5 0		UnVar0)
(00000D3A 95 3 173 4 0 0		func 000004AD)
(00000D40 10)
(00000D41 5 0		UnVar0)
(00000D43 40		car)
(00000D44 11)
(00000D45 8 1		UnVar1)
(00000D47 37 3		symbolp)
(00000D49 13 9 0		nil->JMP 00000D55)
(00000D4C 5 0		UnVar0)
(00000D4E 40		car)
(00000D4F 97 1 203 6 0 0		offset 000006CB)
(00000D55 5 1		UnVar1)
(00000D57 37 2		consp)
(00000D59 61 34 0		nil->JMP 00000D7E)
(00000D5C 5 1		UnVar1)
(00000D5E 40		car)
(00000D5F 81 1 123 0 1 0		lpp-sym?)
(00000D65 9 118 0		'lambda)
(00000D68 38		=)
(00000D69 61 18 0		nil->JMP 00000D7E)
(00000D6C 5 1		UnVar1)
(00000D6E 41		cdr)
(00000D6F 37 2		consp)
(00000D71 61 10 0		nil->JMP 00000D7E)
(00000D74 5 1		UnVar1)
(00000D76 41		cdr)
(00000D77 40		car)
(00000D78 81 1 103 0 1 0		listp)
(00000D7E 13 8 0		nil->JMP 00000D89)
(00000D81 5 1		UnVar1)
(00000D83 96 1 5 12 0 0		func 00000C05)
(00000D89 9 218 0		"VLMSG.DLL")
(00000D8C 51 92 68 0 0		17500)
(00000D91 81 2 217 0 1 0		string-resource)
(00000D97 5 1		UnVar1)
(00000D99 97 2 200 4 0 0		offset 000004C8)
;;;def nil 3487
(00000D9F 20 3 3 3 0)
(00000DA4 5 1		UnVar1)
(00000DA6 13 10 0		nil->JMP 00000DB3)
(00000DA9 5 1		UnVar1)
(00000DAB 40		car)
(00000DAC 95 1 231 13 0 0		func 00000DE7)
(00000DB2 10)
(00000DB3 5 0		UnVar0)
(00000DB5 5 1		UnVar1)
(00000DB7 5 2		UnVar2)
(00000DB9 96 3 216 26 0 0		func 00001AD8)
;;;def nil 3519
(00000DBF 20 3 3 3 0)
(00000DC4 5 1		UnVar1)
(00000DC6 61 5 0		nil->JMP 00000DCE)
(00000DC9 5 1		UnVar1)
(00000DCB 41		cdr)
(00000DCC 41		cdr)
(00000DCD 35		not)
(00000DCE 13 10 0		nil->JMP 00000DDB)
(00000DD1 5 1		UnVar1)
(00000DD3 40		car)
(00000DD4 95 1 231 13 0 0		func 00000DE7)
(00000DDA 10)
(00000DDB 5 0		UnVar0)
(00000DDD 5 1		UnVar1)
(00000DDF 5 2		UnVar2)
(00000DE1 96 3 216 26 0 0		func 00001AD8)
;;;def nil 3559
(00000DE7 20 2 1 1 0)
(00000DEC 100 1		UNVar1)
(00000DEE 5 0		UnVar0)
(00000DF0 37 2		consp)
(00000DF2 61 43 0		nil->JMP 00000E20)
(00000DF5 5 0		UnVar0)
(00000DF7 81 1 124 0 1 0		list-length)
(00000DFD 61 32 0		nil->JMP 00000E20)
(00000E00 5 0		UnVar0)
(00000E02 40		car)
(00000E03 81 1 123 0 1 0		lpp-sym?)
(00000E09 9 102 0		'(quote function))
(00000E0C 81 2 236 0 1 0		memq)
(00000E12 61 11 0		nil->JMP 00000E20)
(00000E15 5 0		UnVar0)
(00000E17 41		cdr)
(00000E18 61 5 0		nil->JMP 00000E20)
(00000E1B 5 0		UnVar0)
(00000E1D 41		cdr)
(00000E1E 41		cdr)
(00000E1F 35		not)
(00000E20 13 141 0		nil->JMP 00000EB0)
(00000E23 5 0		UnVar0)
(00000E25 40		car)
(00000E26 81 1 123 0 1 0		lpp-sym?)
(00000E2C 9 117 0		'function)
(00000E2F 38		=)
(00000E30 13 3 0		nil->JMP 00000E36)
(00000E33 15 119 0		JMP 00000EAD)
(00000E36 5 0		UnVar0)
(00000E38 41		cdr)
(00000E39 40		car)
(00000E3A 37 3		symbolp)
(00000E3C 13 14 0		nil->JMP 00000E4D)
(00000E3F 5 0		UnVar0)
(00000E41 41		cdr)
(00000E42 40		car)
(00000E43 95 1 198 6 0 0		func 000006C6)
(00000E49 10)
(00000E4A 15 96 0		JMP 00000EAD)
(00000E4D 5 0		UnVar0)
(00000E4F 41		cdr)
(00000E50 40		car)
(00000E51 11)
(00000E52 8 1		UnVar1)
(00000E54 37 2		consp)
(00000E56 61 43 0		nil->JMP 00000E84)
(00000E59 5 1		UnVar1)
(00000E5B 81 1 124 0 1 0		list-length)
(00000E61 61 32 0		nil->JMP 00000E84)
(00000E64 5 1		UnVar1)
(00000E66 40		car)
(00000E67 81 1 123 0 1 0		lpp-sym?)
(00000E6D 9 118 0		'lambda)
(00000E70 38		=)
(00000E71 61 16 0		nil->JMP 00000E84)
(00000E74 5 1		UnVar1)
(00000E76 41		cdr)
(00000E77 61 10 0		nil->JMP 00000E84)
(00000E7A 5 1		UnVar1)
(00000E7C 41		cdr)
(00000E7D 40		car)
(00000E7E 81 1 103 0 1 0		listp)
(00000E84 13 12 0		nil->JMP 00000E93)
(00000E87 5 1		UnVar1)
(00000E89 95 1 182 17 0 0		func 000011B6)
(00000E8F 10)
(00000E90 15 26 0		JMP 00000EAD)
(00000E93 9 218 0		"VLMSG.DLL")
(00000E96 51 102 68 0 0		17510)
(00000E9B 81 2 217 0 1 0		string-resource)
(00000EA1 5 1		UnVar1)
(00000EA3 9 101 0		':bad-fun)
(00000EA6 95 3 226 4 0 0		func 000004E2)
(00000EAC 10)
(00000EAD 15 26 0		JMP 00000ECA)
(00000EB0 9 218 0		"VLMSG.DLL")
(00000EB3 51 112 68 0 0		17520)
(00000EB8 81 2 217 0 1 0		string-resource)
(00000EBE 5 0		UnVar0)
(00000EC0 9 100 0		':rt-eval)
(00000EC3 95 3 226 4 0 0		func 000004E2)
(00000EC9 10)
(00000ECA 5 0		UnVar0)
(00000ECC 96 1 5 12 0 0		func 00000C05)
;;;def nil 3794
(00000ED2 20 3 3 3 0)
(00000ED7 3 182 0		*syntax-error-break*)
(00000EDA 13 4 0		nil->JMP 00000EE1)
(00000EDD 1		nil)
(00000EDE 15 9 0		JMP 00000EEA)
(00000EE1 5 1		UnVar1)
(00000EE3 61 4 0		nil->JMP 00000EEA)
(00000EE6 5 1		UnVar1)
(00000EE8 41		cdr)
(00000EE9 35		not)
(00000EEA 13 89 0		nil->JMP 00000F46)
(00000EED 5 1		UnVar1)
(00000EEF 40		car)
(00000EF0 81 1 103 0 1 0		listp)
(00000EF6 61 32 0		nil->JMP 00000F19)
(00000EF9 5 1		UnVar1)
(00000EFB 40		car)
(00000EFC 40		car)
(00000EFD 37 3		symbolp)
(00000EFF 61 23 0		nil->JMP 00000F19)
(00000F02 5 1		UnVar1)
(00000F04 40		car)
(00000F05 40		car)
(00000F06 81 1 123 0 1 0		lpp-sym?)
(00000F0C 9 116 0		'quote)
(00000F0F 38		=)
(00000F10 61 6 0		nil->JMP 00000F19)
(00000F13 5 1		UnVar1)
(00000F15 40		car)
(00000F16 41		cdr)
(00000F17 41		cdr)
(00000F18 35		not)
(00000F19 13 15 0		nil->JMP 00000F2B)
(00000F1C 5 1		UnVar1)
(00000F1E 40		car)
(00000F1F 41		cdr)
(00000F20 40		car)
(00000F21 95 1 182 17 0 0		func 000011B6)
(00000F27 10)
(00000F28 15 27 0		JMP 00000F46)
(00000F2B 9 218 0		"VLMSG.DLL")
(00000F2E 51 122 68 0 0		17530)
(00000F33 81 2 217 0 1 0		string-resource)
(00000F39 5 1		UnVar1)
(00000F3B 40		car)
(00000F3C 9 100 0		':rt-eval)
(00000F3F 95 3 226 4 0 0		func 000004E2)
(00000F45 10)
(00000F46 5 0		UnVar0)
(00000F48 5 1		UnVar1)
(00000F4A 5 2		UnVar2)
(00000F4C 96 3 216 26 0 0		func 00001AD8)
;;;def nil 3922
(00000F52 20 3 3 3 0)
(00000F57 3 182 0		*syntax-error-break*)
(00000F5A 13 4 0		nil->JMP 00000F61)
(00000F5D 1		nil)
(00000F5E 15 13 0		JMP 00000F6E)
(00000F61 5 1		UnVar1)
(00000F63 41		cdr)
(00000F64 61 7 0		nil->JMP 00000F6E)
(00000F67 5 1		UnVar1)
(00000F69 41		cdr)
(00000F6A 41		cdr)
(00000F6B 41		cdr)
(00000F6C 41		cdr)
(00000F6D 35		not)
(00000F6E 13 62 0		nil->JMP 00000FAF)
(00000F71 5 1		UnVar1)
(00000F73 41		cdr)
(00000F74 41		cdr)
(00000F75 40		car)
(00000F76 13 54 0		nil->JMP 00000FAF)
(00000F79 5 1		UnVar1)
(00000F7B 41		cdr)
(00000F7C 41		cdr)
(00000F7D 40		car)
(00000F7E 37 4		stringp)
(00000F80 13 15 0		nil->JMP 00000F92)
(00000F83 5 1		UnVar1)
(00000F85 41		cdr)
(00000F86 41		cdr)
(00000F87 40		car)
(00000F88 53 1 99 0 1 32		acheck-eval-spec-string/err-hk)
(00000F8E 10)
(00000F8F 15 29 0		JMP 00000FAF)
(00000F92 9 218 0		"VLMSG.DLL")
(00000F95 51 122 68 0 0		17530)
(00000F9A 81 2 217 0 1 0		string-resource)
(00000FA0 5 1		UnVar1)
(00000FA2 41		cdr)
(00000FA3 41		cdr)
(00000FA4 40		car)
(00000FA5 9 100 0		':rt-eval)
(00000FA8 95 3 226 4 0 0		func 000004E2)
(00000FAE 10)
(00000FAF 5 0		UnVar0)
(00000FB1 5 1		UnVar1)
(00000FB3 5 2		UnVar2)
(00000FB5 96 3 216 26 0 0		func 00001AD8)
;;;def nil 4027
(00000FBB 20 3 3 3 0)
(00000FC0 3 182 0		*syntax-error-break*)
(00000FC3 13 4 0		nil->JMP 00000FCA)
(00000FC6 1		nil)
(00000FC7 15 11 0		JMP 00000FD5)
(00000FCA 5 1		UnVar1)
(00000FCC 41		cdr)
(00000FCD 61 5 0		nil->JMP 00000FD5)
(00000FD0 5 1		UnVar1)
(00000FD2 41		cdr)
(00000FD3 41		cdr)
(00000FD4 35		not)
(00000FD5 13 51 0		nil->JMP 0000100B)
(00000FD8 5 1		UnVar1)
(00000FDA 41		cdr)
(00000FDB 40		car)
(00000FDC 37 4		stringp)
(00000FDE 13 14 0		nil->JMP 00000FEF)
(00000FE1 5 1		UnVar1)
(00000FE3 41		cdr)
(00000FE4 40		car)
(00000FE5 53 1 99 0 1 32		acheck-eval-spec-string/err-hk)
(00000FEB 10)
(00000FEC 15 28 0		JMP 0000100B)
(00000FEF 9 218 0		"VLMSG.DLL")
(00000FF2 51 122 68 0 0		17530)
(00000FF7 81 2 217 0 1 0		string-resource)
(00000FFD 5 1		UnVar1)
(00000FFF 41		cdr)
(00001000 40		car)
(00001001 9 100 0		':rt-eval)
(00001004 95 3 226 4 0 0		func 000004E2)
(0000100A 10)
(0000100B 5 0		UnVar0)
(0000100D 5 1		UnVar1)
(0000100F 5 2		UnVar2)
(00001011 96 3 216 26 0 0		func 00001AD8)
;;;def acheck-eval-spec-string/err-hk 4119
(00001017 21 1 1 1 0)
(0000101C 9 202 0		'*check-throw*)
(0000101F 1		nil)
(00001020 81 1 137 0 1 0		box)
(00001026 24 2 0)
(00001029 3 202 0		*check-throw*)
(0000102C 57 1 0		list)
(0000102F 15 130 0		JMP 000010B4)
(00001032 20 0 0 0 0)
(00001037 9 194 0		'_%sys-error-hook%)
(0000103A 15 100 0		JMP 000010A1)
(0000103D 20 2 1 1 0)
(00001042 100 1		UNVar1)
(00001044 3 209 0		_%rdr-cons-pos-stack%)
(00001047 13 17 0		nil->JMP 0000105B)
(0000104A 3 208 0		*comp-S-expr*)
(0000104D 3 207 0		_%src-sk%)
(00001050 3 209 0		_%rdr-cons-pos-stack%)
(00001053 53 3 206 0 1 32		localise-expr-in-rdr-stacks)
(00001059 8 1		UnVar1)
(0000105B 9 98 0		':ACTION-ERROR)
(0000105E 95 1 32 5 0 0		AL-symbol)
(00001064 4 2 0		UpVar2-0)
(00001067 5 0		UnVar0)
(00001069 57 1 0		list)
(0000106C 3 204 0		*usubr-source-reference*)
(0000106F 5 1		UnVar1)
(00001071 13 6 0		nil->JMP 0000107A)
(00001074 5 1		UnVar1)
(00001076 40		car)
(00001077 15 2 0		JMP 0000107C)
(0000107A 50 0		0)
(0000107C 5 1		UnVar1)
(0000107E 13 6 0		nil->JMP 00001087)
(00001081 5 1		UnVar1)
(00001083 41		cdr)
(00001084 15 2 0		JMP 00001089)
(00001087 50 0		0)
(00001089 53 3 203 0 1 32		create-show-item)
(0000108F 95 4 102 6 0 0		func 00000666)
(00001095 10)
(00001096 3 202 0		*check-throw*)
(00001099 1		nil)
(0000109A 81 2 201 0 1 0		throw)
(000010A0 22		ret)
(000010A1 12 4 1		'(4157 nil))
(000010A4 24 2 0)
(000010A7 4 1 0		UpVar1-0)
(000010AA 95 1 194 16 0 0		func 000010C2)
(000010B0 25 1 0)
(000010B3 22		ret)
(000010B4 12 3 1		'(4146 -catch-))
(000010B7 1		nil)
(000010B8 81 3 126 0 1 0		_catched-apply)
(000010BE 25 1 0)
(000010C1 22		ret)
;;;def nil 4290
(000010C2 20 4 1 1 0)
(000010C7 100 1		UNVar1)
(000010C9 100 2		UNVar2)
(000010CB 100 3		UNVar3)
(000010CD 5 0		UnVar0)
(000010CF 53 1 97 0 1 32		action-fun-str?)
(000010D5 8 2		UnVar2)
(000010D7 5 2		UnVar2)
(000010D9 63		nil->ret)
(000010DA 9 208 0		'*comp-S-expr*)
(000010DD 3 105 0		*read-eval-from-string*)
(000010E0 13 6 0		nil->JMP 000010E9)
(000010E3 3 208 0		*comp-S-expr*)
(000010E6 15 2 0		JMP 000010EB)
(000010E9 5 0		UnVar0)
(000010EB 9 105 0		'*read-eval-from-string*)
(000010EE 2		T)
(000010EF 24 4 0)
(000010F2 9 136 0		'%rdr-cons-stack%)
(000010F5 1		nil)
(000010F6 9 134 0		'%rdr-cons-pos-stack%)
(000010F9 1		nil)
(000010FA 9 196 0		'*error-trace-stack*)
(000010FD 1		nil)
(000010FE 9 133 0		'%al-rdr-sym8-stack%)
(00001101 81 0 96 0 1 0		make-stack)
(00001107 24 8 0)
(0000110A 5 2		UnVar2)
(0000110C 53 1 95 0 1 32		read-from-spec-string)
(00001112 8 3		UnVar3)
(00001114 3 133 0		%al-rdr-sym8-stack%)
(00001117 81 1 94 0 1 0		stack->list)
(0000111D 11)
(0000111E 8 1		UnVar1)
(00001120 13 35 0		nil->JMP 00001146)
(00001123 9 218 0		"VLMSG.DLL")
(00001126 51 132 68 0 0		17540)
(0000112B 81 2 217 0 1 0		string-resource)
(00001131 5 1		UnVar1)
(00001133 9 162 0		'_addr<)
(00001136 81 2 161 0 1 0		sort)
(0000113C 9 93 0		':READ)
(0000113F 95 3 226 4 0 0		func 000004E2)
(00001145 10)
(00001146 25 4 0)
(00001149 5 3		UnVar3)
(0000114B 95 1 182 17 0 0		func 000011B6)
(00001151 25 2 0)
(00001154 22		ret)
;;;def read-from-spec-string 4437
(00001155 21 3 1 1 0)
(0000115A 5 0		UnVar0)
(0000115C 81 1 92 0 1 0		make-string-input-stream)
(00001162 8 1		UnVar1)
(00001164 5 1		UnVar1)
(00001166 8 2		UnVar2)
(00001168 15 35 0		JMP 0000118E)
(0000116B 20 0 0 0 0)
(00001170 4 1 2		UpVar1-2)
(00001173 81 1 91 0 1 0		streamp)
(00001179 63		nil->ret)
(0000117A 4 1 2		UpVar1-2)
(0000117D 81 1 90 0 1 0		open-streamp)
(00001183 63		nil->ret)
(00001184 4 1 2		UpVar1-2)
(00001187 81 1 89 0 1 0		close)
(0000118D 22		ret)
(0000118E 12 2 1		'(4459 -unwind-cleanup-))
(00001191 15 23 0		JMP 000011AB)
(00001194 20 0 0 0 0)
(00001199 4 1 1		UpVar1-1)
(0000119C 1		nil)
(0000119D 1		nil)
(0000119E 81 1 137 0 1 0		box)
(000011A4 81 3 127 0 1 0		as:read)
(000011AA 22		ret)
(000011AB 12 1 1		'(4500 -unwind-protect-))
(000011AE 1		nil)
(000011AF 81 3 88 0 1 0		_unwinded-apply)
(000011B5 22		ret)
;;;def nil 4534
(000011B6 20 1 1 1 0)
(000011BB 9 104 0		'*run-time-evaluation*)
(000011BE 2		T)
(000011BF 24 2 0)
(000011C2 5 0		UnVar0)
(000011C4 95 1 5 12 0 0		func 00000C05)
(000011CA 25 1 0)
(000011CD 22		ret)
;;;def nil 4558
(000011CE 20 9 2 2 0)
(000011D3 100 2		UNVar2)
(000011D5 100 3		UNVar3)
(000011D7 100 4		UNVar4)
(000011D9 5 1		UnVar1)
(000011DB 13 3 0		nil->JMP 000011E1)
(000011DE 15 30 0		JMP 000011FF)
(000011E1 9 218 0		"VLMSG.DLL")
(000011E4 51 142 68 0 0		17550)
(000011E9 81 2 217 0 1 0		string-resource)
(000011EF 9 113 0		'PRAGMA)
(000011F2 5 0		UnVar0)
(000011F4 42		cons)
(000011F5 9 87 0		':pragma)
(000011F8 95 3 226 4 0 0		func 000004E2)
(000011FE 10)
(000011FF 5 1		UnVar1)
(00001201 13 178 2		nil->JMP 000014B6)
(00001204 5 0		UnVar0)
(00001206 37 2		consp)
(00001208 61 76 0		nil->JMP 00001257)
(0000120B 5 0		UnVar0)
(0000120D 41		cdr)
(0000120E 13 4 0		nil->JMP 00001215)
(00001211 1		nil)
(00001212 15 66 0		JMP 00001257)
(00001215 5 0		UnVar0)
(00001217 40		car)
(00001218 37 2		consp)
(0000121A 61 58 0		nil->JMP 00001257)
(0000121D 5 0		UnVar0)
(0000121F 40		car)
(00001220 41		cdr)
(00001221 37 2		consp)
(00001223 61 49 0		nil->JMP 00001257)
(00001226 5 0		UnVar0)
(00001228 40		car)
(00001229 40		car)
(0000122A 37 3		symbolp)
(0000122C 61 40 0		nil->JMP 00001257)
(0000122F 5 0		UnVar0)
(00001231 40		car)
(00001232 40		car)
(00001233 81 1 123 0 1 0		lpp-sym?)
(00001239 9 116 0		'quote)
(0000123C 38		=)
(0000123D 61 23 0		nil->JMP 00001257)
(00001240 5 0		UnVar0)
(00001242 40		car)
(00001243 41		cdr)
(00001244 40		car)
(00001245 11)
(00001246 8 4		UnVar4)
(00001248 81 1 103 0 1 0		listp)
(0000124E 61 6 0		nil->JMP 00001257)
(00001251 5 0		UnVar0)
(00001253 40		car)
(00001254 41		cdr)
(00001255 41		cdr)
(00001256 35		not)
(00001257 9 218 0		"VLMSG.DLL")
(0000125A 51 152 68 0 0		17560)
(0000125F 81 2 217 0 1 0		string-resource)
(00001265 5 0		UnVar0)
(00001267 95 3 173 4 0 0		func 000004AD)
(0000126D 10)
(0000126E 5 4		UnVar4)
(00001270 8 5		UnVar5)
(00001272 100 6		UNVar6)
(00001274 15 58 2		JMP 000014B1)
(00001277 5 5		UnVar5)
(00001279 40		car)
(0000127A 8 6		UnVar6)
(0000127C 5 5		UnVar5)
(0000127E 41		cdr)
(0000127F 8 5		UnVar5)
(00001281 5 6		UnVar6)
(00001283 81 1 103 0 1 0		listp)
(00001289 13 37 2		nil->JMP 000014B1)
(0000128C 5 6		UnVar6)
(0000128E 40		car)
(0000128F 8 3		UnVar3)
(00001291 5 6		UnVar6)
(00001293 41		cdr)
(00001294 8 2		UnVar2)
(00001296 5 3		UnVar3)
(00001298 81 1 123 0 1 0		lpp-sym?)
(0000129E 9 86 0		'(trace untrace PROTECT-ASSIGN UNPROTECT-ASSIGN DEBUG-on-ENTRY UNDEBUG-on-ENTRY EXPORT-to-ACAD UNEXPORT-to-ACAD))
(000012A1 81 2 236 0 1 0		memq)
(000012A7 13 91 0		nil->JMP 00001305)
(000012AA 5 6		UnVar6)
(000012AC 81 1 124 0 1 0		list-length)
(000012B2 60 23 0		T->JMP 000012CC)
(000012B5 9 218 0		"VLMSG.DLL")
(000012B8 51 162 68 0 0		17570)
(000012BD 81 2 217 0 1 0		string-resource)
(000012C3 5 6		UnVar6)
(000012C5 95 2 195 4 0 0		func 000004C3)
(000012CB 10)
(000012CC 5 2		UnVar2)
(000012CE 8 7		UnVar7)
(000012D0 100 8		UNVar8)
(000012D2 15 40 0		JMP 000012FD)
(000012D5 5 7		UnVar7)
(000012D7 40		car)
(000012D8 8 8		UnVar8)
(000012DA 5 7		UnVar7)
(000012DC 41		cdr)
(000012DD 8 7		UnVar7)
(000012DF 5 8		UnVar8)
(000012E1 37 3		symbolp)
(000012E3 60 23 0		T->JMP 000012FD)
(000012E6 9 218 0		"VLMSG.DLL")
(000012E9 51 172 68 0 0		17580)
(000012EE 81 2 217 0 1 0		string-resource)
(000012F4 5 8		UnVar8)
(000012F6 95 2 195 4 0 0		func 000004C3)
(000012FC 10)
(000012FD 5 7		UnVar7)
(000012FF 60 211 255		T->JMP 000012D5)
(00001302 15 137 0		JMP 0000138E)
(00001305 5 3		UnVar3)
(00001307 81 1 123 0 1 0		lpp-sym?)
(0000130D 9 85 0		'(LINK NOT-LINK LOCALISE LOCALIZE NOT-LOCALIZE NOT-LOCALISE))
(00001310 81 2 236 0 1 0		memq)
(00001316 13 91 0		nil->JMP 00001374)
(00001319 5 6		UnVar6)
(0000131B 81 1 124 0 1 0		list-length)
(00001321 60 23 0		T->JMP 0000133B)
(00001324 9 218 0		"VLMSG.DLL")
(00001327 51 162 68 0 0		17570)
(0000132C 81 2 217 0 1 0		string-resource)
(00001332 5 6		UnVar6)
(00001334 95 2 195 4 0 0		func 000004C3)
(0000133A 10)
(0000133B 5 2		UnVar2)
(0000133D 8 7		UnVar7)
(0000133F 100 8		UNVar8)
(00001341 15 40 0		JMP 0000136C)
(00001344 5 7		UnVar7)
(00001346 40		car)
(00001347 8 8		UnVar8)
(00001349 5 7		UnVar7)
(0000134B 41		cdr)
(0000134C 8 7		UnVar7)
(0000134E 5 8		UnVar8)
(00001350 37 3		symbolp)
(00001352 60 23 0		T->JMP 0000136C)
(00001355 9 218 0		"VLMSG.DLL")
(00001358 51 172 68 0 0		17580)
(0000135D 81 2 217 0 1 0		string-resource)
(00001363 5 8		UnVar8)
(00001365 95 2 195 4 0 0		func 000004C3)
(0000136B 10)
(0000136C 5 7		UnVar7)
(0000136E 60 211 255		T->JMP 00001344)
(00001371 15 26 0		JMP 0000138E)
(00001374 9 218 0		"VLMSG.DLL")
(00001377 51 192 68 0 0		17600)
(0000137C 81 2 217 0 1 0		string-resource)
(00001382 5 6		UnVar6)
(00001384 9 87 0		':pragma)
(00001387 95 3 226 4 0 0		func 000004E2)
(0000138D 10)
(0000138E 5 3		UnVar3)
(00001390 81 1 123 0 1 0		lpp-sym?)
(00001396 9 84 0		'(EXPORT-to-ACAD UNEXPORT-to-ACAD))
(00001399 81 2 236 0 1 0		memq)
(0000139F 13 33 0		nil->JMP 000013C3)
(000013A2 5 2		UnVar2)
(000013A4 8 7		UnVar7)
(000013A6 100 8		UNVar8)
(000013A8 15 19 0		JMP 000013BE)
(000013AB 5 7		UnVar7)
(000013AD 40		car)
(000013AE 8 8		UnVar8)
(000013B0 5 7		UnVar7)
(000013B2 41		cdr)
(000013B3 8 7		UnVar7)
(000013B5 5 8		UnVar8)
(000013B7 95 1 198 6 0 0		func 000006C6)
(000013BD 10)
(000013BE 5 7		UnVar7)
(000013C0 60 232 255		T->JMP 000013AB)
(000013C3 5 3		UnVar3)
(000013C5 81 1 123 0 1 0		lpp-sym?)
(000013CB 9 83 0		'LINK)
(000013CE 38		=)
(000013CF 13 42 0		nil->JMP 000013FC)
(000013D2 5 2		UnVar2)
(000013D4 8 7		UnVar7)
(000013D6 100 8		UNVar8)
(000013D8 15 28 0		JMP 000013F7)
(000013DB 5 7		UnVar7)
(000013DD 40		car)
(000013DE 8 8		UnVar8)
(000013E0 5 7		UnVar7)
(000013E2 41		cdr)
(000013E3 8 7		UnVar7)
(000013E5 5 8		UnVar8)
(000013E7 95 1 182 5 0 0		func 000005B6)
(000013ED 10)
(000013EE 5 8		UnVar8)
(000013F0 95 1 247 5 0 0		func 000005F7)
(000013F6 10)
(000013F7 5 7		UnVar7)
(000013F9 60 223 255		T->JMP 000013DB)
(000013FC 5 3		UnVar3)
(000013FE 81 1 123 0 1 0		lpp-sym?)
(00001404 9 82 0		'NOT-LINK)
(00001407 38		=)
(00001408 13 42 0		nil->JMP 00001435)
(0000140B 5 2		UnVar2)
(0000140D 8 7		UnVar7)
(0000140F 100 8		UNVar8)
(00001411 15 28 0		JMP 00001430)
(00001414 5 7		UnVar7)
(00001416 40		car)
(00001417 8 8		UnVar8)
(00001419 5 7		UnVar7)
(0000141B 41		cdr)
(0000141C 8 7		UnVar7)
(0000141E 5 8		UnVar8)
(00001420 95 1 226 5 0 0		func 000005E2)
(00001426 10)
(00001427 5 8		UnVar8)
(00001429 95 1 203 5 0 0		func 000005CB)
(0000142F 10)
(00001430 5 7		UnVar7)
(00001432 60 223 255		T->JMP 00001414)
(00001435 5 3		UnVar3)
(00001437 81 1 123 0 1 0		lpp-sym?)
(0000143D 9 81 0		'(LOCALIZE LOCALISE))
(00001440 81 2 236 0 1 0		memq)
(00001446 13 42 0		nil->JMP 00001473)
(00001449 5 2		UnVar2)
(0000144B 8 7		UnVar7)
(0000144D 100 8		UNVar8)
(0000144F 15 28 0		JMP 0000146E)
(00001452 5 7		UnVar7)
(00001454 40		car)
(00001455 8 8		UnVar8)
(00001457 5 7		UnVar7)
(00001459 41		cdr)
(0000145A 8 7		UnVar7)
(0000145C 5 8		UnVar8)
(0000145E 95 1 14 6 0 0		func 0000060E)
(00001464 10)
(00001465 5 8		UnVar8)
(00001467 95 1 79 6 0 0		func 0000064F)
(0000146D 10)
(0000146E 5 7		UnVar7)
(00001470 60 223 255		T->JMP 00001452)
(00001473 5 3		UnVar3)
(00001475 81 1 123 0 1 0		lpp-sym?)
(0000147B 9 80 0		'(NOT-LOCALIZE NOT-LOCALISE))
(0000147E 81 2 236 0 1 0		memq)
(00001484 13 42 0		nil->JMP 000014B1)
(00001487 5 2		UnVar2)
(00001489 8 7		UnVar7)
(0000148B 100 8		UNVar8)
(0000148D 15 28 0		JMP 000014AC)
(00001490 5 7		UnVar7)
(00001492 40		car)
(00001493 8 8		UnVar8)
(00001495 5 7		UnVar7)
(00001497 41		cdr)
(00001498 8 7		UnVar7)
(0000149A 5 8		UnVar8)
(0000149C 95 1 58 6 0 0		func 0000063A)
(000014A2 10)
(000014A3 5 8		UnVar8)
(000014A5 95 1 35 6 0 0		func 00000623)
(000014AB 10)
(000014AC 5 7		UnVar7)
(000014AE 60 223 255		T->JMP 00001490)
(000014B1 5 5		UnVar5)
(000014B3 60 193 253		T->JMP 00001277)
(000014B6 1		nil)
(000014B7 22		ret)
;;;def nil 5304
(000014B8 20 1 1 1 0)
(000014BD 5 0		UnVar0)
(000014BF 81 1 123 0 1 0		lpp-sym?)
(000014C5 9 79 0		'*ERROR*)
(000014C8 38		=)
(000014C9 62		T->ret)
(000014CA 9 218 0		"VLMSG.DLL")
(000014CD 51 202 68 0 0		17610)
(000014D2 81 2 217 0 1 0		string-resource)
(000014D8 5 0		UnVar0)
(000014DA 9 78 0		':built-sym)
(000014DD 96 3 226 4 0 0		func 000004E2)
;;;def nil 5347
(000014E3 20 1 1 1 0)
(000014E8 9 218 0		"VLMSG.DLL")
(000014EB 51 202 68 0 0		17610)
(000014F0 81 2 217 0 1 0		string-resource)
(000014F6 5 0		UnVar0)
(000014F8 9 77 0		':spec-form)
(000014FB 96 3 226 4 0 0		func 000004E2)
;;;def nil 5377
(00001501 20 2 1 1 0)
(00001506 100 1		UNVar1)
(00001508 5 0		UnVar0)
(0000150A 41		cdr)
(0000150B 9 218 0		"VLMSG.DLL")
(0000150E 51 212 68 0 0		17620)
(00001513 81 2 217 0 1 0		string-resource)
(00001519 5 0		UnVar0)
(0000151B 95 3 173 4 0 0		func 000004AD)
(00001521 10)
(00001522 5 0		UnVar0)
(00001524 40		car)
(00001525 11)
(00001526 8 1		UnVar1)
(00001528 37 3		symbolp)
(0000152A 13 89 0		nil->JMP 00001586)
(0000152D 5 1		UnVar1)
(0000152F 95 1 143 0 0 0		al-form-descr?)
(00001535 14 8 0		T->JMP 00001540)
(00001538 5 1		UnVar1)
(0000153A 95 1 126 0 0 0		al-sys-protected-p)
(00001540 13 10 0		nil->JMP 0000154D)
(00001543 5 0		UnVar0)
(00001545 40		car)
(00001546 95 1 184 20 0 0		func 000014B8)
(0000154C 10)
(0000154D 5 0		UnVar0)
(0000154F 41		cdr)
(00001550 40		car)
(00001551 95 1 5 12 0 0		func 00000C05)
(00001557 10)
(00001558 5 1		UnVar1)
(0000155A 95 1 25 7 0 0		func 00000719)
(00001560 10)
(00001561 9 181 0		'*bind-list*)
(00001564 5 1		UnVar1)
(00001566 95 1 3 5 0 0		func 00000503)
(0000156C 24 2 0)
(0000156F 5 1		UnVar1)
(00001571 95 1 230 6 0 0		func 000006E6)
(00001577 10)
(00001578 5 0		UnVar0)
(0000157A 41		cdr)
(0000157B 41		cdr)
(0000157C 95 1 145 26 0 0		func 00001A91)
(00001582 25 1 0)
(00001585 22		ret)
(00001586 9 218 0		"VLMSG.DLL")
(00001589 51 222 68 0 0		17630)
(0000158E 81 2 217 0 1 0		string-resource)
(00001594 5 0		UnVar0)
(00001596 40		car)
(00001597 97 2 200 4 0 0		offset 000004C8)
;;;def nil 5533
(0000159D 20 2 1 1 0)
(000015A2 100 1		UNVar1)
(000015A4 5 0		UnVar0)
(000015A6 41		cdr)
(000015A7 9 218 0		"VLMSG.DLL")
(000015AA 51 232 68 0 0		17640)
(000015AF 81 2 217 0 1 0		string-resource)
(000015B5 5 0		UnVar0)
(000015B7 95 3 173 4 0 0		func 000004AD)
(000015BD 10)
(000015BE 5 0		UnVar0)
(000015C0 40		car)
(000015C1 11)
(000015C2 8 1		UnVar1)
(000015C4 37 3		symbolp)
(000015C6 13 89 0		nil->JMP 00001622)
(000015C9 5 1		UnVar1)
(000015CB 95 1 143 0 0 0		al-form-descr?)
(000015D1 14 8 0		T->JMP 000015DC)
(000015D4 5 1		UnVar1)
(000015D6 95 1 126 0 0 0		al-sys-protected-p)
(000015DC 13 10 0		nil->JMP 000015E9)
(000015DF 5 0		UnVar0)
(000015E1 40		car)
(000015E2 95 1 184 20 0 0		func 000014B8)
(000015E8 10)
(000015E9 5 0		UnVar0)
(000015EB 41		cdr)
(000015EC 40		car)
(000015ED 95 1 5 12 0 0		func 00000C05)
(000015F3 10)
(000015F4 5 1		UnVar1)
(000015F6 95 1 25 7 0 0		func 00000719)
(000015FC 10)
(000015FD 9 181 0		'*bind-list*)
(00001600 5 1		UnVar1)
(00001602 95 1 3 5 0 0		func 00000503)
(00001608 24 2 0)
(0000160B 5 1		UnVar1)
(0000160D 95 1 230 6 0 0		func 000006E6)
(00001613 10)
(00001614 5 0		UnVar0)
(00001616 41		cdr)
(00001617 41		cdr)
(00001618 95 1 145 26 0 0		func 00001A91)
(0000161E 25 1 0)
(00001621 22		ret)
(00001622 9 218 0		"VLMSG.DLL")
(00001625 51 242 68 0 0		17650)
(0000162A 81 2 217 0 1 0		string-resource)
(00001630 5 0		UnVar0)
(00001632 40		car)
(00001633 97 2 200 4 0 0		offset 000004C8)
;;;def nil 5689
(00001639 20 3 1 1 0)
(0000163E 100 1		UNVar1)
(00001640 5 0		UnVar0)
(00001642 40		car)
(00001643 81 1 103 0 1 0		listp)
(00001649 61 3 0		nil->JMP 0000164F)
(0000164C 5 0		UnVar0)
(0000164E 41		cdr)
(0000164F 9 218 0		"VLMSG.DLL")
(00001652 51 252 68 0 0		17660)
(00001657 81 2 217 0 1 0		string-resource)
(0000165D 5 0		UnVar0)
(0000165F 95 3 173 4 0 0		func 000004AD)
(00001665 10)
(00001666 5 0		UnVar0)
(00001668 40		car)
(00001669 95 1 172 24 0 0		func 000018AC)
(0000166F 8 1		UnVar1)
(00001671 5 1		UnVar1)
(00001673 41		cdr)
(00001674 8 1		UnVar1)
(00001676 5 1		UnVar1)
(00001678 41		cdr)
(00001679 8 1		UnVar1)
(0000167B 5 0		UnVar0)
(0000167D 41		cdr)
(0000167E 5 1		UnVar1)
(00001680 40		car)
(00001681 8 2		UnVar2)
(00001683 5 1		UnVar1)
(00001685 41		cdr)
(00001686 8 1		UnVar1)
(00001688 5 2		UnVar2)
(0000168A 97 2 87 10 0 0		offset 00000A57)
;;;def nil 5776
(00001690 20 2 1 1 0)
(00001695 100 1		UNVar1)
(00001697 5 0		UnVar0)
(00001699 37 2		consp)
(0000169B 13 76 0		nil->JMP 000016EA)
(0000169E 5 0		UnVar0)
(000016A0 40		car)
(000016A1 37 2		consp)
(000016A3 61 9 0		nil->JMP 000016AF)
(000016A6 5 0		UnVar0)
(000016A8 40		car)
(000016A9 81 1 124 0 1 0		list-length)
(000016AF 9 218 0		"VLMSG.DLL")
(000016B2 51 6 69 0 0		17670)
(000016B7 81 2 217 0 1 0		string-resource)
(000016BD 5 0		UnVar0)
(000016BF 95 3 173 4 0 0		func 000004AD)
(000016C5 10)
(000016C6 5 0		UnVar0)
(000016C8 40		car)
(000016C9 40		car)
(000016CA 95 1 5 12 0 0		func 00000C05)
(000016D0 10)
(000016D1 5 0		UnVar0)
(000016D3 41		cdr)
(000016D4 95 1 144 22 0 0		func 00001690)
(000016DA 10)
(000016DB 5 0		UnVar0)
(000016DD 40		car)
(000016DE 41		cdr)
(000016DF 63		nil->ret)
(000016E0 5 0		UnVar0)
(000016E2 40		car)
(000016E3 41		cdr)
(000016E4 97 1 150 26 0 0		offset 00001A96)
(000016EA 5 0		UnVar0)
(000016EC 63		nil->ret)
(000016ED 9 218 0		"VLMSG.DLL")
(000016F0 51 16 69 0 0		17680)
(000016F5 81 2 217 0 1 0		string-resource)
(000016FB 5 0		UnVar0)
(000016FD 97 2 200 4 0 0		offset 000004C8)
;;;def nil 5891
(00001703 20 2 1 1 0)
(00001708 100 1		UNVar1)
(0000170A 5 0		UnVar0)
(0000170C 41		cdr)
(0000170D 9 218 0		"VLMSG.DLL")
(00001710 51 26 69 0 0		17690)
(00001715 81 2 217 0 1 0		string-resource)
(0000171B 3 208 0		*comp-S-expr*)
(0000171E 95 3 173 4 0 0		func 000004AD)
(00001724 10)
(00001725 5 0		UnVar0)
(00001727 40		car)
(00001728 11)
(00001729 8 1		UnVar1)
(0000172B 37 3		symbolp)
(0000172D 13 3 0		nil->JMP 00001733)
(00001730 15 23 0		JMP 0000174A)
(00001733 9 218 0		"VLMSG.DLL")
(00001736 51 36 69 0 0		17700)
(0000173B 81 2 217 0 1 0		string-resource)
(00001741 5 1		UnVar1)
(00001743 95 2 195 4 0 0		func 000004C3)
(00001749 10)
(0000174A 5 1		UnVar1)
(0000174C 95 1 210 0 0 0		al-spec-form-descr?)
(00001752 13 9 0		nil->JMP 0000175E)
(00001755 5 1		UnVar1)
(00001757 95 1 227 20 0 0		func 000014E3)
(0000175D 10)
(0000175E 5 1		UnVar1)
(00001760 95 1 94 0 0 0		al-sys-fun-exist-p)
(00001766 13 9 0		nil->JMP 00001772)
(00001769 5 1		UnVar1)
(0000176B 95 1 184 20 0 0		func 000014B8)
(00001771 10)
(00001772 5 1		UnVar1)
(00001774 81 1 123 0 1 0		lpp-sym?)
(0000177A 95 1 126 0 0 0		al-sys-protected-p)
(00001780 13 9 0		nil->JMP 0000178C)
(00001783 5 1		UnVar1)
(00001785 95 1 184 20 0 0		func 000014B8)
(0000178B 10)
(0000178C 5 1		UnVar1)
(0000178E 95 1 230 6 0 0		func 000006E6)
(00001794 10)
(00001795 5 1		UnVar1)
(00001797 95 1 15 5 0 0		func 0000050F)
(0000179D 13 6 0		nil->JMP 000017A6)
(000017A0 3 104 0		*run-time-evaluation*)
(000017A3 15 1 0		JMP 000017A7)
(000017A6 2		T)
(000017A7 13 9 0		nil->JMP 000017B3)
(000017AA 5 1		UnVar1)
(000017AC 95 1 182 6 0 0		func 000006B6)
(000017B2 10)
(000017B3 5 0		UnVar0)
(000017B5 41		cdr)
(000017B6 40		car)
(000017B7 95 1 5 12 0 0		func 00000C05)
(000017BD 10)
(000017BE 5 0		UnVar0)
(000017C0 41		cdr)
(000017C1 41		cdr)
(000017C2 11)
(000017C3 8 0		UnVar0)
(000017C5 63		nil->ret)
(000017C6 5 0		UnVar0)
(000017C8 97 1 8 23 0 0		offset 00001708)
;;;def nil 6094
(000017CE 20 1 1 1 0)
(000017D3 1		nil)
(000017D4 22		ret)
;;;def nil 6101
(000017D5 20 5 1 1 0)
(000017DA 100 1		UNVar1)
(000017DC 100 2		UNVar2)
(000017DE 100 3		UNVar3)
(000017E0 5 0		UnVar0)
(000017E2 41		cdr)
(000017E3 41		cdr)
(000017E4 61 21 0		nil->JMP 000017FC)
(000017E7 5 0		UnVar0)
(000017E9 41		cdr)
(000017EA 40		car)
(000017EB 81 1 103 0 1 0		listp)
(000017F1 61 8 0		nil->JMP 000017FC)
(000017F4 5 0		UnVar0)
(000017F6 40		car)
(000017F7 11)
(000017F8 8 2		UnVar2)
(000017FA 37 3		symbolp)
(000017FC 9 218 0		"VLMSG.DLL")
(000017FF 51 46 69 0 0		17710)
(00001804 81 2 217 0 1 0		string-resource)
(0000180A 5 0		UnVar0)
(0000180C 95 3 173 4 0 0		func 000004AD)
(00001812 10)
(00001813 5 2		UnVar2)
(00001815 95 1 210 0 0 0		al-spec-form-descr?)
(0000181B 13 9 0		nil->JMP 00001827)
(0000181E 5 2		UnVar2)
(00001820 95 1 227 20 0 0		func 000014E3)
(00001826 10)
(00001827 5 2		UnVar2)
(00001829 95 1 94 0 0 0		al-sys-fun-exist-p)
(0000182F 13 9 0		nil->JMP 0000183B)
(00001832 5 2		UnVar2)
(00001834 95 1 184 20 0 0		func 000014B8)
(0000183A 10)
(0000183B 5 0		UnVar0)
(0000183D 41		cdr)
(0000183E 40		car)
(0000183F 95 1 172 24 0 0		func 000018AC)
(00001845 8 3		UnVar3)
(00001847 5 2		UnVar2)
(00001849 5 3		UnVar3)
(0000184B 40		car)
(0000184C 8 4		UnVar4)
(0000184E 5 3		UnVar3)
(00001850 41		cdr)
(00001851 8 3		UnVar3)
(00001853 5 4		UnVar4)
(00001855 11)
(00001856 8 1		UnVar1)
(00001858 95 2 246 6 0 0		func 000006F6)
(0000185E 10)
(0000185F 3 104 0		*run-time-evaluation*)
(00001862 13 20 0		nil->JMP 00001879)
(00001865 5 2		UnVar2)
(00001867 5 1		UnVar1)
(00001869 95 2 246 6 0 0		func 000006F6)
(0000186F 10)
(00001870 5 2		UnVar2)
(00001872 95 1 198 6 0 0		func 000006C6)
(00001878 10)
(00001879 5 3		UnVar3)
(0000187B 41		cdr)
(0000187C 8 3		UnVar3)
(0000187E 5 0		UnVar0)
(00001880 41		cdr)
(00001881 41		cdr)
(00001882 5 3		UnVar3)
(00001884 40		car)
(00001885 8 4		UnVar4)
(00001887 5 3		UnVar3)
(00001889 41		cdr)
(0000188A 8 3		UnVar3)
(0000188C 5 4		UnVar4)
(0000188E 97 2 87 10 0 0		offset 00000A57)
;;;def nil 6292
(00001894 20 1 1 1 0)
(00001899 9 104 0		'*run-time-evaluation*)
(0000189C 2		T)
(0000189D 24 2 0)
(000018A0 5 0		UnVar0)
(000018A2 95 1 213 23 0 0		func 000017D5)
(000018A8 25 1 0)
(000018AB 22		ret)
;;;def nil 6316
(000018AC 20 2 1 1 0)
(000018B1 100 1		UNVar1)
(000018B3 9 208 0		'*comp-S-expr*)
(000018B6 5 0		UnVar0)
(000018B8 24 2 0)
(000018BB 5 0		UnVar0)
(000018BD 95 1 233 24 0 0		func 000018E9)
(000018C3 8 1		UnVar1)
(000018C5 5 1		UnVar1)
(000018C7 40		car)
(000018C8 3 76 0		*max-args*)
(000018CB 78		<=)
(000018CC 9 218 0		"VLMSG.DLL")
(000018CF 51 56 69 0 0		17720)
(000018D4 81 2 217 0 1 0		string-resource)
(000018DA 5 0		UnVar0)
(000018DC 95 3 173 4 0 0		func 000004AD)
(000018E2 10)
(000018E3 5 1		UnVar1)
(000018E5 25 1 0)
(000018E8 22		ret)
;;;def nil 6377
(000018E9 20 7 1 6 0)
(000018EE 100 6		UNVar6)
(000018F0 5 4		UnVar4)
(000018F2 60 8 0		T->JMP 000018FD)
(000018F5 50 0		0)
(000018F7 8 4		UnVar4)
(000018F9 50 0		0)
(000018FB 8 5		UnVar5)
(000018FD 5 0		UnVar0)
(000018FF 13 125 1		nil->JMP 00001A7F)
(00001902 5 0		UnVar0)
(00001904 36		atom)
(00001905 13 22 0		nil->JMP 0000191E)
(00001908 9 218 0		"VLMSG.DLL")
(0000190B 51 66 69 0 0		17730)
(00001910 81 2 217 0 1 0		string-resource)
(00001916 5 0		UnVar0)
(00001918 97 2 200 4 0 0		offset 000004C8)
(0000191E 5 0		UnVar0)
(00001920 40		car)
(00001921 11)
(00001922 8 6		UnVar6)
(00001924 37 3		symbolp)
(00001926 13 64 1		nil->JMP 00001A69)
(00001929 5 6		UnVar6)
(0000192B 81 1 123 0 1 0		lpp-sym?)
(00001931 95 1 126 0 0 0		al-sys-protected-p)
(00001937 13 9 0		nil->JMP 00001943)
(0000193A 5 6		UnVar6)
(0000193C 95 1 184 20 0 0		func 000014B8)
(00001942 10)
(00001943 5 6		UnVar6)
(00001945 95 1 210 0 0 0		al-spec-form-descr?)
(0000194B 13 9 0		nil->JMP 00001957)
(0000194E 5 6		UnVar6)
(00001950 95 1 227 20 0 0		func 000014E3)
(00001956 10)
(00001957 5 6		UnVar6)
(00001959 81 1 123 0 1 0		lpp-sym?)
(0000195F 9 75 0		'/)
(00001962 38		=)
(00001963 13 4 0		nil->JMP 0000196A)
(00001966 1		nil)
(00001967 15 8 0		JMP 00001972)
(0000196A 5 6		UnVar6)
(0000196C 95 1 94 0 0 0		al-sys-fun-exist-p)
(00001972 13 9 0		nil->JMP 0000197E)
(00001975 5 6		UnVar6)
(00001977 95 1 184 20 0 0		func 000014B8)
(0000197D 10)
(0000197E 5 0		UnVar0)
(00001980 41		cdr)
(00001981 8 0		UnVar0)
(00001983 5 1		UnVar1)
(00001985 13 129 0		nil->JMP 00001A09)
(00001988 5 6		UnVar6)
(0000198A 5 2		UnVar2)
(0000198C 81 2 236 0 1 0		memq)
(00001992 13 44 0		nil->JMP 000019C1)
(00001995 9 218 0		"VLMSG.DLL")
(00001998 51 86 69 0 0		17750)
(0000199D 81 2 217 0 1 0		string-resource)
(000019A3 5 6		UnVar6)
(000019A5 9 74 0		':arg-lst)
(000019A8 95 3 226 4 0 0		func 000004E2)
(000019AE 10)
(000019AF 5 0		UnVar0)
(000019B1 2		T)
(000019B2 5 2		UnVar2)
(000019B4 5 3		UnVar3)
(000019B6 5 4		UnVar4)
(000019B8 5 5		UnVar5)
(000019BA 79		1+)
(000019BB 97 6 238 24 0 0		offset 000018EE)
(000019C1 5 6		UnVar6)
(000019C3 81 1 123 0 1 0		lpp-sym?)
(000019C9 9 75 0		'/)
(000019CC 38		=)
(000019CD 13 27 0		nil->JMP 000019EB)
(000019D0 9 218 0		"VLMSG.DLL")
(000019D3 51 96 69 0 0		17760)
(000019D8 81 2 217 0 1 0		string-resource)
(000019DE 9 75 0		'/)
(000019E1 5 0		UnVar0)
(000019E3 42		cons)
(000019E4 95 2 195 4 0 0		func 000004C3)
(000019EA 10)
(000019EB 5 6		UnVar6)
(000019ED 95 1 25 7 0 0		func 00000719)
(000019F3 10)
(000019F4 5 0		UnVar0)
(000019F6 2		T)
(000019F7 5 2		UnVar2)
(000019F9 5 6		UnVar6)
(000019FB 5 3		UnVar3)
(000019FD 42		cons)
(000019FE 5 4		UnVar4)
(00001A00 5 5		UnVar5)
(00001A02 79		1+)
(00001A03 97 6 238 24 0 0		offset 000018EE)
(00001A09 5 6		UnVar6)
(00001A0B 5 2		UnVar2)
(00001A0D 81 2 236 0 1 0		memq)
(00001A13 13 23 0		nil->JMP 00001A2D)
(00001A16 9 218 0		"VLMSG.DLL")
(00001A19 51 76 69 0 0		17740)
(00001A1E 81 2 217 0 1 0		string-resource)
(00001A24 5 6		UnVar6)
(00001A26 95 2 195 4 0 0		func 000004C3)
(00001A2C 10)
(00001A2D 5 6		UnVar6)
(00001A2F 81 1 123 0 1 0		lpp-sym?)
(00001A35 9 75 0		'/)
(00001A38 38		=)
(00001A39 13 16 0		nil->JMP 00001A4C)
(00001A3C 5 0		UnVar0)
(00001A3E 2		T)
(00001A3F 5 2		UnVar2)
(00001A41 1		nil)
(00001A42 5 4		UnVar4)
(00001A44 5 5		UnVar5)
(00001A46 97 6 238 24 0 0		offset 000018EE)
(00001A4C 5 6		UnVar6)
(00001A4E 95 1 9 7 0 0		func 00000709)
(00001A54 10)
(00001A55 5 0		UnVar0)
(00001A57 1		nil)
(00001A58 5 6		UnVar6)
(00001A5A 5 2		UnVar2)
(00001A5C 42		cons)
(00001A5D 1		nil)
(00001A5E 5 4		UnVar4)
(00001A60 79		1+)
(00001A61 5 5		UnVar5)
(00001A63 97 6 238 24 0 0		offset 000018EE)
(00001A69 9 218 0		"VLMSG.DLL")
(00001A6C 51 106 69 0 0		17770)
(00001A71 81 2 217 0 1 0		string-resource)
(00001A77 5 6		UnVar6)
(00001A79 97 2 200 4 0 0		offset 000004C8)
(00001A7F 5 4		UnVar4)
(00001A81 5 5		UnVar5)
(00001A83 5 2		UnVar2)
(00001A85 5 3		UnVar3)
(00001A87 81 2 73 0 1 0		append)
(00001A8D 57 3 0		list)
(00001A90 22		ret)
;;;def nil 6801
(00001A91 20 2 1 1 0)
(00001A96 15 19 0		JMP 00001AAC)
(00001A99 5 0		UnVar0)
(00001A9B 40		car)
(00001A9C 8 1		UnVar1)
(00001A9E 5 0		UnVar0)
(00001AA0 41		cdr)
(00001AA1 8 0		UnVar0)
(00001AA3 5 1		UnVar1)
(00001AA5 95 1 5 12 0 0		func 00000C05)
(00001AAB 10)
(00001AAC 5 0		UnVar0)
(00001AAE 60 232 255		T->JMP 00001A99)
(00001AB1 2		T)
(00001AB2 22		ret)
;;;def nil 6835
(00001AB3 20 2 1 2 0)
(00001AB8 5 0		UnVar0)
(00001ABA 3 76 0		*max-args*)
(00001ABD 78		<=)
(00001ABE 62		T->ret)
(00001ABF 5 1		UnVar1)
(00001AC1 63		nil->ret)
(00001AC2 9 218 0		"VLMSG.DLL")
(00001AC5 51 116 69 0 0		17780)
(00001ACA 81 2 217 0 1 0		string-resource)
(00001AD0 5 1		UnVar1)
(00001AD2 97 2 200 4 0 0		offset 000004C8)
;;;def nil 6872
(00001AD8 20 6 3 3 0)
(00001ADD 100 3		UNVar3)
(00001ADF 5 0		UnVar0)
(00001AE1 37 2		consp)
(00001AE3 13 23 0		nil->JMP 00001AFD)
(00001AE6 5 2		UnVar2)
(00001AE8 5 0		UnVar0)
(00001AEA 95 2 179 26 0 0		func 00001AB3)
(00001AF0 10)
(00001AF1 5 0		UnVar0)
(00001AF3 95 1 5 12 0 0		func 00000C05)
(00001AF9 10)
(00001AFA 15 138 1		JMP 00001C87)
(00001AFD 5 0		UnVar0)
(00001AFF 37 3		symbolp)
(00001B01 13 105 1		nil->JMP 00001C6D)
(00001B04 5 0		UnVar0)
(00001B06 95 1 210 0 0 0		al-spec-form-descr?)
(00001B0C 11)
(00001B0D 8 3		UnVar3)
(00001B0F 13 99 0		nil->JMP 00001B75)
(00001B12 5 3		UnVar3)
(00001B14 5 2		UnVar2)
(00001B16 95 2 242 0 0 0		al-not-fit-p)
(00001B1C 8 4		UnVar4)
(00001B1E 5 4		UnVar4)
(00001B20 50 0		0)
(00001B22 81 2 72 0 1 0		equal)
(00001B28 13 29 0		nil->JMP 00001B48)
(00001B2B 9 218 0		"VLMSG.DLL")
(00001B2E 51 136 69 0 0		17800)
(00001B33 81 2 217 0 1 0		string-resource)
(00001B39 5 0		UnVar0)
(00001B3B 5 1		UnVar1)
(00001B3D 42		cons)
(00001B3E 95 2 195 4 0 0		func 000004C3)
(00001B44 10)
(00001B45 15 42 0		JMP 00001B72)
(00001B48 5 4		UnVar4)
(00001B4A 50 1		1)
(00001B4C 81 2 72 0 1 0		equal)
(00001B52 13 29 0		nil->JMP 00001B72)
(00001B55 9 218 0		"VLMSG.DLL")
(00001B58 51 146 69 0 0		17810)
(00001B5D 81 2 217 0 1 0		string-resource)
(00001B63 5 0		UnVar0)
(00001B65 5 1		UnVar1)
(00001B67 42		cons)
(00001B68 95 2 195 4 0 0		func 000004C3)
(00001B6E 10)
(00001B6F 15 0 0		JMP 00001B72)
(00001B72 15 245 0		JMP 00001C6A)
(00001B75 5 0		UnVar0)
(00001B77 81 1 123 0 1 0		lpp-sym?)
(00001B7D 9 71 0		'list)
(00001B80 38		=)
(00001B81 60 230 0		T->JMP 00001C6A)
(00001B84 5 0		UnVar0)
(00001B86 95 1 226 0 0 0		al-sys-fun-descr?)
(00001B8C 11)
(00001B8D 8 3		UnVar3)
(00001B8F 61 107 0		nil->JMP 00001BFD)
(00001B92 5 3		UnVar3)
(00001B94 5 2		UnVar2)
(00001B96 5 0		UnVar0)
(00001B98 95 3 242 0 0 0		al-not-fit-p)
(00001B9E 8 4		UnVar4)
(00001BA0 5 4		UnVar4)
(00001BA2 50 0		0)
(00001BA4 81 2 72 0 1 0		equal)
(00001BAA 13 33 0		nil->JMP 00001BCE)
(00001BAD 9 218 0		"VLMSG.DLL")
(00001BB0 51 136 69 0 0		17800)
(00001BB5 81 2 217 0 1 0		string-resource)
(00001BBB 5 0		UnVar0)
(00001BBD 5 1		UnVar1)
(00001BBF 42		cons)
(00001BC0 9 70 0		':arg-num)
(00001BC3 95 3 226 4 0 0		func 000004E2)
(00001BC9 10)
(00001BCA 1		nil)
(00001BCB 15 47 0		JMP 00001BFD)
(00001BCE 5 4		UnVar4)
(00001BD0 50 1		1)
(00001BD2 81 2 72 0 1 0		equal)
(00001BD8 13 33 0		nil->JMP 00001BFC)
(00001BDB 9 218 0		"VLMSG.DLL")
(00001BDE 51 146 69 0 0		17810)
(00001BE3 81 2 217 0 1 0		string-resource)
(00001BE9 5 0		UnVar0)
(00001BEB 5 1		UnVar1)
(00001BED 42		cons)
(00001BEE 9 70 0		':arg-num)
(00001BF1 95 3 226 4 0 0		func 000004E2)
(00001BF7 10)
(00001BF8 1		nil)
(00001BF9 15 1 0		JMP 00001BFD)
(00001BFC 2		T)
(00001BFD 60 106 0		T->JMP 00001C6A)
(00001C00 5 0		UnVar0)
(00001C02 95 1 94 0 0 0		al-sys-fun-exist-p)
(00001C08 13 14 0		nil->JMP 00001C19)
(00001C0B 5 2		UnVar2)
(00001C0D 5 0		UnVar0)
(00001C0F 95 2 179 26 0 0		func 00001AB3)
(00001C15 10)
(00001C16 15 81 0		JMP 00001C6A)
(00001C19 5 2		UnVar2)
(00001C1B 5 0		UnVar0)
(00001C1D 95 2 179 26 0 0		func 00001AB3)
(00001C23 10)
(00001C24 5 0		UnVar0)
(00001C26 5 2		UnVar2)
(00001C28 95 2 131 6 0 0		func 00000683)
(00001C2E 10)
(00001C2F 5 0		UnVar0)
(00001C31 95 1 15 5 0 0		func 0000050F)
(00001C37 13 26 0		nil->JMP 00001C54)
(00001C3A 9 218 0		"VLMSG.DLL")
(00001C3D 51 156 69 0 0		17820)
(00001C42 81 2 217 0 1 0		string-resource)
(00001C48 5 0		UnVar0)
(00001C4A 9 101 0		':bad-fun)
(00001C4D 95 3 226 4 0 0		func 000004E2)
(00001C53 10)
(00001C54 3 104 0		*run-time-evaluation*)
(00001C57 14 4 0		T->JMP 00001C5E)
(00001C5A 3 125 0		*in-proc-body*)
(00001C5D 35		not)
(00001C5E 13 9 0		nil->JMP 00001C6A)
(00001C61 5 0		UnVar0)
(00001C63 95 1 198 6 0 0		func 000006C6)
(00001C69 10)
(00001C6A 15 26 0		JMP 00001C87)
(00001C6D 9 218 0		"VLMSG.DLL")
(00001C70 51 126 69 0 0		17790)
(00001C75 81 2 217 0 1 0		string-resource)
(00001C7B 5 0		UnVar0)
(00001C7D 5 1		UnVar1)
(00001C7F 42		cons)
(00001C80 95 2 195 4 0 0		func 000004C3)
(00001C86 10)
(00001C87 5 1		UnVar1)
(00001C89 8 4		UnVar4)
(00001C8B 100 5		UNVar5)
(00001C8D 15 19 0		JMP 00001CA3)
(00001C90 5 4		UnVar4)
(00001C92 40		car)
(00001C93 8 5		UnVar5)
(00001C95 5 4		UnVar4)
(00001C97 41		cdr)
(00001C98 8 4		UnVar4)
(00001C9A 5 5		UnVar5)
(00001C9C 95 1 5 12 0 0		func 00000C05)
(00001CA2 10)
(00001CA3 5 4		UnVar4)
(00001CA5 60 232 255		T->JMP 00001C90)
(00001CA8 1		nil)
(00001CA9 22		ret)
;;;def nil 7338
(00001CAA 20 0 0 0 0)
(00001CAF 1		nil)
(00001CB0 22		ret)
;;;def nil 7345
(00001CB1 20 0 0 0 0)
(00001CB6 1		nil)
(00001CB7 22		ret)
;;;def nil 7352
(00001CB8 20 0 0 0 0)
(00001CBD 1		nil)
(00001CBE 22		ret)
;;;def nil 7359
(00001CBF 20 0 0 0 0)
(00001CC4 1		nil)
(00001CC5 22		ret)
;;;def nil 7366
(00001CC6 20 0 0 0 0)
(00001CCB 1		nil)
(00001CCC 22		ret)
;;;def nil 7373
(00001CCD 20 0 0 0 0)
(00001CD2 1		nil)
(00001CD3 22		ret)
;;;def nil 7380
(00001CD4 20 0 0 0 0)
(00001CD9 1		nil)
(00001CDA 22		ret)
;;;def nil 7387
(00001CDB 20 1 1 1 0)
(00001CE0 5 0		UnVar0)
(00001CE2 3 69 0		*decl-link*)
(00001CE5 81 2 178 0 1 0		adjoin)
(00001CEB 11)
(00001CEC 6 69 0		*decl-link*)
(00001CEF 22		ret)
;;;def nil 7408
(00001CF0 20 2 1 1 0)
(00001CF5 100 1		UNVar1)
(00001CF7 5 0		UnVar0)
(00001CF9 3 69 0		*decl-link*)
(00001CFC 81 2 177 0 1 0		delq)
(00001D02 11)
(00001D03 6 69 0		*decl-link*)
(00001D06 22		ret)
;;;def nil 7431
(00001D07 20 1 1 1 0)
(00001D0C 5 0		UnVar0)
(00001D0E 3 68 0		*decl-not-link*)
(00001D11 81 2 178 0 1 0		adjoin)
(00001D17 11)
(00001D18 6 68 0		*decl-not-link*)
(00001D1B 22		ret)
;;;def nil 7452
(00001D1C 20 2 1 1 0)
(00001D21 100 1		UNVar1)
(00001D23 5 0		UnVar0)
(00001D25 3 68 0		*decl-not-link*)
(00001D28 81 2 177 0 1 0		delq)
(00001D2E 11)
(00001D2F 6 68 0		*decl-not-link*)
(00001D32 22		ret)
;;;def nil 7475
(00001D33 20 1 1 1 0)
(00001D38 5 0		UnVar0)
(00001D3A 3 67 0		*decl-local*)
(00001D3D 81 2 178 0 1 0		adjoin)
(00001D43 11)
(00001D44 6 67 0		*decl-local*)
(00001D47 22		ret)
;;;def nil 7496
(00001D48 20 2 1 1 0)
(00001D4D 100 1		UNVar1)
(00001D4F 5 0		UnVar0)
(00001D51 3 67 0		*decl-local*)
(00001D54 81 2 177 0 1 0		delq)
(00001D5A 11)
(00001D5B 6 67 0		*decl-local*)
(00001D5E 22		ret)
;;;def nil 7519
(00001D5F 20 1 1 1 0)
(00001D64 5 0		UnVar0)
(00001D66 3 66 0		*decl-not-local*)
(00001D69 81 2 178 0 1 0		adjoin)
(00001D6F 11)
(00001D70 6 66 0		*decl-not-local*)
(00001D73 22		ret)
;;;def nil 7540
(00001D74 20 2 1 1 0)
(00001D79 100 1		UNVar1)
(00001D7B 5 0		UnVar0)
(00001D7D 3 66 0		*decl-not-local*)
(00001D80 81 2 177 0 1 0		delq)
(00001D86 11)
(00001D87 6 66 0		*decl-not-local*)
(00001D8A 22		ret)
;;;def nil 7563
(00001D8B 20 1 1 1 0)
(00001D90 5 0		UnVar0)
(00001D92 3 65 0		*decl-drop*)
(00001D95 81 2 178 0 1 0		adjoin)
(00001D9B 11)
(00001D9C 6 65 0		*decl-drop*)
(00001D9F 22		ret)
;;;def nil 7584
(00001DA0 20 1 1 1 0)
(00001DA5 5 0		UnVar0)
(00001DA7 3 65 0		*decl-drop*)
(00001DAA 81 2 177 0 1 0		delq)
(00001DB0 11)
(00001DB1 6 65 0		*decl-drop*)
(00001DB4 22		ret)
;;;def nil 7605
(00001DB5 20 1 1 1 0)
(00001DBA 5 0		UnVar0)
(00001DBC 3 64 0		*decl-not-drop*)
(00001DBF 81 2 178 0 1 0		adjoin)
(00001DC5 11)
(00001DC6 6 64 0		*decl-not-drop*)
(00001DC9 22		ret)
;;;def nil 7626
(00001DCA 20 1 1 1 0)
(00001DCF 5 0		UnVar0)
(00001DD1 3 64 0		*decl-not-drop*)
(00001DD4 81 2 177 0 1 0		delq)
(00001DDA 11)
(00001DDB 6 64 0		*decl-not-drop*)
(00001DDE 22		ret)
;;;def nil 7647
(00001DDF 20 1 1 1 0)
(00001DE4 5 0		UnVar0)
(00001DE6 3 63 0		*decl-export-to-acad-prefixs*)
(00001DE9 42		cons)
(00001DEA 11)
(00001DEB 6 63 0		*decl-export-to-acad-prefixs*)
(00001DEE 22		ret)
;;;def global-decl-stream 7663
(00001DEF 21 8 1 2 0)
(00001DF4 100 2		UNVar2)
(00001DF6 100 3		UNVar3)
(00001DF8 100 4		UNVar4)
(00001DFA 100 5		UNVar5)
(00001DFC 100 6		UNVar6)
(00001DFE 5 0		UnVar0)
(00001E00 53 1 142 0 1 32		_istream-source)
(00001E06 9 240 0		':AUTOLISP)
(00001E09 53 2 130 0 1 32		register-istream)
(00001E0F 8 6		UnVar6)
(00001E11 5 6		UnVar6)
(00001E13 8 3		UnVar3)
(00001E15 9 207 0		'_%src-sk%)
(00001E18 81 0 96 0 1 0		make-stack)
(00001E1E 9 209 0		'_%rdr-cons-pos-stack%)
(00001E21 81 0 96 0 1 0		make-stack)
(00001E27 9 69 0		'*decl-link*)
(00001E2A 95 0 177 28 0 0		func 00001CB1)
(00001E30 9 68 0		'*decl-not-link*)
(00001E33 95 0 184 28 0 0		func 00001CB8)
(00001E39 9 67 0		'*decl-local*)
(00001E3C 95 0 191 28 0 0		func 00001CBF)
(00001E42 9 66 0		'*decl-not-local*)
(00001E45 95 0 198 28 0 0		func 00001CC6)
(00001E4B 9 65 0		'*decl-drop*)
(00001E4E 95 0 205 28 0 0		func 00001CCD)
(00001E54 9 64 0		'*decl-not-drop*)
(00001E57 95 0 212 28 0 0		func 00001CD4)
(00001E5D 9 173 0		'*pdb-error-list*)
(00001E60 95 0 76 5 0 0		func 0000054C)
(00001E66 9 182 0		'*syntax-error-break*)
(00001E69 1		nil)
(00001E6A 9 63 0		'*decl-export-to-acad-prefixs*)
(00001E6D 95 0 170 28 0 0		func 00001CAA)
(00001E73 9 62 0		'*src-group*)
(00001E76 5 6		UnVar6)
(00001E78 24 24 0)
(00001E7B 15 77 0		JMP 00001ECB)
(00001E7E 3 209 0		_%rdr-cons-pos-stack%)
(00001E81 50 0		0)
(00001E83 81 2 61 0 1 0		stack-elt)
(00001E89 8 4		UnVar4)
(00001E8B 3 209 0		_%rdr-cons-pos-stack%)
(00001E8E 50 1		1)
(00001E90 81 2 61 0 1 0		stack-elt)
(00001E96 8 5		UnVar5)
(00001E98 9 204 0		'*usubr-source-reference*)
(00001E9B 5 6		UnVar6)
(00001E9D 24 2 0)
(00001EA0 5 1		UnVar1)
(00001EA2 13 3 0		nil->JMP 00001EA8)
(00001EA5 15 19 0		JMP 00001EBB)
(00001EA8 3 227 0		*analyse-output*)
(00001EAB 14 3 0		T->JMP 00001EB1)
(00001EAE 3 60 0		*standard-output*)
(00001EB1 9 59 0		".~!")
(00001EB4 53 2 58 0 1 32		prinf)
(00001EBA 10)
(00001EBB 5 2		UnVar2)
(00001EBD 5 5		UnVar5)
(00001EBF 5 4		UnVar4)
(00001EC1 53 3 57 0 1 32		collect-decl)
(00001EC7 10)
(00001EC8 25 1 0)
(00001ECB 9 240 0		':AUTOLISP)
(00001ECE 81 1 56 0 1 0		_in-package)
(00001ED4 8 7		UnVar7)
(00001ED6 15 15 0		JMP 00001EE8)
(00001ED9 20 0 0 0 0)
(00001EDE 4 1 7		UpVar1-7)
(00001EE1 81 1 56 0 1 0		_in-package)
(00001EE7 22		ret)
(00001EE8 12 0 1		'(7897 -unwind-cleanup-))
(00001EEB 15 18 0		JMP 00001F00)
(00001EEE 20 0 0 0 0)
(00001EF3 4 1 0		UpVar1-0)
(00001EF6 1		nil)
(00001EF7 4 1 3		UpVar1-3)
(00001EFA 47 3 55 0 32 32		read-top-with-pos)
(00001F00 12 255 0		'(7918 -unwind-protect-))
(00001F03 1		nil)
(00001F04 81 3 88 0 1 0		_unwinded-apply)
(00001F0A 11)
(00001F0B 8 2		UnVar2)
(00001F0D 5 3		UnVar3)
(00001F0F 38		=)
(00001F10 35		not)
(00001F11 60 106 255		T->JMP 00001E7E)
(00001F14 5 0		UnVar0)
(00001F16 95 1 32 31 0 0		func 00001F20)
(00001F1C 25 12 0)
(00001F1F 22		ret)
;;;def nil 7968
(00001F20 20 1 1 1 0)
(00001F25 9 143 0		':inp-stream)
(00001F28 95 1 32 5 0 0		AL-symbol)
(00001F2E 5 0		UnVar0)
(00001F30 53 1 142 0 1 32		_istream-source)
(00001F36 42		cons)
(00001F37 9 141 0		':ERROR)
(00001F3A 95 1 32 5 0 0		AL-symbol)
(00001F40 3 173 0		*pdb-error-list*)
(00001F43 42		cons)
(00001F44 9 149 0		':link)
(00001F47 95 1 32 5 0 0		AL-symbol)
(00001F4D 3 69 0		*decl-link*)
(00001F50 42		cons)
(00001F51 9 148 0		':not-link)
(00001F54 95 1 32 5 0 0		AL-symbol)
(00001F5A 3 68 0		*decl-not-link*)
(00001F5D 42		cons)
(00001F5E 9 147 0		':local)
(00001F61 95 1 32 5 0 0		AL-symbol)
(00001F67 3 67 0		*decl-local*)
(00001F6A 42		cons)
(00001F6B 9 146 0		':not-local)
(00001F6E 95 1 32 5 0 0		AL-symbol)
(00001F74 3 66 0		*decl-not-local*)
(00001F77 42		cons)
(00001F78 9 54 0		':drop)
(00001F7B 95 1 32 5 0 0		AL-symbol)
(00001F81 3 65 0		*decl-drop*)
(00001F84 42		cons)
(00001F85 9 53 0		':not-drop)
(00001F88 95 1 32 5 0 0		AL-symbol)
(00001F8E 3 64 0		*decl-not-drop*)
(00001F91 42		cons)
(00001F92 9 52 0		':export-to-acad-prefixs)
(00001F95 95 1 32 5 0 0		AL-symbol)
(00001F9B 3 63 0		*decl-export-to-acad-prefixs*)
(00001F9E 42		cons)
(00001F9F 57 9 0		list)
(00001FA2 22		ret)
;;;def decl-inp-stream:val 8099
(00001FA3 20 1 1 1 0)
(00001FA8 9 143 0		':inp-stream)
(00001FAB 81 1 51 0 1 0		al-sym?)
(00001FB1 5 0		UnVar0)
(00001FB3 81 2 50 0 1 0		assq)
(00001FB9 41		cdr)
(00001FBA 22		ret)
;;;def decl-error:val 8123
(00001FBB 20 1 1 1 0)
(00001FC0 9 141 0		':ERROR)
(00001FC3 81 1 51 0 1 0		al-sym?)
(00001FC9 5 0		UnVar0)
(00001FCB 81 2 50 0 1 0		assq)
(00001FD1 41		cdr)
(00001FD2 22		ret)
;;;def decl-link:val 8147
(00001FD3 20 1 1 1 0)
(00001FD8 9 149 0		':link)
(00001FDB 81 1 51 0 1 0		al-sym?)
(00001FE1 5 0		UnVar0)
(00001FE3 81 2 50 0 1 0		assq)
(00001FE9 41		cdr)
(00001FEA 22		ret)
;;;def decl-not-link:val 8171
(00001FEB 20 1 1 1 0)
(00001FF0 9 148 0		':not-link)
(00001FF3 81 1 51 0 1 0		al-sym?)
(00001FF9 5 0		UnVar0)
(00001FFB 81 2 50 0 1 0		assq)
(00002001 41		cdr)
(00002002 22		ret)
;;;def decl-local:val 8195
(00002003 20 1 1 1 0)
(00002008 9 147 0		':local)
(0000200B 81 1 51 0 1 0		al-sym?)
(00002011 5 0		UnVar0)
(00002013 81 2 50 0 1 0		assq)
(00002019 41		cdr)
(0000201A 22		ret)
;;;def decl-not-local:val 8219
(0000201B 20 1 1 1 0)
(00002020 9 146 0		':not-local)
(00002023 81 1 51 0 1 0		al-sym?)
(00002029 5 0		UnVar0)
(0000202B 81 2 50 0 1 0		assq)
(00002031 41		cdr)
(00002032 22		ret)
;;;def decl-drop:val 8243
(00002033 20 1 1 1 0)
(00002038 9 54 0		':drop)
(0000203B 81 1 51 0 1 0		al-sym?)
(00002041 5 0		UnVar0)
(00002043 81 2 50 0 1 0		assq)
(00002049 41		cdr)
(0000204A 22		ret)
;;;def decl-not-drop:val 8267
(0000204B 20 1 1 1 0)
(00002050 9 53 0		':not-drop)
(00002053 81 1 51 0 1 0		al-sym?)
(00002059 5 0		UnVar0)
(0000205B 81 2 50 0 1 0		assq)
(00002061 41		cdr)
(00002062 22		ret)
;;;def decl-export-to-acad-prefixs:val 8291
(00002063 20 1 1 1 0)
(00002068 9 52 0		':export-to-acad-prefixs)
(0000206B 81 1 51 0 1 0		al-sym?)
(00002071 5 0		UnVar0)
(00002073 81 2 50 0 1 0		assq)
(00002079 41		cdr)
(0000207A 22		ret)
;;;def decl-has-errors-p 8315
(0000207B 20 1 1 1 0)
(00002080 5 0		UnVar0)
(00002082 95 1 187 31 0 0		decl-error:val)
(00002088 81 1 49 0 1 0		ZEROP)
(0000208E 35		not)
(0000208F 22		ret)
;;;def collect-decl 8336
(00002090 21 6 3 3 0)
(00002095 100 3		UNVar3)
(00002097 100 4		UNVar4)
(00002099 100 5		UNVar5)
(0000209B 9 202 0		'*check-throw*)
(0000209E 1		nil)
(0000209F 81 1 137 0 1 0		box)
(000020A5 24 2 0)
(000020A8 3 202 0		*check-throw*)
(000020AB 57 1 0		list)
(000020AE 15 246 2		JMP 000023A7)
(000020B1 20 2 0 0 0)
(000020B6 9 208 0		'*comp-S-expr*)
(000020B9 4 1 0		UpVar1-0)
(000020BC 24 2 0)
(000020BF 4 1 0		UpVar1-0)
(000020C2 81 1 103 0 1 0		listp)
(000020C8 13 190 2		nil->JMP 00002389)
(000020CB 4 1 0		UpVar1-0)
(000020CE 40		car)
(000020CF 7 1 4		UpVar1-4)
(000020D2 4 1 0		UpVar1-0)
(000020D5 41		cdr)
(000020D6 7 1 3		UpVar1-3)
(000020D9 4 1 4		UpVar1-4)
(000020DC 81 1 123 0 1 0		lpp-sym?)
(000020E2 9 48 0		'(LINK NOT-LINK DROP NOT-DROP LOCALIZE NOT-LOCALIZE LOCALISE NOT-LOCALISE))
(000020E5 81 2 236 0 1 0		memq)
(000020EB 13 94 0		nil->JMP 0000214C)
(000020EE 4 1 0		UpVar1-0)
(000020F1 81 1 124 0 1 0		list-length)
(000020F7 60 24 0		T->JMP 00002112)
(000020FA 9 218 0		"VLMSG.DLL")
(000020FD 51 176 69 0 0		17840)
(00002102 81 2 217 0 1 0		string-resource)
(00002108 4 1 0		UpVar1-0)
(0000210B 95 2 195 4 0 0		func 000004C3)
(00002111 10)
(00002112 4 1 3		UpVar1-3)
(00002115 8 0		UnVar0)
(00002117 100 1		UNVar1)
(00002119 15 40 0		JMP 00002144)
(0000211C 5 0		UnVar0)
(0000211E 40		car)
(0000211F 8 1		UnVar1)
(00002121 5 0		UnVar0)
(00002123 41		cdr)
(00002124 8 0		UnVar0)
(00002126 5 1		UnVar1)
(00002128 37 3		symbolp)
(0000212A 60 23 0		T->JMP 00002144)
(0000212D 9 218 0		"VLMSG.DLL")
(00002130 51 186 69 0 0		17850)
(00002135 81 2 217 0 1 0		string-resource)
(0000213B 5 1		UnVar1)
(0000213D 95 2 195 4 0 0		func 000004C3)
(00002143 10)
(00002144 5 0		UnVar0)
(00002146 60 211 255		T->JMP 0000211C)
(00002149 15 137 0		JMP 000021D5)
(0000214C 4 1 4		UpVar1-4)
(0000214F 81 1 123 0 1 0		lpp-sym?)
(00002155 9 47 0		'autoexport-to-ACAD-prefix)
(00002158 38		=)
(00002159 13 94 0		nil->JMP 000021BA)
(0000215C 4 1 0		UpVar1-0)
(0000215F 81 1 124 0 1 0		list-length)
(00002165 60 24 0		T->JMP 00002180)
(00002168 9 218 0		"VLMSG.DLL")
(0000216B 51 176 69 0 0		17840)
(00002170 81 2 217 0 1 0		string-resource)
(00002176 4 1 0		UpVar1-0)
(00002179 95 2 195 4 0 0		func 000004C3)
(0000217F 10)
(00002180 4 1 3		UpVar1-3)
(00002183 8 0		UnVar0)
(00002185 100 1		UNVar1)
(00002187 15 40 0		JMP 000021B2)
(0000218A 5 0		UnVar0)
(0000218C 40		car)
(0000218D 8 1		UnVar1)
(0000218F 5 0		UnVar0)
(00002191 41		cdr)
(00002192 8 0		UnVar0)
(00002194 5 1		UnVar1)
(00002196 37 4		stringp)
(00002198 60 23 0		T->JMP 000021B2)
(0000219B 9 218 0		"VLMSG.DLL")
(0000219E 51 196 69 0 0		17860)
(000021A3 81 2 217 0 1 0		string-resource)
(000021A9 5 1		UnVar1)
(000021AB 95 2 195 4 0 0		func 000004C3)
(000021B1 10)
(000021B2 5 0		UnVar0)
(000021B4 60 211 255		T->JMP 0000218A)
(000021B7 15 27 0		JMP 000021D5)
(000021BA 9 218 0		"VLMSG.DLL")
(000021BD 51 206 69 0 0		17870)
(000021C2 81 2 217 0 1 0		string-resource)
(000021C8 4 1 0		UpVar1-0)
(000021CB 9 87 0		':pragma)
(000021CE 95 3 226 4 0 0		func 000004E2)
(000021D4 10)
(000021D5 4 1 4		UpVar1-4)
(000021D8 81 1 123 0 1 0		lpp-sym?)
(000021DE 9 46 0		'DROP)
(000021E1 38		=)
(000021E2 13 61 0		nil->JMP 00002222)
(000021E5 4 1 3		UpVar1-3)
(000021E8 8 0		UnVar0)
(000021EA 100 1		UNVar1)
(000021EC 15 46 0		JMP 0000221D)
(000021EF 5 0		UnVar0)
(000021F1 40		car)
(000021F2 8 1		UnVar1)
(000021F4 5 0		UnVar0)
(000021F6 41		cdr)
(000021F7 8 0		UnVar0)
(000021F9 5 1		UnVar1)
(000021FB 95 1 139 29 0 0		func 00001D8B)
(00002201 10)
(00002202 5 1		UnVar1)
(00002204 95 1 202 29 0 0		func 00001DCA)
(0000220A 10)
(0000220B 5 1		UnVar1)
(0000220D 95 1 219 28 0 0		func 00001CDB)
(00002213 10)
(00002214 5 1		UnVar1)
(00002216 95 1 28 29 0 0		func 00001D1C)
(0000221C 10)
(0000221D 5 0		UnVar0)
(0000221F 60 205 255		T->JMP 000021EF)
(00002222 4 1 4		UpVar1-4)
(00002225 81 1 123 0 1 0		lpp-sym?)
(0000222B 9 45 0		'NOT-DROP)
(0000222E 38		=)
(0000222F 13 43 0		nil->JMP 0000225D)
(00002232 4 1 3		UpVar1-3)
(00002235 8 0		UnVar0)
(00002237 100 1		UNVar1)
(00002239 15 28 0		JMP 00002258)
(0000223C 5 0		UnVar0)
(0000223E 40		car)
(0000223F 8 1		UnVar1)
(00002241 5 0		UnVar0)
(00002243 41		cdr)
(00002244 8 0		UnVar0)
(00002246 5 1		UnVar1)
(00002248 95 1 181 29 0 0		func 00001DB5)
(0000224E 10)
(0000224F 5 1		UnVar1)
(00002251 95 1 160 29 0 0		func 00001DA0)
(00002257 10)
(00002258 5 0		UnVar0)
(0000225A 60 223 255		T->JMP 0000223C)
(0000225D 4 1 4		UpVar1-4)
(00002260 81 1 123 0 1 0		lpp-sym?)
(00002266 9 83 0		'LINK)
(00002269 38		=)
(0000226A 13 43 0		nil->JMP 00002298)
(0000226D 4 1 3		UpVar1-3)
(00002270 8 0		UnVar0)
(00002272 100 1		UNVar1)
(00002274 15 28 0		JMP 00002293)
(00002277 5 0		UnVar0)
(00002279 40		car)
(0000227A 8 1		UnVar1)
(0000227C 5 0		UnVar0)
(0000227E 41		cdr)
(0000227F 8 0		UnVar0)
(00002281 5 1		UnVar1)
(00002283 95 1 219 28 0 0		func 00001CDB)
(00002289 10)
(0000228A 5 1		UnVar1)
(0000228C 95 1 28 29 0 0		func 00001D1C)
(00002292 10)
(00002293 5 0		UnVar0)
(00002295 60 223 255		T->JMP 00002277)
(00002298 4 1 4		UpVar1-4)
(0000229B 81 1 123 0 1 0		lpp-sym?)
(000022A1 9 82 0		'NOT-LINK)
(000022A4 38		=)
(000022A5 13 43 0		nil->JMP 000022D3)
(000022A8 4 1 3		UpVar1-3)
(000022AB 8 0		UnVar0)
(000022AD 100 1		UNVar1)
(000022AF 15 28 0		JMP 000022CE)
(000022B2 5 0		UnVar0)
(000022B4 40		car)
(000022B5 8 1		UnVar1)
(000022B7 5 0		UnVar0)
(000022B9 41		cdr)
(000022BA 8 0		UnVar0)
(000022BC 5 1		UnVar1)
(000022BE 95 1 7 29 0 0		func 00001D07)
(000022C4 10)
(000022C5 5 1		UnVar1)
(000022C7 95 1 240 28 0 0		func 00001CF0)
(000022CD 10)
(000022CE 5 0		UnVar0)
(000022D0 60 223 255		T->JMP 000022B2)
(000022D3 4 1 4		UpVar1-4)
(000022D6 81 1 123 0 1 0		lpp-sym?)
(000022DC 9 81 0		'(LOCALIZE LOCALISE))
(000022DF 81 2 236 0 1 0		memq)
(000022E5 13 43 0		nil->JMP 00002313)
(000022E8 4 1 3		UpVar1-3)
(000022EB 8 0		UnVar0)
(000022ED 100 1		UNVar1)
(000022EF 15 28 0		JMP 0000230E)
(000022F2 5 0		UnVar0)
(000022F4 40		car)
(000022F5 8 1		UnVar1)
(000022F7 5 0		UnVar0)
(000022F9 41		cdr)
(000022FA 8 0		UnVar0)
(000022FC 5 1		UnVar1)
(000022FE 95 1 51 29 0 0		func 00001D33)
(00002304 10)
(00002305 5 1		UnVar1)
(00002307 95 1 116 29 0 0		func 00001D74)
(0000230D 10)
(0000230E 5 0		UnVar0)
(00002310 60 223 255		T->JMP 000022F2)
(00002313 4 1 4		UpVar1-4)
(00002316 81 1 123 0 1 0		lpp-sym?)
(0000231C 9 80 0		'(NOT-LOCALIZE NOT-LOCALISE))
(0000231F 81 2 236 0 1 0		memq)
(00002325 13 43 0		nil->JMP 00002353)
(00002328 4 1 3		UpVar1-3)
(0000232B 8 0		UnVar0)
(0000232D 100 1		UNVar1)
(0000232F 15 28 0		JMP 0000234E)
(00002332 5 0		UnVar0)
(00002334 40		car)
(00002335 8 1		UnVar1)
(00002337 5 0		UnVar0)
(00002339 41		cdr)
(0000233A 8 0		UnVar0)
(0000233C 5 1		UnVar1)
(0000233E 95 1 95 29 0 0		func 00001D5F)
(00002344 10)
(00002345 5 1		UnVar1)
(00002347 95 1 72 29 0 0		func 00001D48)
(0000234D 10)
(0000234E 5 0		UnVar0)
(00002350 60 223 255		T->JMP 00002332)
(00002353 4 1 4		UpVar1-4)
(00002356 81 1 123 0 1 0		lpp-sym?)
(0000235C 9 47 0		'autoexport-to-ACAD-prefix)
(0000235F 38		=)
(00002360 61 35 0		nil->JMP 00002386)
(00002363 4 1 3		UpVar1-3)
(00002366 8 0		UnVar0)
(00002368 100 1		UNVar1)
(0000236A 15 19 0		JMP 00002380)
(0000236D 5 0		UnVar0)
(0000236F 40		car)
(00002370 8 1		UnVar1)
(00002372 5 0		UnVar0)
(00002374 41		cdr)
(00002375 8 0		UnVar0)
(00002377 5 1		UnVar1)
(00002379 95 1 223 29 0 0		func 00001DDF)
(0000237F 10)
(00002380 5 0		UnVar0)
(00002382 60 232 255		T->JMP 0000236D)
(00002385 1		nil)
(00002386 15 26 0		JMP 000023A3)
(00002389 9 218 0		"VLMSG.DLL")
(0000238C 51 216 69 0 0		17880)
(00002391 81 2 217 0 1 0		string-resource)
(00002397 4 1 0		UpVar1-0)
(0000239A 9 87 0		':pragma)
(0000239D 95 3 226 4 0 0		func 000004E2)
(000023A3 25 1 0)
(000023A6 22		ret)
(000023A7 12 254 0		'(8369 -catch-))
(000023AA 1		nil)
(000023AB 81 3 126 0 1 0		_catched-apply)
(000023B1 25 1 0)
(000023B4 22		ret)
;;;def loc-pdb-stream 9141
(000023B5 20 1 1 1 0)
(000023BA 9 185 0		'*check-warning*)
(000023BD 1		nil)
(000023BE 24 2 0)
(000023C1 5 0		UnVar0)
(000023C3 53 1 44 0 1 32		collect-stream-pdb)
(000023C9 25 1 0)
(000023CC 22		ret)
;;;def check-pdb-stream 9165
(000023CD 20 1 1 1 0)
(000023D2 9 185 0		'*check-warning*)
(000023D5 2		T)
(000023D6 9 187 0		'_%msglevel%)
(000023D9 50 1		1)
(000023DB 24 4 0)
(000023DE 5 0		UnVar0)
(000023E0 53 1 44 0 1 32		collect-stream-pdb)
(000023E6 10)
(000023E7 3 227 0		*analyse-output*)
(000023EA 14 3 0		T->JMP 000023F0)
(000023ED 3 60 0		*standard-output*)
(000023F0 9 218 0		"VLMSG.DLL")
(000023F3 51 226 69 0 0		17890)
(000023F8 81 2 217 0 1 0		string-resource)
(000023FE 53 2 58 0 1 32		prinf)
(00002404 10)
(00002405 1		nil)
(00002406 25 2 0)
(00002409 22		ret)
;;;def collect-stream-pdb 9226
(0000240A 21 8 1 1 0)
(0000240F 100 1		UNVar1)
(00002411 100 2		UNVar2)
(00002413 100 3		UNVar3)
(00002415 100 4		UNVar4)
(00002417 100 5		UNVar5)
(00002419 100 6		UNVar6)
(0000241B 5 0		UnVar0)
(0000241D 53 1 142 0 1 32		_istream-source)
(00002423 9 240 0		':AUTOLISP)
(00002426 53 2 130 0 1 32		register-istream)
(0000242C 8 6		UnVar6)
(0000242E 5 6		UnVar6)
(00002430 8 3		UnVar3)
(00002432 9 207 0		'_%src-sk%)
(00002435 81 0 96 0 1 0		make-stack)
(0000243B 9 209 0		'_%rdr-cons-pos-stack%)
(0000243E 81 0 96 0 1 0		make-stack)
(00002444 9 132 0		'_%al-rdr-sym8-stack%)
(00002447 81 0 96 0 1 0		make-stack)
(0000244D 9 144 0		'*integral-pdb-info*)
(00002450 95 0 41 7 0 0		func 00000729)
(00002456 9 105 0		'*read-eval-from-string*)
(00002459 1		nil)
(0000245A 9 125 0		'*in-proc-body*)
(0000245D 1		nil)
(0000245E 9 179 0		'*stream-link*)
(00002461 95 0 84 5 0 0		func 00000554)
(00002467 9 176 0		'*stream-not-link*)
(0000246A 95 0 91 5 0 0		func 0000055B)
(00002470 9 175 0		'*stream-local*)
(00002473 95 0 98 5 0 0		func 00000562)
(00002479 9 174 0		'*stream-not-local*)
(0000247C 95 0 105 5 0 0		func 00000569)
(00002482 9 173 0		'*pdb-error-list*)
(00002485 95 0 76 5 0 0		func 0000054C)
(0000248B 9 182 0		'*syntax-error-break*)
(0000248E 1		nil)
(0000248F 9 104 0		'*run-time-evaluation*)
(00002492 1		nil)
(00002493 9 62 0		'*src-group*)
(00002496 5 6		UnVar6)
(00002498 24 28 0)
(0000249B 15 124 0		JMP 0000251A)
(0000249E 3 209 0		_%rdr-cons-pos-stack%)
(000024A1 50 0		0)
(000024A3 81 2 61 0 1 0		stack-elt)
(000024A9 8 4		UnVar4)
(000024AB 3 209 0		_%rdr-cons-pos-stack%)
(000024AE 50 1		1)
(000024B0 81 2 61 0 1 0		stack-elt)
(000024B6 8 5		UnVar5)
(000024B8 9 204 0		'*usubr-source-reference*)
(000024BB 5 6		UnVar6)
(000024BD 9 208 0		'*comp-S-expr*)
(000024C0 5 2		UnVar2)
(000024C2 24 4 0)
(000024C5 3 132 0		_%al-rdr-sym8-stack%)
(000024C8 81 1 94 0 1 0		stack->list)
(000024CE 11)
(000024CF 8 1		UnVar1)
(000024D1 13 35 0		nil->JMP 000024F7)
(000024D4 9 218 0		"VLMSG.DLL")
(000024D7 51 132 68 0 0		17540)
(000024DC 81 2 217 0 1 0		string-resource)
(000024E2 5 1		UnVar1)
(000024E4 9 162 0		'_addr<)
(000024E7 81 2 161 0 1 0		sort)
(000024ED 9 93 0		':READ)
(000024F0 95 3 226 4 0 0		func 000004E2)
(000024F6 10)
(000024F7 3 227 0		*analyse-output*)
(000024FA 14 3 0		T->JMP 00002500)
(000024FD 3 60 0		*standard-output*)
(00002500 9 59 0		".~!")
(00002503 53 2 58 0 1 32		prinf)
(00002509 10)
(0000250A 5 2		UnVar2)
(0000250C 5 5		UnVar5)
(0000250E 5 4		UnVar4)
(00002510 53 3 43 0 1 32		collect-top)
(00002516 10)
(00002517 25 2 0)
(0000251A 9 240 0		':AUTOLISP)
(0000251D 81 1 56 0 1 0		_in-package)
(00002523 8 7		UnVar7)
(00002525 15 15 0		JMP 00002537)
(00002528 20 0 0 0 0)
(0000252D 4 1 7		UpVar1-7)
(00002530 81 1 56 0 1 0		_in-package)
(00002536 22		ret)
(00002537 12 253 0		'(9512 -unwind-cleanup-))
(0000253A 15 18 0		JMP 0000254F)
(0000253D 20 0 0 0 0)
(00002542 4 1 0		UpVar1-0)
(00002545 1		nil)
(00002546 4 1 3		UpVar1-3)
(00002549 47 3 55 0 32 32		read-top-with-pos)
(0000254F 12 252 0		'(9533 -unwind-protect-))
(00002552 1		nil)
(00002553 81 3 88 0 1 0		_unwinded-apply)
(00002559 11)
(0000255A 8 2		UnVar2)
(0000255C 5 3		UnVar3)
(0000255E 38		=)
(0000255F 35		not)
(00002560 60 59 255		T->JMP 0000249E)
(00002563 5 0		UnVar0)
(00002565 95 1 114 8 0 0		func 00000872)
(0000256B 8 2		UnVar2)
(0000256D 5 2		UnVar2)
(0000256F 95 1 110 38 0 0		func 0000266E)
(00002575 25 14 0)
(00002578 22		ret)
;;;def sym-list-sort 9593
(00002579 20 1 1 1 0)
(0000257E 5 0		UnVar0)
(00002580 9 42 0		'string-lessp)
(00002583 81 2 161 0 1 0		sort)
(00002589 22		ret)
;;;def nil 9610
(0000258A 20 3 2 2 0)
(0000258F 100 2		UNVar2)
(00002591 3 185 0		*check-warning*)
(00002594 61 21 0		nil->JMP 000025AC)
(00002597 3 41 0		*al-check-warning*)
(0000259A 61 15 0		nil->JMP 000025AC)
(0000259D 3 169 0		*top-non-loc-assign*)
(000025A0 14 9 0		T->JMP 000025AC)
(000025A3 3 170 0		*top-non-loc-val-ref*)
(000025A6 14 3 0		T->JMP 000025AC)
(000025A9 3 165 0		*top-def-arg-num*)
(000025AC 63		nil->ret)
(000025AD 3 227 0		*analyse-output*)
(000025B0 14 3 0		T->JMP 000025B6)
(000025B3 3 60 0		*standard-output*)
(000025B6 8 2		UnVar2)
(000025B8 5 2		UnVar2)
(000025BA 81 1 222 0 1 0		fresh-line)
(000025C0 10)
(000025C1 9 219 0		'*msg-default-title*)
(000025C4 9 218 0		"VLMSG.DLL")
(000025C7 51 60 65 0 0		16700)
(000025CC 81 2 217 0 1 0		string-resource)
(000025D2 9 216 0		'*msg-default-prompt*)
(000025D5 9 218 0		"VLMSG.DLL")
(000025D8 51 70 65 0 0		16710)
(000025DD 81 2 217 0 1 0		string-resource)
(000025E3 24 4 0)
(000025E6 5 2		UnVar2)
(000025E8 3 204 0		*usubr-source-reference*)
(000025EB 5 0		UnVar0)
(000025ED 5 1		UnVar1)
(000025EF 53 3 193 0 1 32		instantiate-show-item)
(000025F5 9 218 0		"VLMSG.DLL")
(000025F8 51 30 70 0 0		17950)
(000025FD 81 2 217 0 1 0		string-resource)
(00002603 53 3 213 0 1 32		prinf-msg)
(00002609 10)
(0000260A 3 169 0		*top-non-loc-assign*)
(0000260D 14 3 0		T->JMP 00002613)
(00002610 3 170 0		*top-non-loc-val-ref*)
(00002613 13 50 0		nil->JMP 00002648)
(00002616 5 2		UnVar2)
(00002618 9 40 0		"~&~a ~s~%~!")
(0000261B 9 218 0		"VLMSG.DLL")
(0000261E 51 40 70 0 0		17960)
(00002623 81 2 217 0 1 0		string-resource)
(00002629 3 169 0		*top-non-loc-assign*)
(0000262C 3 170 0		*top-non-loc-val-ref*)
(0000262F 53 1 39 0 1 32		copy-list)
(00002635 81 2 73 0 1 0		append)
(0000263B 95 1 121 37 0 0		sym-list-sort)
(00002641 53 4 58 0 1 32		prinf)
(00002647 10)
(00002648 3 165 0		*top-def-arg-num*)
(0000264B 61 28 0		nil->JMP 0000266A)
(0000264E 5 2		UnVar2)
(00002650 9 40 0		"~&~a ~s~%~!")
(00002653 9 218 0		"VLMSG.DLL")
(00002656 51 50 70 0 0		17970)
(0000265B 81 2 217 0 1 0		string-resource)
(00002661 3 165 0		*top-def-arg-num*)
(00002664 53 4 58 0 1 32		prinf)
(0000266A 25 2 0)
(0000266D 22		ret)
;;;def nil 9838
(0000266E 20 1 1 1 0)
(00002673 5 0		UnVar0)
(00002675 22		ret)
;;;def acheck-fly 9846
(00002676 20 2 1 2 0)
(0000267B 9 182 0		'*syntax-error-break*)
(0000267E 2		T)
(0000267F 9 185 0		'*check-warning*)
(00002682 1		nil)
(00002683 9 187 0		'_%msglevel%)
(00002686 1		nil)
(00002687 9 105 0		'*read-eval-from-string*)
(0000268A 1		nil)
(0000268B 9 125 0		'*in-proc-body*)
(0000268E 5 1		UnVar1)
(00002690 35		not)
(00002691 9 179 0		'*stream-link*)
(00002694 95 0 84 5 0 0		func 00000554)
(0000269A 9 176 0		'*stream-not-link*)
(0000269D 95 0 91 5 0 0		func 0000055B)
(000026A3 9 175 0		'*stream-local*)
(000026A6 95 0 98 5 0 0		func 00000562)
(000026AC 9 174 0		'*stream-not-local*)
(000026AF 95 0 105 5 0 0		func 00000569)
(000026B5 9 164 0		'*top-bind-param*)
(000026B8 95 0 112 5 0 0		func 00000570)
(000026BE 9 163 0		'*top-bind-aux*)
(000026C1 95 0 119 5 0 0		func 00000577)
(000026C7 9 165 0		'*top-def-arg-num*)
(000026CA 95 0 126 5 0 0		func 0000057E)
(000026D0 9 166 0		'*top-assign*)
(000026D3 95 0 133 5 0 0		func 00000585)
(000026D9 9 167 0		'*top-val-ref*)
(000026DC 95 0 140 5 0 0		func 0000058C)
(000026E2 9 169 0		'*top-non-loc-assign*)
(000026E5 95 0 147 5 0 0		func 00000593)
(000026EB 9 170 0		'*top-non-loc-val-ref*)
(000026EE 95 0 154 5 0 0		func 0000059A)
(000026F4 9 171 0		'*top-quoted-sym*)
(000026F7 95 0 161 5 0 0		func 000005A1)
(000026FD 9 172 0		'*top-fcall-num*)
(00002700 95 0 168 5 0 0		func 000005A8)
(00002706 9 168 0		'*top-call-by-name*)
(00002709 95 0 175 5 0 0		func 000005AF)
(0000270F 9 181 0		'*bind-list*)
(00002712 1		nil)
(00002713 95 1 251 4 0 0		func 000004FB)
(00002719 24 40 0)
(0000271C 5 0		UnVar0)
(0000271E 5 1		UnVar1)
(00002720 95 2 5 12 0 0		func 00000C05)
(00002726 10)
(00002727 25 20 0)
(0000272A 2		T)
(0000272B 22		ret)
;;;def lpdb-strm 10028
(0000272C 20 1 1 1 0)
(00002731 5 0		UnVar0)
(00002733 40		car)
(00002734 40		car)
(00002735 9 143 0		':inp-stream)
(00002738 81 1 51 0 1 0		al-sym?)
(0000273E 38		=)
(0000273F 9 38 0		"Bad LPDB")
(00002742 53 2 188 0 1 32		assert)
(00002748 10)
(00002749 5 0		UnVar0)
(0000274B 40		car)
(0000274C 41		cdr)
(0000274D 22		ret)
;;;def lpdb-err 10062
(0000274E 20 1 1 1 0)
(00002753 5 0		UnVar0)
(00002755 41		cdr)
(00002756 40		car)
(00002757 40		car)
(00002758 9 141 0		':ERROR)
(0000275B 81 1 51 0 1 0		al-sym?)
(00002761 38		=)
(00002762 9 38 0		"Bad LPDB")
(00002765 53 2 188 0 1 32		assert)
(0000276B 10)
(0000276C 5 0		UnVar0)
(0000276E 41		cdr)
(0000276F 40		car)
(00002770 41		cdr)
(00002771 22		ret)
;;;def lpdb-inf 10098
(00002772 20 1 1 1 0)
(00002777 5 0		UnVar0)
(00002779 41		cdr)
(0000277A 41		cdr)
(0000277B 40		car)
(0000277C 40		car)
(0000277D 9 140 0		':stream-info)
(00002780 81 1 51 0 1 0		al-sym?)
(00002786 38		=)
(00002787 9 38 0		"Bad LPDB")
(0000278A 53 2 188 0 1 32		assert)
(00002790 10)
(00002791 5 0		UnVar0)
(00002793 41		cdr)
(00002794 41		cdr)
(00002795 40		car)
(00002796 41		cdr)
(00002797 22		ret)
;;;def lpdb-top-pos-inf 10136
(00002798 20 1 1 1 0)
(0000279D 9 160 0		':pos)
(000027A0 81 1 51 0 1 0		al-sym?)
(000027A6 5 0		UnVar0)
(000027A8 81 2 50 0 1 0		assq)
(000027AE 41		cdr)
(000027AF 22		ret)
;;;def lpdb-top-fcall-num-inf 10160
(000027B0 20 1 1 1 0)
(000027B5 9 151 0		':fcall-num)
(000027B8 81 1 51 0 1 0		al-sym?)
(000027BE 5 0		UnVar0)
(000027C0 81 2 50 0 1 0		assq)
(000027C6 41		cdr)
(000027C7 22		ret)
;;;def lpdb-top-call-by-name-inf 10184
(000027C8 20 1 1 1 0)
(000027CD 9 150 0		':call-by-name)
(000027D0 81 1 51 0 1 0		al-sym?)
(000027D6 5 0		UnVar0)
(000027D8 81 2 50 0 1 0		assq)
(000027DE 41		cdr)
(000027DF 22		ret)
;;;def lpdb-top-non-loc-val-ref-inf 10208
(000027E0 20 1 1 1 0)
(000027E5 9 153 0		':non-loc-val-ref)
(000027E8 81 1 51 0 1 0		al-sym?)
(000027EE 5 0		UnVar0)
(000027F0 81 2 50 0 1 0		assq)
(000027F6 41		cdr)
(000027F7 22		ret)
;;;def lpdb-top-non-loc-assign-inf 10232
(000027F8 20 1 1 1 0)
(000027FD 9 154 0		':non-loc-assign)
(00002800 81 1 51 0 1 0		al-sym?)
(00002806 5 0		UnVar0)
(00002808 81 2 50 0 1 0		assq)
(0000280E 41		cdr)
(0000280F 22		ret)
;;;def lpdb-top-quoted-sym-inf 10256
(00002810 20 1 1 1 0)
(00002815 9 152 0		':quoted)
(00002818 81 1 51 0 1 0		al-sym?)
(0000281E 5 0		UnVar0)
(00002820 81 2 50 0 1 0		assq)
(00002826 41		cdr)
(00002827 22		ret)
;;;def lpdb-top-val-ref-inf 10280
(00002828 20 1 1 1 0)
(0000282D 9 155 0		':val-ref)
(00002830 81 1 51 0 1 0		al-sym?)
(00002836 5 0		UnVar0)
(00002838 81 2 50 0 1 0		assq)
(0000283E 41		cdr)
(0000283F 22		ret)
;;;def lpdb-top-assign-inf 10304
(00002840 20 1 1 1 0)
(00002845 9 156 0		':assign)
(00002848 81 1 51 0 1 0		al-sym?)
(0000284E 5 0		UnVar0)
(00002850 81 2 50 0 1 0		assq)
(00002856 41		cdr)
(00002857 22		ret)
;;;def lpdb-top-def-arg-num-inf 10328
(00002858 20 1 1 1 0)
(0000285D 9 157 0		':def-arg-num)
(00002860 81 1 51 0 1 0		al-sym?)
(00002866 5 0		UnVar0)
(00002868 81 2 50 0 1 0		assq)
(0000286E 41		cdr)
(0000286F 22		ret)
;;;def lpdb-top-bind-param-inf 10352
(00002870 20 1 1 1 0)
(00002875 9 159 0		':bind-param)
(00002878 81 1 51 0 1 0		al-sym?)
(0000287E 5 0		UnVar0)
(00002880 81 2 50 0 1 0		assq)
(00002886 41		cdr)
(00002887 22		ret)
;;;def lpdb-top-bind-aux-inf 10376
(00002888 20 1 1 1 0)
(0000288D 9 158 0		':bind-aux)
(00002890 81 1 51 0 1 0		al-sym?)
(00002896 5 0		UnVar0)
(00002898 81 2 50 0 1 0		assq)
(0000289E 41		cdr)
(0000289F 22		ret)
;;;def lpdb-top-link-inf 10400
(000028A0 20 1 1 1 0)
(000028A5 9 149 0		':link)
(000028A8 81 1 51 0 1 0		al-sym?)
(000028AE 5 0		UnVar0)
(000028B0 81 2 50 0 1 0		assq)
(000028B6 41		cdr)
(000028B7 22		ret)
;;;def lpdb-top-not-link-inf 10424
(000028B8 20 1 1 1 0)
(000028BD 9 148 0		':not-link)
(000028C0 81 1 51 0 1 0		al-sym?)
(000028C6 5 0		UnVar0)
(000028C8 81 2 50 0 1 0		assq)
(000028CE 41		cdr)
(000028CF 22		ret)
;;;def lpdb-top-local-inf 10448
(000028D0 20 1 1 1 0)
(000028D5 9 147 0		':local)
(000028D8 81 1 51 0 1 0		al-sym?)
(000028DE 5 0		UnVar0)
(000028E0 81 2 50 0 1 0		assq)
(000028E6 41		cdr)
(000028E7 22		ret)
;;;def lpdb-top-not-local-inf 10472
(000028E8 20 1 1 1 0)
(000028ED 9 146 0		':not-local)
(000028F0 81 1 51 0 1 0		al-sym?)
(000028F6 5 0		UnVar0)
(000028F8 81 2 50 0 1 0		assq)
(000028FE 41		cdr)
(000028FF 22		ret)
;;;def lpdb-has-errors-p 10496
(00002900 20 1 1 1 0)
(00002905 5 0		UnVar0)
(00002907 95 1 78 39 0 0		lpdb-err)
(0000290D 81 1 49 0 1 0		ZEROP)
(00002913 35		not)
(00002914 22		ret)
;;;def lpdb-p 10517
(00002915 20 1 1 1 0)
(0000291A 5 0		UnVar0)
(0000291C 40		car)
(0000291D 40		car)
(0000291E 9 143 0		':inp-stream)
(00002921 81 1 51 0 1 0		al-sym?)
(00002927 38		=)
(00002928 63		nil->ret)
(00002929 5 0		UnVar0)
(0000292B 41		cdr)
(0000292C 40		car)
(0000292D 40		car)
(0000292E 9 141 0		':ERROR)
(00002931 81 1 51 0 1 0		al-sym?)
(00002937 38		=)
(00002938 63		nil->ret)
(00002939 5 0		UnVar0)
(0000293B 41		cdr)
(0000293C 41		cdr)
(0000293D 40		car)
(0000293E 40		car)
(0000293F 9 140 0		':stream-info)
(00002942 81 1 51 0 1 0		al-sym?)
(00002948 38		=)
(00002949 22		ret)
;;;def lpdb-save 10570
(0000294A 21 4 2 2 0)
(0000294F 5 1		UnVar1)
(00002951 9 37 0		':OUTPUT)
(00002954 81 2 36 0 1 0		open)
(0000295A 8 2		UnVar2)
(0000295C 5 2		UnVar2)
(0000295E 8 3		UnVar3)
(00002960 15 35 0		JMP 00002986)
(00002963 20 0 0 0 0)
(00002968 4 1 2		UpVar1-2)
(0000296B 81 1 91 0 1 0		streamp)
(00002971 63		nil->ret)
(00002972 4 1 2		UpVar1-2)
(00002975 81 1 90 0 1 0		open-streamp)
(0000297B 63		nil->ret)
(0000297C 4 1 2		UpVar1-2)
(0000297F 81 1 89 0 1 0		close)
(00002985 22		ret)
(00002986 12 251 0		'(10595 -unwind-cleanup-))
(00002989 15 54 0		JMP 000029C2)
(0000298C 20 0 0 0 0)
(00002991 9 35 0		'LPDB-AL-TREE)
(00002994 4 1 3		UpVar1-3)
(00002997 81 2 34 0 1 0		princ)
(0000299D 10)
(0000299E 9 218 0		"VLMSG.DLL")
(000029A1 51 108 52 0 0		13420)
(000029A6 81 2 217 0 1 0		string-resource)
(000029AC 4 1 3		UpVar1-3)
(000029AF 81 2 33 0 1 0		write-line)
(000029B5 10)
(000029B6 4 1 0		UpVar1-0)
(000029B9 4 1 3		UpVar1-3)
(000029BC 96 2 95 42 0 0		al-tree-dump)
(000029C2 12 250 0		'(10636 -unwind-protect-))
(000029C5 1		nil)
(000029C6 81 3 88 0 1 0		_unwinded-apply)
(000029CC 10)
(000029CD 1		nil)
(000029CE 22		ret)
;;;def load-lpdb 10703
(000029CF 21 5 1 1 0)
(000029D4 100 1		UNVar1)
(000029D6 100 2		UNVar2)
(000029D8 5 0		UnVar0)
(000029DA 9 32 0		':INPUT)
(000029DD 81 2 36 0 1 0		open)
(000029E3 8 3		UnVar3)
(000029E5 5 3		UnVar3)
(000029E7 8 4		UnVar4)
(000029E9 15 35 0		JMP 00002A0F)
(000029EC 20 0 0 0 0)
(000029F1 4 1 3		UpVar1-3)
(000029F4 81 1 91 0 1 0		streamp)
(000029FA 63		nil->ret)
(000029FB 4 1 3		UpVar1-3)
(000029FE 81 1 90 0 1 0		open-streamp)
(00002A04 63		nil->ret)
(00002A05 4 1 3		UpVar1-3)
(00002A08 81 1 89 0 1 0		close)
(00002A0E 22		ret)
(00002A0F 12 249 0		'(10732 -unwind-cleanup-))
(00002A12 15 63 0		JMP 00002A54)
(00002A15 20 0 0 0 0)
(00002A1A 4 1 4		UpVar1-4)
(00002A1D 81 1 127 0 1 0		as:read)
(00002A23 81 1 123 0 1 0		lpp-sym?)
(00002A29 9 35 0		'LPDB-AL-TREE)
(00002A2C 38		=)
(00002A2D 13 3 0		nil->JMP 00002A33)
(00002A30 15 24 0		JMP 00002A4B)
(00002A33 9 218 0		"VLMSG.DLL")
(00002A36 51 166 69 0 0		17830)
(00002A3B 81 2 217 0 1 0		string-resource)
(00002A41 4 1 0		UpVar1-0)
(00002A44 81 2 191 0 1 0		_msg-err)
(00002A4A 10)
(00002A4B 4 1 4		UpVar1-4)
(00002A4E 47 1 31 0 32 32		al-tree-restore)
(00002A54 12 248 0		'(10773 -unwind-protect-))
(00002A57 1		nil)
(00002A58 81 3 88 0 1 0		_unwinded-apply)
(00002A5E 22		ret)
;;;def al-tree-dump 10847
(00002A5F 20 5 2 2 0)
(00002A64 100 2		UNVar2)
(00002A66 100 3		UNVar3)
(00002A68 100 4		UNVar4)
(00002A6A 81 0 96 0 1 0		make-stack)
(00002A70 8 3		UnVar3)
(00002A72 5 0		UnVar0)
(00002A74 5 3		UnVar3)
(00002A76 95 2 253 44 0 0		func 00002CFD)
(00002A7C 8 4		UnVar4)
(00002A7E 5 4		UnVar4)
(00002A80 5 1		UnVar1)
(00002A82 95 2 219 44 0 0		func 00002CDB)
(00002A88 10)
(00002A89 5 1		UnVar1)
(00002A8B 81 1 212 0 1 0		terpri)
(00002A91 10)
(00002A92 5 4		UnVar4)
(00002A94 37 2		consp)
(00002A96 13 20 0		nil->JMP 00002AAD)
(00002A99 9 30 0		'_%reclaim-list-confirm%)
(00002A9C 2		T)
(00002A9D 24 2 0)
(00002AA0 5 4		UnVar4)
(00002AA2 2		T)
(00002AA3 81 2 29 0 1 0		_reclaim-list)
(00002AA9 10)
(00002AAA 25 1 0)
(00002AAD 5 3		UnVar3)
(00002AAF 2		T)
(00002AB0 81 2 94 0 1 0		stack->list)
(00002AB6 8 4		UnVar4)
(00002AB8 81 0 28 0 1 0		make-string-output-stream)
(00002ABE 8 2		UnVar2)
(00002AC0 5 4		UnVar4)
(00002AC2 5 2		UnVar2)
(00002AC4 95 2 219 44 0 0		func 00002CDB)
(00002ACA 10)
(00002ACB 9 27 0		";")
(00002ACE 5 2		UnVar2)
(00002AD0 81 2 34 0 1 0		princ)
(00002AD6 10)
(00002AD7 9 30 0		'_%reclaim-list-confirm%)
(00002ADA 2		T)
(00002ADB 24 2 0)
(00002ADE 5 4		UnVar4)
(00002AE0 81 1 29 0 1 0		_reclaim-list)
(00002AE6 10)
(00002AE7 25 1 0)
(00002AEA 5 2		UnVar2)
(00002AEC 81 1 26 0 1 0		_ostream-buf)
(00002AF2 8 2		UnVar2)
(00002AF4 5 2		UnVar2)
(00002AF6 81 1 25 0 1 0		streambuf-position)
(00002AFC 8 4		UnVar4)
(00002AFE 3 24 0		*crunch-fasl*)
(00002B01 13 17 0		nil->JMP 00002B15)
(00002B04 50 5		5)
(00002B06 5 4		UnVar4)
(00002B08 50 5		5)
(00002B0A 74		%)
(00002B0B 70		+)
(00002B0C 53 1 23 0 1 32		random-string)
(00002B12 15 3 0		JMP 00002B18)
(00002B15 9 22 0		"")
(00002B18 8 3		UnVar3)
(00002B1A 5 3		UnVar3)
(00002B1C 5 2		UnVar2)
(00002B1E 81 2 21 0 1 0		_nstring-crunch)
(00002B24 10)
(00002B25 5 4		UnVar4)
(00002B27 5 3		UnVar3)
(00002B29 81 1 20 0 1 0		strlen)
(00002B2F 50 1		1)
(00002B31 81 3 19 0 1 0		+&)
(00002B37 5 1		UnVar1)
(00002B39 81 2 34 0 1 0		princ)
(00002B3F 10)
(00002B40 9 18 0		" ;")
(00002B43 5 1		UnVar1)
(00002B45 81 2 34 0 1 0		princ)
(00002B4B 10)
(00002B4C 5 2		UnVar2)
(00002B4E 5 1		UnVar1)
(00002B50 81 2 17 0 1 0		_write-nb-str)
(00002B56 10)
(00002B57 5 3		UnVar3)
(00002B59 5 1		UnVar1)
(00002B5B 81 2 17 0 1 0		_write-nb-str)
(00002B61 10)
(00002B62 5 3		UnVar3)
(00002B64 81 1 20 0 1 0		strlen)
(00002B6A 5 1		UnVar1)
(00002B6C 81 2 16 0 1 0		write-byte)
(00002B72 10)
(00002B73 9 27 0		";")
(00002B76 5 1		UnVar1)
(00002B78 81 2 34 0 1 0		princ)
(00002B7E 10)
(00002B7F 5 1		UnVar1)
(00002B81 81 1 212 0 1 0		terpri)
(00002B87 10)
(00002B88 2		T)
(00002B89 22		ret)
;;;def al-tree-restore 11146
(00002B8A 21 7 1 1 0)
(00002B8F 100 1		UNVar1)
(00002B91 100 2		UNVar2)
(00002B93 100 3		UNVar3)
(00002B95 100 4		UNVar4)
(00002B97 100 5		UNVar5)
(00002B99 9 240 0		':AUTOLISP)
(00002B9C 81 1 56 0 1 0		_in-package)
(00002BA2 8 6		UnVar6)
(00002BA4 15 15 0		JMP 00002BB6)
(00002BA7 20 0 0 0 0)
(00002BAC 4 1 6		UpVar1-6)
(00002BAF 81 1 56 0 1 0		_in-package)
(00002BB5 22		ret)
(00002BB6 12 247 0		'(11175 -unwind-cleanup-))
(00002BB9 15 20 1		JMP 00002CD0)
(00002BBC 20 0 0 0 0)
(00002BC1 4 1 0		UpVar1-0)
(00002BC4 81 1 127 0 1 0		as:read)
(00002BCA 11)
(00002BCB 7 1 5		UpVar1-5)
(00002BCE 63		nil->ret)
(00002BCF 4 1 5		UpVar1-5)
(00002BD2 37 2		consp)
(00002BD4 14 9 0		T->JMP 00002BE0)
(00002BD7 4 1 5		UpVar1-5)
(00002BDA 81 1 210 0 1 0		fixnump)
(00002BE0 63		nil->ret)
(00002BE1 4 1 0		UpVar1-0)
(00002BE4 81 1 127 0 1 0		as:read)
(00002BEA 11)
(00002BEB 7 1 4		UpVar1-4)
(00002BEE 63		nil->ret)
(00002BEF 4 1 4		UpVar1-4)
(00002BF2 81 1 210 0 1 0		fixnump)
(00002BF8 63		nil->ret)
(00002BF9 2		T)
(00002BFA 4 1 0		UpVar1-0)
(00002BFD 81 2 15 0 1 0		peek-char)
(00002C03 63		nil->ret)
(00002C04 50 59		59)
(00002C06 4 1 0		UpVar1-0)
(00002C09 81 1 14 0 1 0		read-char)
(00002C0F 81 2 230 0 1 0		=&)
(00002C15 63		nil->ret)
(00002C16 4 1 4		UpVar1-4)
(00002C19 4 1 0		UpVar1-0)
(00002C1C 81 2 13 0 1 0		_read-nb)
(00002C22 11)
(00002C23 7 1 3		UpVar1-3)
(00002C26 63		nil->ret)
(00002C27 4 1 4		UpVar1-4)
(00002C2A 4 1 3		UpVar1-3)
(00002C2D 81 1 20 0 1 0		strlen)
(00002C33 81 2 230 0 1 0		=&)
(00002C39 63		nil->ret)
(00002C3A 50 59		59)
(00002C3C 4 1 0		UpVar1-0)
(00002C3F 81 1 14 0 1 0		read-char)
(00002C45 81 2 230 0 1 0		=&)
(00002C4B 63		nil->ret)
(00002C4C 4 1 3		UpVar1-3)
(00002C4F 4 1 4		UpVar1-4)
(00002C52 80		1-)
(00002C53 81 2 12 0 1 0		char)
(00002C59 7 1 2		UpVar1-2)
(00002C5C 4 1 3		UpVar1-3)
(00002C5F 4 1 4		UpVar1-4)
(00002C62 4 1 2		UpVar1-2)
(00002C65 50 1		1)
(00002C67 81 3 11 0 1 0		-&)
(00002C6D 4 1 2		UpVar1-2)
(00002C70 81 3 10 0 1 0		substr)
(00002C76 4 1 3		UpVar1-3)
(00002C79 81 2 21 0 1 0		_nstring-crunch)
(00002C7F 81 1 92 0 1 0		make-string-input-stream)
(00002C85 81 1 127 0 1 0		as:read)
(00002C8B 11)
(00002C8C 7 1 1		UpVar1-1)
(00002C8F 81 1 103 0 1 0		listp)
(00002C95 63		nil->ret)
(00002C96 4 1 5		UpVar1-5)
(00002C99 4 1 1		UpVar1-1)
(00002C9C 95 2 135 45 0 0		func 00002D87)
(00002CA2 7 1 3		UpVar1-3)
(00002CA5 9 30 0		'_%reclaim-list-confirm%)
(00002CA8 2		T)
(00002CA9 24 2 0)
(00002CAC 4 1 5		UpVar1-5)
(00002CAF 37 2		consp)
(00002CB1 13 11 0		nil->JMP 00002CBF)
(00002CB4 4 1 5		UpVar1-5)
(00002CB7 2		T)
(00002CB8 81 2 29 0 1 0		_reclaim-list)
(00002CBE 10)
(00002CBF 4 1 1		UpVar1-1)
(00002CC2 81 1 29 0 1 0		_reclaim-list)
(00002CC8 10)
(00002CC9 25 1 0)
(00002CCC 4 1 3		UpVar1-3)
(00002CCF 22		ret)
(00002CD0 12 246 0		'(11196 -unwind-protect-))
(00002CD3 1		nil)
(00002CD4 81 3 88 0 1 0		_unwinded-apply)
(00002CDA 22		ret)
;;;def nil 11483
(00002CDB 20 2 2 2 0)
(00002CE0 9 221 0		'*print-length*)
(00002CE3 1		nil)
(00002CE4 9 220 0		'*print-level*)
(00002CE7 1		nil)
(00002CE8 9 9 0		'%al-print%)
(00002CEB 2		T)
(00002CEC 24 6 0)
(00002CEF 5 0		UnVar0)
(00002CF1 5 1		UnVar1)
(00002CF3 81 2 8 0 1 0		prin1)
(00002CF9 25 3 0)
(00002CFC 22		ret)
;;;def nil 11517
(00002CFD 20 2 2 2 0)
(00002D02 5 0		UnVar0)
(00002D04 37 2		consp)
(00002D06 13 24 0		nil->JMP 00002D21)
(00002D09 5 0		UnVar0)
(00002D0B 40		car)
(00002D0C 5 1		UnVar1)
(00002D0E 95 2 253 44 0 0		func 00002CFD)
(00002D14 5 0		UnVar0)
(00002D16 41		cdr)
(00002D17 5 1		UnVar1)
(00002D19 95 2 253 44 0 0		func 00002CFD)
(00002D1F 42		cons)
(00002D20 22		ret)
(00002D21 5 0		UnVar0)
(00002D23 81 1 210 0 1 0		fixnump)
(00002D29 61 26 0		nil->JMP 00002D46)
(00002D2C 5 0		UnVar0)
(00002D2E 5 0		UnVar0)
(00002D30 50 1		1)
(00002D32 81 2 7 0 1 0		lsh)
(00002D38 50 255		-1)
(00002D3A 81 2 6 0 1 0		ash)
(00002D40 81 2 230 0 1 0		=&)
(00002D46 13 12 0		nil->JMP 00002D55)
(00002D49 5 0		UnVar0)
(00002D4B 50 1		1)
(00002D4D 81 2 7 0 1 0		lsh)
(00002D53 79		1+)
(00002D54 22		ret)
(00002D55 5 0		UnVar0)
(00002D57 13 43 0		nil->JMP 00002D85)
(00002D5A 5 1		UnVar1)
(00002D5C 5 0		UnVar0)
(00002D5E 2		T)
(00002D5F 81 3 5 0 1 0		stack-posq)
(00002D65 14 20 0		T->JMP 00002D7C)
(00002D68 5 1		UnVar1)
(00002D6A 5 0		UnVar0)
(00002D6C 81 2 4 0 1 0		stack-push)
(00002D72 10)
(00002D73 5 1		UnVar1)
(00002D75 81 1 3 0 1 0		stack-length)
(00002D7B 80		1-)
(00002D7C 50 1		1)
(00002D7E 81 2 7 0 1 0		lsh)
(00002D84 22		ret)
(00002D85 1		nil)
(00002D86 22		ret)
;;;def nil 11655
(00002D87 20 2 2 2 0)
(00002D8C 5 0		UnVar0)
(00002D8E 37 2		consp)
(00002D90 13 24 0		nil->JMP 00002DAB)
(00002D93 5 0		UnVar0)
(00002D95 40		car)
(00002D96 5 1		UnVar1)
(00002D98 95 2 135 45 0 0		func 00002D87)
(00002D9E 5 0		UnVar0)
(00002DA0 41		cdr)
(00002DA1 5 1		UnVar1)
(00002DA3 95 2 135 45 0 0		func 00002D87)
(00002DA9 42		cons)
(00002DAA 22		ret)
(00002DAB 5 0		UnVar0)
(00002DAD 13 41 0		nil->JMP 00002DD9)
(00002DB0 5 0		UnVar0)
(00002DB2 81 1 2 0 1 0		evenp&)
(00002DB8 13 19 0		nil->JMP 00002DCE)
(00002DBB 5 0		UnVar0)
(00002DBD 50 255		-1)
(00002DBF 81 2 7 0 1 0		lsh)
(00002DC5 5 1		UnVar1)
(00002DC7 81 2 1 0 1 0		nth)
(00002DCD 22		ret)
(00002DCE 5 0		UnVar0)
(00002DD0 50 255		-1)
(00002DD2 81 2 6 0 1 0		ash)
(00002DD8 22		ret)
(00002DD9 1		nil)
(00002DDA 22		ret)
;;;==========Main==========
(00000000 20 0 0 0 0)
(00000005 1		nil)
(00000006 10)
(00000007 9 101 0		"3/5/18 10:08 PM")
(0000000A 26 100 0		*LOCPDB-date*)
(0000000D 9 100 0		'*LOCPDB-date*)
(00000010 10)
(00000011 9 99 0		'LOCPDB)
(00000014 81 1 98 0 0 0		provide)
(0000001A 10)
(0000001B 9 97 0		'topui)
(0000001E 81 1 96 0 0 0		require)
(00000024 28		[ret])
(00000025 20 0 0 0 0)
(0000002A 1		nil)
(0000002B 10)
(0000002C 1		nil)
(0000002D 28		[ret])
(0000002E 20 3 0 0 0)
(00000033 1		nil)
(00000034 10)
(00000035 1		nil)
(00000036 10)
(00000037 9 156 0		'descr-ht-fill)
(0000003A 26 95 0		descr-ht-fill)
(0000003D 9 95 0		'descr-ht-fill)
(00000040 10)
(00000041 9 155 0		'descr-ht-get?)
(00000044 26 94 0		descr-ht-get?)
(00000047 9 94 0		'descr-ht-get?)
(0000004A 10)
(0000004B 9 154 0		'al-sys-fun-exist-p)
(0000004E 26 93 0		al-sys-fun-exist-p)
(00000051 9 93 0		'al-sys-fun-exist-p)
(00000054 10)
(00000055 9 92 0		'(T PI))
(00000058 27 91 0		*al-init-protected*)
(0000005B 9 91 0		'*al-init-protected*)
(0000005E 10)
(0000005F 9 153 0		'al-sys-protected-p)
(00000062 26 90 0		al-sys-protected-p)
(00000065 9 90 0		'al-sys-protected-p)
(00000068 10)
(00000069 50 127		127)
(0000006B 81 1 89 0 1 0		make-vector)
(00000071 26 88 0		*al-sys-fun-descr-ht*)
(00000074 9 88 0		'*al-sys-fun-descr-ht*)
(00000077 10)
(00000078 50 17		17)
(0000007A 81 1 89 0 1 0		make-vector)
(00000080 26 87 0		*al-spec-form-descr-ht*)
(00000083 9 87 0		'*al-spec-form-descr-ht*)
(00000086 10)
(00000087 9 86 0		'((progn 0 T) (if 2 3) (or 0 T) (and 0 T) (command 0 T) (repeat 1 T) (while 1 T) (trace 1) (untrace 1) (cond 0 T) (setq 2 T) (defun 3 T) (DEFUN-Q 3 T) (lambda 2 T) (PRAGMA 1) (foreach 2 T) (VLAX-FOR 2 T) (quote 1) (function 1)))
(0000008A 8 0		UnVar0)
(0000008C 9 85 0		'((+ 0 T) (- 0 T) (* 0 T) (/ 0 T) (= 1 T) (/= 1 T) (< 1 T) (<= 1 T) (> 1 T) (>= 1 T) (~ 1) (1+ 1) (1- 1) (ABS 1) (ADS 0) (alert 1) (alloc 1) (ANGLE 2) (ANGTOF 1 2) (ANGTOS 1 3) (append 0 T) (apply 2) (ASCII 1) (assoc 2) (ATAN 1 2) (ATOF 1) (atoi 1) (atom 1) (ATOMS-FAMILY 1 2) (BOOLE 3 T) (boundp 1) (car 1) (caar 1) (caaar 1) (cadr 1) (cadar 1) (caddr 1) (caadr 1) (cdr 1) (cdar 1) (cddr 1) (cdaar 1) (cdadr 1) (cddar 1) (cdddr 1) (caaaar 1) (caaadr 1) (caadar 1) (caaddr 1) (cadaar 1) (cadadr 1) (caddar 1) (cadddr 1) (cdaaar 1) (cdaadr 1) (cdadar 1) (cdaddr 1) (cddaar 1) (cddadr 1) (cdddar 1) (cddddr 1) (chr 1) (close 1) (cons 2) (COS 1) (CVUNIT 3) (DISTANCE 2) (DISTOF 1 2) (ENTDEL 1) (ENTGET 1 2) (ENTLAST 0) (ENTMAKE 0 1) (ENTMOD 1) (ENTNEXT 0 1) (ENTSEL 0 1) (ENTUPD 1) (eq 2) (equal 2 3) (*ERROR* 1) (eval 1) (exit 0) (EXP 1) (EXPAND 1) (EXPT 0 T) (FINDFILE 1) (FINDTRUSTEDFILE 1) (FIX 1) (FLOAT 1) (gc 0) (GCD 2) (GETANGLE 0 2) (GETCORNER 1 2) (GETDIST 0 2) (getenv 1) (GETFILED 4) (GETINT 0 1) (GETKWORD 0 1) (GETORIENT 0 2) (GETPOINT 0 2) (GETREAL 0 1) (GETSTRING 0 2) (GETVAR 1) (GRAPHSCR 0) (GRCLEAR 0) (GRDRAW 3 4) (GRREAD 0 3) (GRTEXT 0 3) (GRVECS 1 2) (HANDENT 1) (INITGET 0 2) (INTERS 4 5) (itoa 1) (last 1) (length 1) (list 0 T) (listp 1) (load 1 2) (LOG 1) (logand 0 T) (logior 0 T) (lsh 0 T) (mapcar 2 T) (MAX 0 T) (mem 0) (member 2) (MENUCMD 1) (MIN 0 T) (MINUSP 1) (NENTSEL 0 1) (NENTSELP 0 2) (not 1) (nth 2) (null 1) (NUMBERP 1) (open 2) (OSNAP 2) (POLAR 3) (prin1 0 2) (princ 0 2) (print 0 2) (prompt 1) (quit 0) (read 1) (read-char 0 1) (read-line 0 1) (REDRAW 0 2) (REGAPP 1) (REM 0 T) (reverse 1) (RTOS 1 3) (set 2) (SETVAR 2) (SIN 1) (SQRT 1) (SSADD 0 2) (SSDEL 2) (SSGET 0 5) (SSLENGTH 1) (SSMEMB 2) (SSNAME 2) (STRCASE 1 2) (strcat 0 T) (strlen 0 T) (subst 3) (substr 2 3) (TABLET 1 5) (TBLNEXT 1 2) (TBLSEARCH 2 3) (terpri 0) (TEXTBOX 1) (TEXTPAGE 0) (TEXTSCR 0) (TRANS 3 4) (type 1) (VER 0) (VMON 0) (VPORTS 0) (WCMATCH 2) (write-char 1 2) (write-line 1 2) (XDROOM 1) (XDSIZE 1) (XLOAD 1 2) (XUNLOAD 1 2) (ZEROP 1) (ACAD_STRLSORT 1) (REPORT 1) (ACTION_TILE 2) (ADD_LIST 1) (CLIENT_DATA_TILE 2) (DIMX_TILE 1) (DIMY_TILE 1) (DONE_DIALOG 0 1) (END_IMAGE 0) (END_LIST 0) (FILL_IMAGE 5) (GET_ATTR 2) (GET_TILE 1) (LOAD_DIALOG 1) (MODE_TILE 2) (NEW_DIALOG 2 4) (SET_TILE 2) (SLIDE_IMAGE 5) (START_DIALOG 0) (START_IMAGE 1) (START_LIST 1 3) (TERM_DIALOG 0) (UNLOAD_DIALOG 1) (VECTOR_IMAGE 5) (ARX 0) (arxload 1 2) (arxunload 1 2) (DICTSEARCH 2 3) (DICTNEXT 1 2) (DICTADD 3) (DICTRENAME 3) (DICTREMOVE 2) (ENTMAKEX 0 1) (GETCNAME 1) (GETCFG 1) (HELP 0 3) (NAMEDOBJDICT 0) (SETCFG 2) (SETFUNHELP 1 4) (SETVIEW 1 2) (SNVALID 1 2) (SSGETFIRST 0) (SSNAMEX 1 2) (SSSETFIRST 1 2) (TBLOBJNAME 2)))
(0000008F 8 1		UnVar1)
(00000091 9 84 0		'((_VLISP-VERSION 0) (vl-ACAD-defun 1) (vl-ACAD-undefun 1) (VLISP-IMPORT-EXSUBRS 1) (VLISP-IMPORT-SYMBOL 1) (VLISP-EXPORT-SYMBOL 1) (VLISP-FASRES-LOAD 1 2) (VLISP-FASRES-LIST 1) (VLISP-INIRES-LIST 1) (VL-FILE-SIZE 1) (VL-FILE-COPY 2 3) (VL-FILE-RENAME 2) (VL-FILE-DELETE 1) (VL-FILE-DIRECTORY-P 1) (VL-DIRECTORY-FILES 0 3) (VL-FILENAME-MKTEMP 0 3) (VL-FILENAME-EXTENSION 1) (VL-FILENAME-DIRECTORY 1) (VL-FILENAME-BASE 1) (VL-PRIN1-TO-STRING 1) (VL-PRINC-TO-STRING 1) (VL-SYMBOLP 1) (VL-SYMBOL-NAME 1) (VL-SYMBOL-VALUE 1) (VL-CONSP 1) (VL-LIST* 1 T) (VL-LIST-LENGTH 1) (VL-LIST->STRING 1) (VL-STRING->LIST 1) (VL-SORT 2) (VL-SORT-I 2) (VL-SOME 2 T) (VL-EVERY 2 T) (VL-MEMBER-IF 2) (VL-MEMBER-IF-NOT 2) (VL-REMOVE 2) (VL-REMOVE-IF 2) (VL-REMOVE-IF-NOT 2) (VL-STRING-ELT 2) (VL-POSITION 2) (VL-FILE-SYSTIME 1) (VL-NANP 1) (VL-INFP 1) (VLISP-FASRES-UPDATE 2 3) (VLISP-INIRES-UPDATE 2)))
(00000094 8 2		UnVar2)
(00000096 3 87 0		*al-spec-form-descr-ht*)
(00000099 5 0		UnVar0)
(0000009B 53 2 95 0 1 32		descr-ht-fill)
(000000A1 10)
(000000A2 3 88 0		*al-sys-fun-descr-ht*)
(000000A5 5 1		UnVar1)
(000000A7 53 2 95 0 1 32		descr-ht-fill)
(000000AD 10)
(000000AE 3 88 0		*al-sys-fun-descr-ht*)
(000000B1 5 2		UnVar2)
(000000B3 53 2 95 0 1 32		descr-ht-fill)
(000000B9 10)
(000000BA 9 152 0		'al-form-descr?)
(000000BD 26 83 0		al-form-descr?)
(000000C0 9 83 0		'al-form-descr?)
(000000C3 10)
(000000C4 9 151 0		'al-spec-form-descr?)
(000000C7 26 82 0		al-spec-form-descr?)
(000000CA 9 82 0		'al-spec-form-descr?)
(000000CD 10)
(000000CE 9 150 0		'al-sys-fun-descr?)
(000000D1 26 81 0		al-sys-fun-descr?)
(000000D4 9 81 0		'al-sys-fun-descr?)
(000000D7 10)
(000000D8 9 149 0		'al-not-fit-p)
(000000DB 26 80 0		al-not-fit-p)
(000000DE 9 80 0		'al-not-fit-p)
(000000E1 28		[ret])
(000000E2 20 0 0 0 0)
(000000E7 1		nil)
(000000E8 10)
(000000E9 1		nil)
(000000EA 10)
(000000EB 1		nil)
(000000EC 10)
(000000ED 1		nil)
(000000EE 28		[ret])
(000000EF 20 0 0 0 0)
(000000F4 1		nil)
(000000F5 10)
(000000F6 1		nil)
(000000F7 10)
(000000F8 1		nil)
(000000F9 10)
(000000FA 1		nil)
(000000FB 10)
(000000FC 12 148 0		'make-fly-err-hook-fn)
(000000FF 26 79 0		make-fly-err-hook-fn)
(00000102 9 79 0		'make-fly-err-hook-fn)
(00000105 10)
(00000106 1		nil)
(00000107 10)
(00000108 1		nil)
(00000109 10)
(0000010A 1		nil)
(0000010B 28		[ret])
(0000010C 20 0 0 0 0)
(00000111 1		nil)
(00000112 10)
(00000113 1		nil)
(00000114 10)
(00000115 1		nil)
(00000116 27 78 0		*syntax-error-break*)
(00000119 9 78 0		'*syntax-error-break*)
(0000011C 10)
(0000011D 1		nil)
(0000011E 27 77 0		*check-warning*)
(00000121 9 77 0		'*check-warning*)
(00000124 10)
(00000125 1		nil)
(00000126 10)
(00000127 1		nil)
(00000128 10)
(00000129 1		nil)
(0000012A 10)
(0000012B 1		nil)
(0000012C 10)
(0000012D 1		nil)
(0000012E 28		[ret])
(0000012F 20 0 0 0 0)
(00000134 1		nil)
(00000135 10)
(00000136 1		nil)
(00000137 27 76 0		*read-eval-from-string*)
(0000013A 9 76 0		'*read-eval-from-string*)
(0000013D 10)
(0000013E 1		nil)
(0000013F 27 75 0		*run-time-evaluation*)
(00000142 9 75 0		'*run-time-evaluation*)
(00000145 10)
(00000146 3 78 0		*syntax-error-break*)
(00000149 27 78 0		*syntax-error-break*)
(0000014C 9 78 0		'*syntax-error-break*)
(0000014F 10)
(00000150 3 74 0		*comp-S-expr*)
(00000153 27 74 0		*comp-S-expr*)
(00000156 9 74 0		'*comp-S-expr*)
(00000159 10)
(0000015A 3 73 0		*in-proc-body*)
(0000015D 27 73 0		*in-proc-body*)
(00000160 9 73 0		'*in-proc-body*)
(00000163 10)
(00000164 3 72 0		*bind-list*)
(00000167 27 72 0		*bind-list*)
(0000016A 9 72 0		'*bind-list*)
(0000016D 10)
(0000016E 1		nil)
(0000016F 10)
(00000170 1		nil)
(00000171 10)
(00000172 1		nil)
(00000173 28		[ret])
(00000174 20 0 0 0 0)
(00000179 1		nil)
(0000017A 10)
(0000017B 1		nil)
(0000017C 10)
(0000017D 9 147 0		'AL-symbol)
(00000180 26 71 0		AL-symbol)
(00000183 9 71 0		'AL-symbol)
(00000186 10)
(00000187 1		nil)
(00000188 10)
(00000189 3 70 0		*stream-link*)
(0000018C 27 70 0		*stream-link*)
(0000018F 9 70 0		'*stream-link*)
(00000192 10)
(00000193 3 69 0		*stream-not-link*)
(00000196 27 69 0		*stream-not-link*)
(00000199 9 69 0		'*stream-not-link*)
(0000019C 10)
(0000019D 3 68 0		*stream-local*)
(000001A0 27 68 0		*stream-local*)
(000001A3 9 68 0		'*stream-local*)
(000001A6 10)
(000001A7 3 67 0		*stream-not-local*)
(000001AA 27 67 0		*stream-not-local*)
(000001AD 9 67 0		'*stream-not-local*)
(000001B0 10)
(000001B1 50 0		0)
(000001B3 27 66 0		*pdb-error-list*)
(000001B6 9 66 0		'*pdb-error-list*)
(000001B9 10)
(000001BA 3 65 0		*integral-pdb-info*)
(000001BD 27 65 0		*integral-pdb-info*)
(000001C0 9 65 0		'*integral-pdb-info*)
(000001C3 10)
(000001C4 3 64 0		*top-call-by-name*)
(000001C7 27 64 0		*top-call-by-name*)
(000001CA 9 64 0		'*top-call-by-name*)
(000001CD 10)
(000001CE 3 63 0		*top-bind-param*)
(000001D1 27 63 0		*top-bind-param*)
(000001D4 9 63 0		'*top-bind-param*)
(000001D7 10)
(000001D8 3 62 0		*top-bind-aux*)
(000001DB 27 62 0		*top-bind-aux*)
(000001DE 9 62 0		'*top-bind-aux*)
(000001E1 10)
(000001E2 3 61 0		*top-def-arg-num*)
(000001E5 27 61 0		*top-def-arg-num*)
(000001E8 9 61 0		'*top-def-arg-num*)
(000001EB 10)
(000001EC 3 60 0		*top-assign*)
(000001EF 27 60 0		*top-assign*)
(000001F2 9 60 0		'*top-assign*)
(000001F5 10)
(000001F6 3 59 0		*top-val-ref*)
(000001F9 27 59 0		*top-val-ref*)
(000001FC 9 59 0		'*top-val-ref*)
(000001FF 10)
(00000200 3 58 0		*top-quoted-sym*)
(00000203 27 58 0		*top-quoted-sym*)
(00000206 9 58 0		'*top-quoted-sym*)
(00000209 10)
(0000020A 3 57 0		*top-non-loc-assign*)
(0000020D 27 57 0		*top-non-loc-assign*)
(00000210 9 57 0		'*top-non-loc-assign*)
(00000213 10)
(00000214 3 56 0		*top-non-loc-val-ref*)
(00000217 27 56 0		*top-non-loc-val-ref*)
(0000021A 9 56 0		'*top-non-loc-val-ref*)
(0000021D 10)
(0000021E 3 55 0		*top-fcall-num*)
(00000221 27 55 0		*top-fcall-num*)
(00000224 9 55 0		'*top-fcall-num*)
(00000227 10)
(00000228 1		nil)
(00000229 10)
(0000022A 1		nil)
(0000022B 10)
(0000022C 1		nil)
(0000022D 10)
(0000022E 1		nil)
(0000022F 10)
(00000230 1		nil)
(00000231 10)
(00000232 1		nil)
(00000233 10)
(00000234 1		nil)
(00000235 10)
(00000236 1		nil)
(00000237 10)
(00000238 1		nil)
(00000239 10)
(0000023A 1		nil)
(0000023B 10)
(0000023C 1		nil)
(0000023D 10)
(0000023E 1		nil)
(0000023F 10)
(00000240 1		nil)
(00000241 10)
(00000242 1		nil)
(00000243 10)
(00000244 1		nil)
(00000245 10)
(00000246 1		nil)
(00000247 10)
(00000248 1		nil)
(00000249 10)
(0000024A 1		nil)
(0000024B 10)
(0000024C 1		nil)
(0000024D 10)
(0000024E 1		nil)
(0000024F 10)
(00000250 1		nil)
(00000251 10)
(00000252 1		nil)
(00000253 10)
(00000254 1		nil)
(00000255 10)
(00000256 1		nil)
(00000257 10)
(00000258 1		nil)
(00000259 10)
(0000025A 1		nil)
(0000025B 10)
(0000025C 1		nil)
(0000025D 10)
(0000025E 1		nil)
(0000025F 10)
(00000260 1		nil)
(00000261 10)
(00000262 1		nil)
(00000263 10)
(00000264 1		nil)
(00000265 10)
(00000266 1		nil)
(00000267 10)
(00000268 1		nil)
(00000269 10)
(0000026A 1		nil)
(0000026B 10)
(0000026C 1		nil)
(0000026D 10)
(0000026E 1		nil)
(0000026F 10)
(00000270 1		nil)
(00000271 10)
(00000272 1		nil)
(00000273 10)
(00000274 1		nil)
(00000275 10)
(00000276 1		nil)
(00000277 28		[ret])
(00000278 20 0 0 0 0)
(0000027D 1		nil)
(0000027E 10)
(0000027F 1		nil)
(00000280 10)
(00000281 12 146 0		'read-top-with-pos)
(00000284 26 54 0		read-top-with-pos)
(00000287 9 54 0		'read-top-with-pos)
(0000028A 28		[ret])
(0000028B 20 0 0 0 0)
(00000290 1		nil)
(00000291 10)
(00000292 1		nil)
(00000293 10)
(00000294 12 145 0		'collect-top)
(00000297 26 53 0		collect-top)
(0000029A 9 53 0		'collect-top)
(0000029D 10)
(0000029E 1		nil)
(0000029F 10)
(000002A0 1		nil)
(000002A1 10)
(000002A2 1		nil)
(000002A3 10)
(000002A4 1		nil)
(000002A5 10)
(000002A6 1		nil)
(000002A7 10)
(000002A8 1		nil)
(000002A9 10)
(000002AA 1		nil)
(000002AB 10)
(000002AC 1		nil)
(000002AD 10)
(000002AE 1		nil)
(000002AF 10)
(000002B0 1		nil)
(000002B1 10)
(000002B2 1		nil)
(000002B3 10)
(000002B4 1		nil)
(000002B5 10)
(000002B6 1		nil)
(000002B7 10)
(000002B8 12 144 0		'acheck-eval-spec-string/err-hk)
(000002BB 26 52 0		acheck-eval-spec-string/err-hk)
(000002BE 9 52 0		'acheck-eval-spec-string/err-hk)
(000002C1 10)
(000002C2 1		nil)
(000002C3 10)
(000002C4 1		nil)
(000002C5 10)
(000002C6 12 143 0		'read-from-spec-string)
(000002C9 26 51 0		read-from-spec-string)
(000002CC 9 51 0		'read-from-spec-string)
(000002CF 10)
(000002D0 1		nil)
(000002D1 10)
(000002D2 1		nil)
(000002D3 10)
(000002D4 1		nil)
(000002D5 10)
(000002D6 1		nil)
(000002D7 10)
(000002D8 1		nil)
(000002D9 10)
(000002DA 1		nil)
(000002DB 10)
(000002DC 1		nil)
(000002DD 10)
(000002DE 1		nil)
(000002DF 10)
(000002E0 1		nil)
(000002E1 10)
(000002E2 1		nil)
(000002E3 10)
(000002E4 1		nil)
(000002E5 10)
(000002E6 1		nil)
(000002E7 10)
(000002E8 1		nil)
(000002E9 10)
(000002EA 1		nil)
(000002EB 10)
(000002EC 1		nil)
(000002ED 10)
(000002EE 1		nil)
(000002EF 10)
(000002F0 1		nil)
(000002F1 10)
(000002F2 1		nil)
(000002F3 28		[ret])
(000002F4 20 0 0 0 0)
(000002F9 1		nil)
(000002FA 10)
(000002FB 1		nil)
(000002FC 10)
(000002FD 3 50 0		*decl-link*)
(00000300 27 50 0		*decl-link*)
(00000303 9 50 0		'*decl-link*)
(00000306 10)
(00000307 3 49 0		*decl-not-link*)
(0000030A 27 49 0		*decl-not-link*)
(0000030D 9 49 0		'*decl-not-link*)
(00000310 10)
(00000311 3 48 0		*decl-local*)
(00000314 27 48 0		*decl-local*)
(00000317 9 48 0		'*decl-local*)
(0000031A 10)
(0000031B 3 47 0		*decl-not-local*)
(0000031E 27 47 0		*decl-not-local*)
(00000321 9 47 0		'*decl-not-local*)
(00000324 10)
(00000325 3 46 0		*decl-drop*)
(00000328 27 46 0		*decl-drop*)
(0000032B 9 46 0		'*decl-drop*)
(0000032E 10)
(0000032F 3 45 0		*decl-not-drop*)
(00000332 27 45 0		*decl-not-drop*)
(00000335 9 45 0		'*decl-not-drop*)
(00000338 10)
(00000339 3 44 0		*decl-export-to-acad-prefixs*)
(0000033C 27 44 0		*decl-export-to-acad-prefixs*)
(0000033F 9 44 0		'*decl-export-to-acad-prefixs*)
(00000342 10)
(00000343 1		nil)
(00000344 10)
(00000345 1		nil)
(00000346 10)
(00000347 1		nil)
(00000348 10)
(00000349 1		nil)
(0000034A 10)
(0000034B 1		nil)
(0000034C 10)
(0000034D 1		nil)
(0000034E 10)
(0000034F 1		nil)
(00000350 10)
(00000351 1		nil)
(00000352 10)
(00000353 1		nil)
(00000354 10)
(00000355 1		nil)
(00000356 10)
(00000357 1		nil)
(00000358 10)
(00000359 1		nil)
(0000035A 10)
(0000035B 1		nil)
(0000035C 10)
(0000035D 1		nil)
(0000035E 10)
(0000035F 1		nil)
(00000360 10)
(00000361 1		nil)
(00000362 10)
(00000363 1		nil)
(00000364 10)
(00000365 1		nil)
(00000366 10)
(00000367 1		nil)
(00000368 10)
(00000369 1		nil)
(0000036A 10)
(0000036B 1		nil)
(0000036C 10)
(0000036D 12 142 0		'global-decl-stream)
(00000370 26 43 0		global-decl-stream)
(00000373 9 43 0		'global-decl-stream)
(00000376 10)
(00000377 1		nil)
(00000378 10)
(00000379 1		nil)
(0000037A 10)
(0000037B 9 141 0		'decl-inp-stream:val)
(0000037E 26 42 0		decl-inp-stream:val)
(00000381 9 42 0		'decl-inp-stream:val)
(00000384 10)
(00000385 9 140 0		'decl-error:val)
(00000388 26 41 0		decl-error:val)
(0000038B 9 41 0		'decl-error:val)
(0000038E 10)
(0000038F 9 139 0		'decl-link:val)
(00000392 26 40 0		decl-link:val)
(00000395 9 40 0		'decl-link:val)
(00000398 10)
(00000399 9 138 0		'decl-not-link:val)
(0000039C 26 39 0		decl-not-link:val)
(0000039F 9 39 0		'decl-not-link:val)
(000003A2 10)
(000003A3 9 137 0		'decl-local:val)
(000003A6 26 38 0		decl-local:val)
(000003A9 9 38 0		'decl-local:val)
(000003AC 10)
(000003AD 9 136 0		'decl-not-local:val)
(000003B0 26 37 0		decl-not-local:val)
(000003B3 9 37 0		'decl-not-local:val)
(000003B6 10)
(000003B7 9 135 0		'decl-drop:val)
(000003BA 26 36 0		decl-drop:val)
(000003BD 9 36 0		'decl-drop:val)
(000003C0 10)
(000003C1 9 134 0		'decl-not-drop:val)
(000003C4 26 35 0		decl-not-drop:val)
(000003C7 9 35 0		'decl-not-drop:val)
(000003CA 10)
(000003CB 9 133 0		'decl-export-to-acad-prefixs:val)
(000003CE 26 34 0		decl-export-to-acad-prefixs:val)
(000003D1 9 34 0		'decl-export-to-acad-prefixs:val)
(000003D4 10)
(000003D5 9 132 0		'decl-has-errors-p)
(000003D8 26 33 0		decl-has-errors-p)
(000003DB 9 33 0		'decl-has-errors-p)
(000003DE 10)
(000003DF 12 131 0		'collect-decl)
(000003E2 26 32 0		collect-decl)
(000003E5 9 32 0		'collect-decl)
(000003E8 28		[ret])
(000003E9 20 0 0 0 0)
(000003EE 1		nil)
(000003EF 10)
(000003F0 1		nil)
(000003F1 10)
(000003F2 1		nil)
(000003F3 10)
(000003F4 9 130 0		'loc-pdb-stream)
(000003F7 26 31 0		loc-pdb-stream)
(000003FA 9 31 0		'loc-pdb-stream)
(000003FD 10)
(000003FE 9 129 0		'check-pdb-stream)
(00000401 26 30 0		check-pdb-stream)
(00000404 9 30 0		'check-pdb-stream)
(00000407 10)
(00000408 12 128 0		'collect-stream-pdb)
(0000040B 26 29 0		collect-stream-pdb)
(0000040E 9 29 0		'collect-stream-pdb)
(00000411 28		[ret])
(00000412 20 0 0 0 0)
(00000417 1		nil)
(00000418 10)
(00000419 1		nil)
(0000041A 10)
(0000041B 1		nil)
(0000041C 10)
(0000041D 1		nil)
(0000041E 10)
(0000041F 9 127 0		'sym-list-sort)
(00000422 26 28 0		sym-list-sort)
(00000425 9 28 0		'sym-list-sort)
(00000428 10)
(00000429 1		nil)
(0000042A 10)
(0000042B 1		nil)
(0000042C 28		[ret])
(0000042D 20 0 0 0 0)
(00000432 1		nil)
(00000433 10)
(00000434 1		nil)
(00000435 10)
(00000436 1		nil)
(00000437 10)
(00000438 9 126 0		'acheck-fly)
(0000043B 26 27 0		acheck-fly)
(0000043E 9 27 0		'acheck-fly)
(00000441 28		[ret])
(00000442 20 0 0 0 0)
(00000447 1		nil)
(00000448 10)
(00000449 1		nil)
(0000044A 10)
(0000044B 9 125 0		'lpdb-strm)
(0000044E 26 26 0		lpdb-strm)
(00000451 9 26 0		'lpdb-strm)
(00000454 10)
(00000455 9 124 0		'lpdb-err)
(00000458 26 25 0		lpdb-err)
(0000045B 9 25 0		'lpdb-err)
(0000045E 10)
(0000045F 9 123 0		'lpdb-inf)
(00000462 26 24 0		lpdb-inf)
(00000465 9 24 0		'lpdb-inf)
(00000468 10)
(00000469 9 122 0		'lpdb-top-pos-inf)
(0000046C 26 23 0		lpdb-top-pos-inf)
(0000046F 9 23 0		'lpdb-top-pos-inf)
(00000472 10)
(00000473 9 121 0		'lpdb-top-fcall-num-inf)
(00000476 26 22 0		lpdb-top-fcall-num-inf)
(00000479 9 22 0		'lpdb-top-fcall-num-inf)
(0000047C 10)
(0000047D 9 120 0		'lpdb-top-call-by-name-inf)
(00000480 26 21 0		lpdb-top-call-by-name-inf)
(00000483 9 21 0		'lpdb-top-call-by-name-inf)
(00000486 10)
(00000487 9 119 0		'lpdb-top-non-loc-val-ref-inf)
(0000048A 26 20 0		lpdb-top-non-loc-val-ref-inf)
(0000048D 9 20 0		'lpdb-top-non-loc-val-ref-inf)
(00000490 10)
(00000491 9 118 0		'lpdb-top-non-loc-assign-inf)
(00000494 26 19 0		lpdb-top-non-loc-assign-inf)
(00000497 9 19 0		'lpdb-top-non-loc-assign-inf)
(0000049A 10)
(0000049B 9 117 0		'lpdb-top-quoted-sym-inf)
(0000049E 26 18 0		lpdb-top-quoted-sym-inf)
(000004A1 9 18 0		'lpdb-top-quoted-sym-inf)
(000004A4 10)
(000004A5 9 116 0		'lpdb-top-val-ref-inf)
(000004A8 26 17 0		lpdb-top-val-ref-inf)
(000004AB 9 17 0		'lpdb-top-val-ref-inf)
(000004AE 10)
(000004AF 9 115 0		'lpdb-top-assign-inf)
(000004B2 26 16 0		lpdb-top-assign-inf)
(000004B5 9 16 0		'lpdb-top-assign-inf)
(000004B8 10)
(000004B9 9 114 0		'lpdb-top-def-arg-num-inf)
(000004BC 26 15 0		lpdb-top-def-arg-num-inf)
(000004BF 9 15 0		'lpdb-top-def-arg-num-inf)
(000004C2 10)
(000004C3 9 113 0		'lpdb-top-bind-param-inf)
(000004C6 26 14 0		lpdb-top-bind-param-inf)
(000004C9 9 14 0		'lpdb-top-bind-param-inf)
(000004CC 10)
(000004CD 9 112 0		'lpdb-top-bind-aux-inf)
(000004D0 26 13 0		lpdb-top-bind-aux-inf)
(000004D3 9 13 0		'lpdb-top-bind-aux-inf)
(000004D6 10)
(000004D7 9 111 0		'lpdb-top-link-inf)
(000004DA 26 12 0		lpdb-top-link-inf)
(000004DD 9 12 0		'lpdb-top-link-inf)
(000004E0 10)
(000004E1 9 110 0		'lpdb-top-not-link-inf)
(000004E4 26 11 0		lpdb-top-not-link-inf)
(000004E7 9 11 0		'lpdb-top-not-link-inf)
(000004EA 10)
(000004EB 9 109 0		'lpdb-top-local-inf)
(000004EE 26 10 0		lpdb-top-local-inf)
(000004F1 9 10 0		'lpdb-top-local-inf)
(000004F4 10)
(000004F5 9 108 0		'lpdb-top-not-local-inf)
(000004F8 26 9 0		lpdb-top-not-local-inf)
(000004FB 9 9 0		'lpdb-top-not-local-inf)
(000004FE 10)
(000004FF 9 107 0		'lpdb-has-errors-p)
(00000502 26 8 0		lpdb-has-errors-p)
(00000505 9 8 0		'lpdb-has-errors-p)
(00000508 10)
(00000509 9 106 0		'lpdb-p)
(0000050C 26 7 0		lpdb-p)
(0000050F 9 7 0		'lpdb-p)
(00000512 28		[ret])
(00000513 20 0 0 0 0)
(00000518 1		nil)
(00000519 10)
(0000051A 1		nil)
(0000051B 10)
(0000051C 9 6 0		'LPDB-AL-TREE)
(0000051F 26 5 0		*lpdb-mark*)
(00000522 9 5 0		'*lpdb-mark*)
(00000525 10)
(00000526 12 105 0		'lpdb-save)
(00000529 26 4 0		lpdb-save)
(0000052C 9 4 0		'lpdb-save)
(0000052F 10)
(00000530 12 104 0		'load-lpdb)
(00000533 26 3 0		load-lpdb)
(00000536 9 3 0		'load-lpdb)
(00000539 28		[ret])
(0000053A 20 0 0 0 0)
(0000053F 1		nil)
(00000540 10)
(00000541 1		nil)
(00000542 10)
(00000543 9 103 0		'al-tree-dump)
(00000546 26 2 0		al-tree-dump)
(00000549 9 2 0		'al-tree-dump)
(0000054C 10)
(0000054D 12 102 0		'al-tree-restore)
(00000550 26 1 0		al-tree-restore)
(00000553 9 1 0		'al-tree-restore)
(00000556 10)
(00000557 1		nil)
(00000558 10)
(00000559 1		nil)
(0000055A 10)
(0000055B 1		nil)
(0000055C 22		ret)
