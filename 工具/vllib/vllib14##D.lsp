;;;==========SubFunction==========
;;;def c-save 1
(00000001 20 4 1 2 0)
(00000006 100 2		UNVar2)
(00000008 5 0		UnVar0)
(0000000A 81 1 135 3 1 0		TWinp)
(00000010 60 12 0		T->JMP 0000001F)
(00000013 9 134 3		'c-save)
(00000016 5 0		UnVar0)
(00000018 81 2 133 3 1 0		no-applicable-method)
(0000001E 10)
(0000001F 5 0		UnVar0)
(00000021 53 1 132 3 1 32		list-attributes)
(00000027 8 2		UnVar2)
(00000029 5 2		UnVar2)
(0000002B 61 22 0		nil->JMP 00000044)
(0000002E 5 0		UnVar0)
(00000030 81 1 131 3 1 0		terminalp)
(00000036 14 11 0		T->JMP 00000044)
(00000039 5 2		UnVar2)
(0000003B 9 130 3		':FILENAME)
(0000003E 81 2 129 3 1 0		getf)
(00000044 63		nil->ret)
(00000045 9 128 3		"(")
(00000048 5 1		UnVar1)
(0000004A 81 2 127 3 1 0		princ)
(00000050 10)
(00000051 5 0		UnVar0)
(00000053 81 1 126 3 1 0		type-of)
(00000059 5 1		UnVar1)
(0000005B 81 2 127 3 1 0		princ)
(00000061 10)
(00000062 5 1		UnVar1)
(00000064 81 1 125 3 1 0		terpri)
(0000006A 10)
(0000006B 15 73 0		JMP 000000B7)
(0000006E 50 9		9)
(00000070 5 1		UnVar1)
(00000072 81 2 124 3 1 0		write-byte)
(00000078 10)
(00000079 5 2		UnVar2)
(0000007B 40		car)
(0000007C 8 3		UnVar3)
(0000007E 5 2		UnVar2)
(00000080 41		cdr)
(00000081 8 2		UnVar2)
(00000083 5 3		UnVar3)
(00000085 5 1		UnVar1)
(00000087 81 2 123 3 1 0		prin1)
(0000008D 10)
(0000008E 50 32		32)
(00000090 5 1		UnVar1)
(00000092 81 2 124 3 1 0		write-byte)
(00000098 10)
(00000099 5 2		UnVar2)
(0000009B 40		car)
(0000009C 8 3		UnVar3)
(0000009E 5 2		UnVar2)
(000000A0 41		cdr)
(000000A1 8 2		UnVar2)
(000000A3 5 3		UnVar3)
(000000A5 5 1		UnVar1)
(000000A7 81 2 123 3 1 0		prin1)
(000000AD 10)
(000000AE 5 1		UnVar1)
(000000B0 81 1 125 3 1 0		terpri)
(000000B6 10)
(000000B7 5 2		UnVar2)
(000000B9 60 178 255		T->JMP 0000006E)
(000000BC 9 122 3		"\t)")
(000000BF 5 1		UnVar1)
(000000C1 81 2 121 3 1 0		write-line)
(000000C7 22		ret)
;;;def c-restore 200
(000000C8 21 5 1 1 0)
(000000CD 100 1		UNVar1)
(000000CF 100 2		UNVar2)
(000000D1 9 120 3		':LPP)
(000000D4 81 1 119 3 1 0		_in-package)
(000000DA 8 3		UnVar3)
(000000DC 15 15 0		JMP 000000EE)
(000000DF 20 0 0 0 0)
(000000E4 4 1 3		UpVar1-3)
(000000E7 81 1 119 3 1 0		_in-package)
(000000ED 22		ret)
(000000EE 12 205 3		'(223 -unwind-cleanup-))
(000000F1 15 22 0		JMP 0000010A)
(000000F4 20 0 0 0 0)
(000000F9 4 1 0		UpVar1-0)
(000000FC 1		nil)
(000000FD 2		T)
(000000FE 1		nil)
(000000FF 81 4 118 3 1 0		read)
(00000105 11)
(00000106 7 1 1		UpVar1-1)
(00000109 22		ret)
(0000010A 12 204 3		'(244 -unwind-protect-))
(0000010D 1		nil)
(0000010E 81 3 117 3 1 0		_unwinded-apply)
(00000114 10)
(00000115 5 1		UnVar1)
(00000117 37 2		consp)
(00000119 61 3 0		nil->JMP 0000011F)
(0000011C 5 1		UnVar1)
(0000011E 40		car)
(0000011F 8 2		UnVar2)
(00000121 5 2		UnVar2)
(00000123 8 4		UnVar4)
(00000125 5 4		UnVar4)
(00000127 9 116 3		'editor)
(0000012A 38		=)
(0000012B 13 11 0		nil->JMP 00000139)
(0000012E 5 1		UnVar1)
(00000130 95 1 175 1 0 0		restore-editor)
(00000136 10)
(00000137 2		T)
(00000138 22		ret)
(00000139 5 4		UnVar4)
(0000013B 9 115 3		'(terminal console))
(0000013E 81 2 114 3 1 0		memq)
(00000144 13 11 0		nil->JMP 00000152)
(00000147 5 1		UnVar1)
(00000149 53 1 113 3 1 32		restore-term/con)
(0000014F 10)
(00000150 2		T)
(00000151 22		ret)
(00000152 5 4		UnVar4)
(00000154 9 112 3		':AL)
(00000157 38		=)
(00000158 13 11 0		nil->JMP 00000166)
(0000015B 5 1		UnVar1)
(0000015D 95 1 247 9 0 0		restore-desktop-options)
(00000163 10)
(00000164 2		T)
(00000165 22		ret)
(00000166 5 4		UnVar4)
(00000168 9 120 3		':LPP)
(0000016B 38		=)
(0000016C 13 30 0		nil->JMP 0000018D)
(0000016F 53 0 111 3 1 32		alesmaint?)
(00000175 13 11 0		nil->JMP 00000183)
(00000178 5 1		UnVar1)
(0000017A 95 1 247 9 0 0		restore-desktop-options)
(00000180 10)
(00000181 2		T)
(00000182 22		ret)
(00000183 9 110 3		"extra options ignored in desktop file;")
(00000186 81 1 109 3 1 0		_msg-err)
(0000018C 22		ret)
(0000018D 5 0		UnVar0)
(0000018F 81 1 108 3 1 0		eof-streamp)
(00000195 60 21 0		T->JMP 000001AD)
(00000198 9 107 3		"VLMSG.DLL")
(0000019B 51 122 83 0 0		21370)
(000001A0 81 2 106 3 1 0		string-resource)
(000001A6 81 1 109 3 1 0		_msg-err)
(000001AC 10)
(000001AD 1		nil)
(000001AE 22		ret)
;;;def restore-editor 431
(000001AF 20 3 1 1 0)
(000001B4 5 0		UnVar0)
(000001B6 41		cdr)
(000001B7 9 130 3		':FILENAME)
(000001BA 81 2 129 3 1 0		getf)
(000001C0 8 1		UnVar1)
(000001C2 5 1		UnVar1)
(000001C4 61 8 0		nil->JMP 000001CF)
(000001C7 5 1		UnVar1)
(000001C9 53 1 105 3 1 32		find-opened-editor)
(000001CF 8 2		UnVar2)
(000001D1 5 2		UnVar2)
(000001D3 13 48 0		nil->JMP 00000206)
(000001D6 5 2		UnVar2)
(000001D8 5 0		UnVar0)
(000001DA 41		cdr)
(000001DB 53 2 104 3 1 32		twin.update-attributes)
(000001E1 10)
(000001E2 5 2		UnVar2)
(000001E4 53 1 103 3 1 32		host-spouse-exists-p)
(000001EA 13 13 0		nil->JMP 000001FA)
(000001ED 5 2		UnVar2)
(000001EF 1		nil)
(000001F0 53 2 102 3 1 32		update-host-spouse)
(000001F6 10)
(000001F7 15 9 0		JMP 00000203)
(000001FA 5 2		UnVar2)
(000001FC 53 1 101 3 1 32		create-host-spouse)
(00000202 10)
(00000203 15 49 0		JMP 00000237)
(00000206 5 1		UnVar1)
(00000208 81 1 100 3 1 0		file-readable-p)
(0000020E 13 12 0		nil->JMP 0000021D)
(00000211 5 0		UnVar0)
(00000213 53 1 99 3 1 32		editor.desktop-restore)
(00000219 10)
(0000021A 15 26 0		JMP 00000237)
(0000021D 3 98 3		*trace-output*)
(00000220 9 107 3		"VLMSG.DLL")
(00000223 51 132 83 0 0		21380)
(00000228 81 2 106 3 1 0		string-resource)
(0000022E 5 1		UnVar1)
(00000230 53 3 97 3 1 32		prinf)
(00000236 10)
(00000237 5 2		UnVar2)
(00000239 22		ret)
;;;def clear-desktop 570
(0000023A 21 1 1 1 0)
(0000023F 9 96 3		'clear-abort)
(00000242 57 1 0		list)
(00000245 15 101 1		JMP 000003AD)
(00000248 20 3 0 0 0)
(0000024D 53 0 95 3 1 32		list-true-dialogs-with-host-spouse)
(00000253 8 0		UnVar0)
(00000255 15 15 0		JMP 00000267)
(00000258 5 0		UnVar0)
(0000025A 40		car)
(0000025B 53 1 94 3 1 32		destroy-host-spouse)
(00000261 10)
(00000262 5 0		UnVar0)
(00000264 41		cdr)
(00000265 8 0		UnVar0)
(00000267 5 0		UnVar0)
(00000269 60 236 255		T->JMP 00000258)
(0000026C 81 0 93 3 1 0		list-mdiwindows-with-host-spouse)
(00000272 8 0		UnVar0)
(00000274 100 1		UNVar1)
(00000276 15 45 1		JMP 000003A6)
(00000279 5 0		UnVar0)
(0000027B 40		car)
(0000027C 8 1		UnVar1)
(0000027E 5 0		UnVar0)
(00000280 41		cdr)
(00000281 8 0		UnVar0)
(00000283 5 1		UnVar1)
(00000285 3 92 3		*console*)
(00000288 38		=)
(00000289 13 4 0		nil->JMP 00000290)
(0000028C 1		nil)
(0000028D 15 17 0		JMP 000002A1)
(00000290 5 1		UnVar1)
(00000292 81 1 126 3 1 0		type-of)
(00000298 4 1 0		UpVar1-0)
(0000029B 81 2 114 3 1 0		memq)
(000002A1 13 2 1		nil->JMP 000003A6)
(000002A4 5 1		UnVar1)
(000002A6 53 1 91 3 1 32		editorp)
(000002AC 61 8 0		nil->JMP 000002B7)
(000002AF 5 1		UnVar1)
(000002B1 53 1 90 3 1 32		needs-save-p)
(000002B7 13 213 0		nil->JMP 0000038F)
(000002BA 5 1		UnVar1)
(000002BC 53 1 89 3 1 32		mdiwindow-show-up)
(000002C2 10)
(000002C3 3 88 3		*yes-no-cancel-alert*)
(000002C6 9 107 3		"VLMSG.DLL")
(000002C9 51 142 83 0 0		21390)
(000002CE 81 2 106 3 1 0		string-resource)
(000002D4 5 1		UnVar1)
(000002D6 9 87 3		'caption)
(000002D9 81 2 86 3 1 0		slot-value)
(000002DF 53 3 85 3 1 32		alert)
(000002E5 8 2		UnVar2)
(000002E7 5 2		UnVar2)
(000002E9 9 84 3		':YES)
(000002EC 38		=)
(000002ED 13 12 0		nil->JMP 000002FC)
(000002F0 5 1		UnVar1)
(000002F2 53 1 83 3 1 32		save!)
(000002F8 10)
(000002F9 15 147 0		JMP 0000038F)
(000002FC 5 2		UnVar2)
(000002FE 9 82 3		':NO)
(00000301 38		=)
(00000302 13 115 0		nil->JMP 00000378)
(00000305 5 1		UnVar1)
(00000307 9 81 3		'is-loaded)
(0000030A 81 2 86 3 1 0		slot-value)
(00000310 13 5 0		nil->JMP 00000318)
(00000313 100 1		UNVar1)
(00000315 15 93 0		JMP 00000375)
(00000318 5 1		UnVar1)
(0000031A 50 0		0)
(0000031C 9 107 3		"VLMSG.DLL")
(0000031F 51 152 83 0 0		21400)
(00000324 81 2 106 3 1 0		string-resource)
(0000032A 81 3 80 3 1 0		TBuf.insert)
(00000330 10)
(00000331 5 1		UnVar1)
(00000333 1		nil)
(00000334 9 79 3		'filename)
(00000337 81 3 78 3 1 0		slot-value<-)
(0000033D 10)
(0000033E 5 1		UnVar1)
(00000340 9 77 3		"*** ")
(00000343 5 1		UnVar1)
(00000345 9 87 3		'caption)
(00000348 81 2 86 3 1 0		slot-value)
(0000034E 9 76 3		" ***")
(00000351 81 3 75 3 1 0		concat)
(00000357 9 87 3		'caption)
(0000035A 81 3 78 3 1 0		slot-value<-)
(00000360 10)
(00000361 5 1		UnVar1)
(00000363 2		T)
(00000364 53 2 74 3 1 32		tbuf.read-only<-)
(0000036A 10)
(0000036B 5 1		UnVar1)
(0000036D 1		nil)
(0000036E 81 2 73 3 1 0		TBuf.set-mod-tick)
(00000374 10)
(00000375 15 23 0		JMP 0000038F)
(00000378 5 2		UnVar2)
(0000037A 9 72 3		':CANCEL)
(0000037D 38		=)
(0000037E 13 14 0		nil->JMP 0000038F)
(00000381 9 96 3		'clear-abort)
(00000384 1		nil)
(00000385 81 2 71 3 1 0		throw)
(0000038B 10)
(0000038C 15 0 0		JMP 0000038F)
(0000038F 5 1		UnVar1)
(00000391 13 18 0		nil->JMP 000003A6)
(00000394 5 1		UnVar1)
(00000396 53 1 94 3 1 32		destroy-host-spouse)
(0000039C 10)
(0000039D 5 1		UnVar1)
(0000039F 53 1 70 3 1 32		gc-unprotect-term/con)
(000003A5 10)
(000003A6 5 0		UnVar0)
(000003A8 60 206 254		T->JMP 00000279)
(000003AB 1		nil)
(000003AC 22		ret)
(000003AD 12 203 3		'(584 -catch-))
(000003B0 1		nil)
(000003B1 81 3 69 3 1 0		_catched-apply)
(000003B7 10)
(000003B8 1		nil)
(000003B9 47 1 68 3 32 32		_purge-*editors*)
;;;def sv-dsk 959
(000003BF 21 3 1 1 0)
(000003C4 5 0		UnVar0)
(000003C6 3 67 3		*editor-backup-by-copy*)
(000003C9 53 2 66 3 1 32		file-backup)
(000003CF 10)
(000003D0 5 0		UnVar0)
(000003D2 9 65 3		':OUTPUT)
(000003D5 81 2 64 3 1 0		open)
(000003DB 8 1		UnVar1)
(000003DD 5 1		UnVar1)
(000003DF 8 2		UnVar2)
(000003E1 15 35 0		JMP 00000407)
(000003E4 20 0 0 0 0)
(000003E9 4 1 1		UpVar1-1)
(000003EC 81 1 63 3 1 0		streamp)
(000003F2 63		nil->ret)
(000003F3 4 1 1		UpVar1-1)
(000003F6 81 1 62 3 1 0		open-streamp)
(000003FC 63		nil->ret)
(000003FD 4 1 1		UpVar1-1)
(00000400 81 1 61 3 1 0		close)
(00000406 22		ret)
(00000407 12 202 3		'(996 -unwind-cleanup-))
(0000040A 15 107 0		JMP 00000478)
(0000040D 20 2 0 0 0)
(00000412 9 60 3		";# VLIDE desktop file [v.3]. DO NOT EDIT!!!")
(00000415 4 1 2		UpVar1-2)
(00000418 81 2 121 3 1 0		write-line)
(0000041E 10)
(0000041F 4 1 2		UpVar1-2)
(00000422 9 112 3		':AL)
(00000425 3 59 3		*ales-options-list*)
(00000428 95 3 76 9 0 0		store-desktop-options)
(0000042E 10)
(0000042F 53 0 111 3 1 32		alesmaint?)
(00000435 13 16 0		nil->JMP 00000448)
(00000438 4 1 2		UpVar1-2)
(0000043B 9 120 3		':LPP)
(0000043E 3 58 3		*lex-options-list*)
(00000441 95 3 76 9 0 0		store-desktop-options)
(00000447 10)
(00000448 3 57 3		*desktop-save-windows*)
(0000044B 13 40 0		nil->JMP 00000476)
(0000044E 81 0 93 3 1 0		list-mdiwindows-with-host-spouse)
(00000454 8 0		UnVar0)
(00000456 100 1		UNVar1)
(00000458 15 22 0		JMP 00000471)
(0000045B 5 0		UnVar0)
(0000045D 40		car)
(0000045E 8 1		UnVar1)
(00000460 5 0		UnVar0)
(00000462 41		cdr)
(00000463 8 0		UnVar0)
(00000465 5 1		UnVar1)
(00000467 4 1 2		UpVar1-2)
(0000046A 95 2 1 0 0 0		c-save)
(00000470 10)
(00000471 5 0		UnVar0)
(00000473 60 229 255		T->JMP 0000045B)
(00000476 2		T)
(00000477 22		ret)
(00000478 12 201 3		'(1037 -unwind-protect-))
(0000047B 1		nil)
(0000047C 81 3 117 3 1 0		_unwinded-apply)
(00000482 22		ret)
;;;def lpp-save-config 1155
(00000483 20 2 0 2 0)
(00000488 9 56 3		'_%sys-error-hook%)
(0000048B 15 25 0		JMP 000004A7)
(0000048E 20 1 1 1 0)
(00000493 53 0 111 3 1 32		alesmaint?)
(00000499 13 9 0		nil->JMP 000004A5)
(0000049C 5 0		UnVar0)
(0000049E 81 1 55 3 1 0		_sys-errout)
(000004A4 10)
(000004A5 1		nil)
(000004A6 22		ret)
(000004A7 9 200 3		'(1166 nil))
(000004AA 24 2 0)
(000004AD 1		nil)
(000004AE 9 54 3		'sv-dsk)
(000004B1 5 0		UnVar0)
(000004B3 14 24 0		T->JMP 000004CE)
(000004B6 5 1		UnVar1)
(000004B8 14 7 0		T->JMP 000004C2)
(000004BB 53 0 111 3 1 32		alesmaint?)
(000004C1 35		not)
(000004C2 13 6 0		nil->JMP 000004CB)
(000004C5 3 53 3		*default-desktop-file*)
(000004C8 15 3 0		JMP 000004CE)
(000004CB 9 52 3		"VLIDE.DSK")
(000004CE 57 1 0		list)
(000004D1 81 3 51 3 1 0		_protected-apply)
(000004D7 25 1 0)
(000004DA 22		ret)
;;;def lpp-restore-config 1243
(000004DB 21 2 0 1 0)
(000004E0 100 1		UNVar1)
(000004E2 9 56 3		'_%sys-error-hook%)
(000004E5 15 12 0		JMP 000004F4)
(000004E8 20 1 1 1 0)
(000004ED 5 0		UnVar0)
(000004EF 11)
(000004F0 7 1 1		UpVar1-1)
(000004F3 22		ret)
(000004F4 12 199 3		'(1256 nil))
(000004F7 9 50 3		'*error-trace-stack*)
(000004FA 53 0 111 3 1 32		alesmaint?)
(00000500 61 3 0		nil->JMP 00000506)
(00000503 3 50 3		*error-trace-stack*)
(00000506 24 4 0)
(00000509 5 0		UnVar0)
(0000050B 13 3 0		nil->JMP 00000511)
(0000050E 15 5 0		JMP 00000516)
(00000511 9 52 3		"VLIDE.DSK")
(00000514 8 0		UnVar0)
(00000516 5 0		UnVar0)
(00000518 53 0 111 3 1 32		alesmaint?)
(0000051E 13 15 0		nil->JMP 00000530)
(00000521 81 0 49 3 1 0		chdir)
(00000527 3 48 3		*LOCAL-PROFILE-DIR*)
(0000052A 57 2 0		list)
(0000052D 15 6 0		JMP 00000536)
(00000530 3 48 3		*LOCAL-PROFILE-DIR*)
(00000533 57 1 0		list)
(00000536 1		nil)
(00000537 2		T)
(00000538 81 4 47 3 1 0		find-file)
(0000053E 11)
(0000053F 8 0		UnVar0)
(00000541 61 11 0		nil->JMP 0000054F)
(00000544 5 0		UnVar0)
(00000546 53 1 46 3 1 32		file-absolute-name)
(0000054C 11)
(0000054D 8 0		UnVar0)
(0000054F 61 108 1		nil->JMP 000006BE)
(00000552 9 107 3		"VLMSG.DLL")
(00000555 51 162 83 0 0		21410)
(0000055A 81 2 106 3 1 0		string-resource)
(00000560 81 1 45 3 1 0		ales-prompt-msg)
(00000566 10)
(00000567 2		T)
(00000568 15 184 0		JMP 00000623)
(0000056B 21 5 1 1 0)
(00000570 100 1		UNVar1)
(00000572 100 2		UNVar2)
(00000574 5 0		UnVar0)
(00000576 9 44 3		':INPUT)
(00000579 81 2 64 3 1 0		open)
(0000057F 8 3		UnVar3)
(00000581 5 3		UnVar3)
(00000583 8 4		UnVar4)
(00000585 15 35 0		JMP 000005AB)
(00000588 20 0 0 0 0)
(0000058D 4 1 3		UpVar1-3)
(00000590 81 1 63 3 1 0		streamp)
(00000596 63		nil->ret)
(00000597 4 1 3		UpVar1-3)
(0000059A 81 1 62 3 1 0		open-streamp)
(000005A0 63		nil->ret)
(000005A1 4 1 3		UpVar1-3)
(000005A4 81 1 61 3 1 0		close)
(000005AA 22		ret)
(000005AB 12 198 3		'(1416 -unwind-cleanup-))
(000005AE 15 94 0		JMP 0000060F)
(000005B1 20 0 0 0 0)
(000005B6 9 43 3		"\r\n\t ")
(000005B9 4 1 4		UpVar1-4)
(000005BC 81 1 42 3 1 0		read-line)
(000005C2 14 3 0		T->JMP 000005C8)
(000005C5 9 41 3		"")
(000005C8 81 2 40 3 1 0		string-right-trim)
(000005CE 7 1 1		UpVar1-1)
(000005D1 4 1 1		UpVar1-1)
(000005D4 9 60 3		";# VLIDE desktop file [v.3]. DO NOT EDIT!!!")
(000005D7 81 2 39 3 1 0		string=)
(000005DD 13 27 0		nil->JMP 000005FB)
(000005E0 9 38 3		'(editor))
(000005E3 53 1 37 3 1 32		clear-desktop)
(000005E9 10)
(000005EA 15 0 0		JMP 000005ED)
(000005ED 4 1 4		UpVar1-4)
(000005F0 53 1 36 3 1 32		c-restore)
(000005F6 60 244 255		T->JMP 000005ED)
(000005F9 2		T)
(000005FA 22		ret)
(000005FB 9 107 3		"VLMSG.DLL")
(000005FE 51 172 83 0 0		21420)
(00000603 81 2 106 3 1 0		string-resource)
(00000609 47 1 35 3 32 32		warn)
(0000060F 12 197 3		'(1457 -unwind-protect-))
(00000612 1		nil)
(00000613 81 3 117 3 1 0		_unwinded-apply)
(00000619 10)
(0000061A 81 0 34 3 1 0		mdiwindows-arrange-icons)
(00000620 10)
(00000621 1		nil)
(00000622 22		ret)
(00000623 12 196 3		'(1387 nil))
(00000626 5 0		UnVar0)
(00000628 57 1 0		list)
(0000062B 81 3 51 3 1 0		_protected-apply)
(00000631 13 66 0		nil->JMP 00000676)
(00000634 1		nil)
(00000635 6 33 3		*desktop-autosave*)
(00000638 9 107 3		"VLMSG.DLL")
(0000063B 51 182 83 0 0		21430)
(00000640 81 2 106 3 1 0		string-resource)
(00000646 5 0		UnVar0)
(00000648 53 2 35 3 1 32		warn)
(0000064E 10)
(0000064F 53 0 111 3 1 32		alesmaint?)
(00000655 13 26 0		nil->JMP 00000672)
(00000658 3 98 3		*trace-output*)
(0000065B 9 107 3		"VLMSG.DLL")
(0000065E 51 192 83 0 0		21440)
(00000663 81 2 106 3 1 0		string-resource)
(00000669 5 1		UnVar1)
(0000066B 53 3 97 3 1 32		prinf)
(00000671 10)
(00000672 1		nil)
(00000673 15 72 0		JMP 000006BE)
(00000676 3 57 3		*desktop-save-windows*)
(00000679 13 3 0		nil->JMP 0000067F)
(0000067C 15 36 0		JMP 000006A3)
(0000067F 3 92 3		*console*)
(00000682 9 32 3		':NORMAL)
(00000685 9 31 3		'state)
(00000688 81 3 78 3 1 0		slot-value<-)
(0000068E 10)
(0000068F 3 92 3		*console*)
(00000692 53 1 102 3 1 32		update-host-spouse)
(00000698 10)
(00000699 3 92 3		*console*)
(0000069C 53 1 30 3 1 32		!mdiwin-cascade)
(000006A2 10)
(000006A3 3 98 3		*trace-output*)
(000006A6 9 107 3		"VLMSG.DLL")
(000006A9 51 202 83 0 0		21450)
(000006AE 81 2 106 3 1 0		string-resource)
(000006B4 5 0		UnVar0)
(000006B6 53 3 97 3 1 32		prinf)
(000006BC 10)
(000006BD 2		T)
(000006BE 25 2 0)
(000006C1 22		ret)
;;;def desktop::clear! 1730
(000006C2 20 1 1 1 0)
(000006C7 9 38 3		'(editor))
(000006CA 47 1 37 3 32 32		clear-desktop)
;;;def desktop::save! 1744
(000006D0 20 4 1 2 0)
(000006D5 100 2		UNVar2)
(000006D7 100 3		UNVar3)
(000006D9 5 1		UnVar1)
(000006DB 13 3 0		nil->JMP 000006E1)
(000006DE 15 50 0		JMP 00000713)
(000006E1 9 29 3		":/")
(000006E4 9 28 3		"://")
(000006E7 53 0 111 3 1 32		alesmaint?)
(000006ED 13 9 0		nil->JMP 000006F9)
(000006F0 81 0 49 3 1 0		chdir)
(000006F6 15 3 0		JMP 000006FC)
(000006F9 3 48 3		*LOCAL-PROFILE-DIR*)
(000006FC 9 27 3		"/VLIDE.DSK")
(000006FF 81 2 75 3 1 0		concat)
(00000705 53 1 26 3 1 32		filename-beautify)
(0000070B 81 3 25 3 1 0		string-subst)
(00000711 8 1		UnVar1)
(00000713 9 107 3		"VLMSG.DLL")
(00000716 51 212 83 0 0		21460)
(0000071B 81 2 106 3 1 0		string-resource)
(00000721 8 3		UnVar3)
(00000723 3 57 3		*desktop-save-windows*)
(00000726 13 17 0		nil->JMP 0000073A)
(00000729 9 107 3		"VLMSG.DLL")
(0000072C 51 222 83 0 0		21470)
(00000731 81 2 106 3 1 0		string-resource)
(00000737 15 3 0		JMP 0000073D)
(0000073A 9 41 3		"")
(0000073D 8 2		UnVar2)
(0000073F 2		T)
(00000740 63		nil->ret)
(00000741 5 1		UnVar1)
(00000743 1		nil)
(00000744 95 2 131 4 0 0		lpp-save-config)
(0000074A 13 51 0		nil->JMP 00000780)
(0000074D 3 98 3		*trace-output*)
(00000750 5 3		UnVar3)
(00000752 5 2		UnVar2)
(00000754 5 1		UnVar1)
(00000756 53 4 97 3 1 32		prinf)
(0000075C 10)
(0000075D 9 107 3		"VLMSG.DLL")
(00000760 51 56 119 0 0		30520)
(00000765 81 2 106 3 1 0		string-resource)
(0000076B 5 1		UnVar1)
(0000076D 81 1 24 3 1 0		string)
(00000773 81 2 23 3 1 0		_win-format-message)
(00000779 81 1 45 3 1 0		ales-prompt-msg)
(0000077F 22		ret)
(00000780 3 22 3		*stop-alert*)
(00000783 9 107 3		"VLMSG.DLL")
(00000786 51 242 83 0 0		21490)
(0000078B 81 2 106 3 1 0		string-resource)
(00000791 5 1		UnVar1)
(00000793 47 3 85 3 32 32		alert)
;;;def add-desktop-option 1945
(00000799 20 7 1 1 1)
(0000079E 5 1		UnVar1)
(000007A0 8 2		UnVar2)
(000007A2 5 2		UnVar2)
(000007A4 9 21 3		':ACCESSOR)
(000007A7 1		nil)
(000007A8 81 3 129 3 1 0		getf)
(000007AE 8 3		UnVar3)
(000007B0 5 2		UnVar2)
(000007B2 9 20 3		':L-CONTEXT)
(000007B5 1		nil)
(000007B6 81 3 129 3 1 0		getf)
(000007BC 8 4		UnVar4)
(000007BE 5 2		UnVar2)
(000007C0 9 19 3		':CHECK)
(000007C3 1		nil)
(000007C4 81 3 129 3 1 0		getf)
(000007CA 8 5		UnVar5)
(000007CC 5 2		UnVar2)
(000007CE 9 18 3		':DOQ)
(000007D1 1		nil)
(000007D2 81 3 129 3 1 0		getf)
(000007D8 8 6		UnVar6)
(000007DA 5 0		UnVar0)
(000007DC 37 3		symbolp)
(000007DE 9 107 3		"VLMSG.DLL")
(000007E1 51 72 83 0 0		21320)
(000007E6 81 2 106 3 1 0		string-resource)
(000007EC 5 0		UnVar0)
(000007EE 53 3 17 3 1 32		assert)
(000007F4 10)
(000007F5 5 0		UnVar0)
(000007F7 3 58 3		*lex-options-list*)
(000007FA 81 2 16 3 1 0		assq)
(00000800 14 11 0		T->JMP 0000080E)
(00000803 5 0		UnVar0)
(00000805 3 59 3		*ales-options-list*)
(00000808 81 2 16 3 1 0		assq)
(0000080E 13 22 0		nil->JMP 00000827)
(00000811 9 107 3		"VLMSG.DLL")
(00000814 51 82 83 0 0		21330)
(00000819 81 2 106 3 1 0		string-resource)
(0000081F 5 0		UnVar0)
(00000821 47 2 35 3 32 32		warn)
(00000827 5 6		UnVar6)
(00000829 13 7 0		nil->JMP 00000833)
(0000082C 5 6		UnVar6)
(0000082E 57 1 0		list)
(00000831 8 6		UnVar6)
(00000833 5 5		UnVar5)
(00000835 13 7 0		nil->JMP 0000083F)
(00000838 5 5		UnVar5)
(0000083A 5 6		UnVar6)
(0000083C 42		cons)
(0000083D 8 6		UnVar6)
(0000083F 5 3		UnVar3)
(00000841 5 6		UnVar6)
(00000843 42		cons)
(00000844 8 6		UnVar6)
(00000846 5 0		UnVar0)
(00000848 5 6		UnVar6)
(0000084A 42		cons)
(0000084B 8 6		UnVar6)
(0000084D 5 4		UnVar4)
(0000084F 9 15 3		':AUTOLISP)
(00000852 38		=)
(00000853 13 11 0		nil->JMP 00000861)
(00000856 5 6		UnVar6)
(00000858 3 59 3		*ales-options-list*)
(0000085B 42		cons)
(0000085C 11)
(0000085D 6 59 3		*ales-options-list*)
(00000860 22		ret)
(00000861 5 6		UnVar6)
(00000863 3 58 3		*lex-options-list*)
(00000866 42		cons)
(00000867 11)
(00000868 6 58 3		*lex-options-list*)
(0000086B 22		ret)
;;;def nil 2156
(0000086C 20 1 1 1 0)
(00000871 5 0		UnVar0)
(00000873 40		car)
(00000874 22		ret)
;;;def nil 2165
(00000875 20 1 1 1 0)
(0000087A 5 0		UnVar0)
(0000087C 41		cdr)
(0000087D 40		car)
(0000087E 62		T->ret)
(0000087F 5 0		UnVar0)
(00000881 40		car)
(00000882 22		ret)
;;;def nil 2179
(00000883 20 1 1 1 0)
(00000888 5 0		UnVar0)
(0000088A 41		cdr)
(0000088B 41		cdr)
(0000088C 40		car)
(0000088D 22		ret)
;;;def desktop-option.store 2190
(0000088E 20 3 1 1 0)
(00000893 100 1		UNVar1)
(00000895 5 0		UnVar0)
(00000897 8 2		UnVar2)
(00000899 5 2		UnVar2)
(0000089B 40		car)
(0000089C 5 0		UnVar0)
(0000089E 8 2		UnVar2)
(000008A0 5 2		UnVar2)
(000008A2 41		cdr)
(000008A3 40		car)
(000008A4 14 3 0		T->JMP 000008AA)
(000008A7 5 2		UnVar2)
(000008A9 40		car)
(000008AA 53 1 14 3 1 32		accessed-value)
(000008B0 42		cons)
(000008B1 22		ret)
;;;def desktop-option.restore 2226
(000008B2 20 4 2 2 0)
(000008B7 100 2		UNVar2)
(000008B9 5 0		UnVar0)
(000008BB 8 3		UnVar3)
(000008BD 5 3		UnVar3)
(000008BF 41		cdr)
(000008C0 40		car)
(000008C1 14 3 0		T->JMP 000008C7)
(000008C4 5 3		UnVar3)
(000008C6 40		car)
(000008C7 5 1		UnVar1)
(000008C9 47 2 13 3 32 32		accessed-value<-)
;;;def desktop-option-restore 2255
(000008CF 20 5 2 2 0)
(000008D4 100 2		UNVar2)
(000008D6 100 3		UNVar3)
(000008D8 5 1		UnVar1)
(000008DA 40		car)
(000008DB 5 0		UnVar0)
(000008DD 8 4		UnVar4)
(000008DF 5 4		UnVar4)
(000008E1 9 112 3		':AL)
(000008E4 38		=)
(000008E5 13 6 0		nil->JMP 000008EE)
(000008E8 3 59 3		*ales-options-list*)
(000008EB 15 16 0		JMP 000008FE)
(000008EE 5 4		UnVar4)
(000008F0 9 120 3		':LPP)
(000008F3 38		=)
(000008F4 13 6 0		nil->JMP 000008FD)
(000008F7 3 58 3		*lex-options-list*)
(000008FA 15 1 0		JMP 000008FE)
(000008FD 1		nil)
(000008FE 81 2 16 3 1 0		assq)
(00000904 8 3		UnVar3)
(00000906 5 3		UnVar3)
(00000908 8 4		UnVar4)
(0000090A 5 4		UnVar4)
(0000090C 41		cdr)
(0000090D 41		cdr)
(0000090E 40		car)
(0000090F 11)
(00000910 8 2		UnVar2)
(00000912 13 38 0		nil->JMP 0000093B)
(00000915 5 1		UnVar1)
(00000917 41		cdr)
(00000918 5 2		UnVar2)
(0000091A 52 1 1		)
(0000091D 13 3 0		nil->JMP 00000923)
(00000920 15 24 0		JMP 0000093B)
(00000923 9 107 3		"VLMSG.DLL")
(00000926 51 92 83 0 0		21340)
(0000092B 81 2 106 3 1 0		string-resource)
(00000931 5 1		UnVar1)
(00000933 41		cdr)
(00000934 81 2 109 3 1 0		_msg-err)
(0000093A 10)
(0000093B 5 3		UnVar3)
(0000093D 63		nil->ret)
(0000093E 5 3		UnVar3)
(00000940 5 1		UnVar1)
(00000942 41		cdr)
(00000943 95 2 178 8 0 0		desktop-option.restore)
(00000949 10)
(0000094A 2		T)
(0000094B 22		ret)
;;;def store-desktop-options 2380
(0000094C 20 5 3 3 0)
(00000951 5 2		UnVar2)
(00000953 8 3		UnVar3)
(00000955 100 4		UNVar4)
(00000957 15 19 0		JMP 0000096D)
(0000095A 5 3		UnVar3)
(0000095C 40		car)
(0000095D 95 1 142 8 0 0		desktop-option.store)
(00000963 5 4		UnVar4)
(00000965 42		cons)
(00000966 8 4		UnVar4)
(00000968 5 3		UnVar3)
(0000096A 41		cdr)
(0000096B 8 3		UnVar3)
(0000096D 5 3		UnVar3)
(0000096F 60 232 255		T->JMP 0000095A)
(00000972 5 4		UnVar4)
(00000974 81 1 12 3 1 0		nreverse)
(0000097A 8 2		UnVar2)
(0000097C 5 1		UnVar1)
(0000097E 9 112 3		':AL)
(00000981 38		=)
(00000982 13 5 0		nil->JMP 0000098A)
(00000985 5 2		UnVar2)
(00000987 6 11 3		_%dsk-options%)
(0000098A 9 128 3		"(")
(0000098D 5 1		UnVar1)
(0000098F 81 1 24 3 1 0		string)
(00000995 81 2 75 3 1 0		concat)
(0000099B 5 0		UnVar0)
(0000099D 81 2 121 3 1 0		write-line)
(000009A3 10)
(000009A4 9 10 3		'*print-length*)
(000009A7 1		nil)
(000009A8 9 9 3		'*print-level*)
(000009AB 1		nil)
(000009AC 24 4 0)
(000009AF 5 2		UnVar2)
(000009B1 8 3		UnVar3)
(000009B3 100 4		UNVar4)
(000009B5 15 41 0		JMP 000009E1)
(000009B8 5 3		UnVar3)
(000009BA 40		car)
(000009BB 8 4		UnVar4)
(000009BD 5 3		UnVar3)
(000009BF 41		cdr)
(000009C0 8 3		UnVar3)
(000009C2 50 9		9)
(000009C4 5 0		UnVar0)
(000009C6 81 2 124 3 1 0		write-byte)
(000009CC 10)
(000009CD 5 4		UnVar4)
(000009CF 5 0		UnVar0)
(000009D1 81 2 123 3 1 0		prin1)
(000009D7 10)
(000009D8 5 0		UnVar0)
(000009DA 81 1 125 3 1 0		terpri)
(000009E0 10)
(000009E1 5 3		UnVar3)
(000009E3 60 210 255		T->JMP 000009B8)
(000009E6 25 2 0)
(000009E9 9 122 3		"\t)")
(000009EC 5 0		UnVar0)
(000009EE 81 2 121 3 1 0		write-line)
(000009F4 10)
(000009F5 2		T)
(000009F6 22		ret)
;;;def restore-desktop-options 2551
(000009F7 20 3 1 1 0)
(000009FC 5 0		UnVar0)
(000009FE 9 112 3		':AL)
(00000A01 81 2 8 3 1 0		eqcar)
(00000A07 13 5 0		nil->JMP 00000A0F)
(00000A0A 5 0		UnVar0)
(00000A0C 6 11 3		_%dsk-options%)
(00000A0F 5 0		UnVar0)
(00000A11 41		cdr)
(00000A12 8 1		UnVar1)
(00000A14 100 2		UNVar2)
(00000A16 15 22 0		JMP 00000A2F)
(00000A19 5 1		UnVar1)
(00000A1B 40		car)
(00000A1C 8 2		UnVar2)
(00000A1E 5 1		UnVar1)
(00000A20 41		cdr)
(00000A21 8 1		UnVar1)
(00000A23 5 0		UnVar0)
(00000A25 40		car)
(00000A26 5 2		UnVar2)
(00000A28 95 2 207 8 0 0		desktop-option-restore)
(00000A2E 10)
(00000A2F 5 1		UnVar1)
(00000A31 60 229 255		T->JMP 00000A19)
(00000A34 1		nil)
(00000A35 22		ret)
;;;def delayed-desktop-restore 2614
(00000A36 20 3 2 3 0)
(00000A3B 5 2		UnVar2)
(00000A3D 13 3 0		nil->JMP 00000A43)
(00000A40 15 4 0		JMP 00000A47)
(00000A43 5 0		UnVar0)
(00000A45 8 2		UnVar2)
(00000A47 9 112 3		':AL)
(00000A4A 5 0		UnVar0)
(00000A4C 3 11 3		_%dsk-options%)
(00000A4F 41		cdr)
(00000A50 81 2 16 3 1 0		assq)
(00000A56 95 2 207 8 0 0		desktop-option-restore)
(00000A5C 62		T->ret)
(00000A5D 5 2		UnVar2)
(00000A5F 5 1		UnVar1)
(00000A61 47 2 13 3 32 32		accessed-value<-)
;;;def nil 2663
(00000A67 20 0 0 0 0)
(00000A6C 3 7 3		*edit-file-history*)
(00000A6F 22		ret)
;;;def nil 2672
(00000A70 20 1 1 1 0)
(00000A75 9 100 3		'file-readable-p)
(00000A78 5 0		UnVar0)
(00000A7A 81 2 6 3 1 0		delete-if-not)
(00000A80 8 0		UnVar0)
(00000A82 5 0		UnVar0)
(00000A84 63		nil->ret)
(00000A85 5 0		UnVar0)
(00000A87 41		cdr)
(00000A88 6 7 3		*edit-file-history*)
(00000A8B 5 0		UnVar0)
(00000A8D 40		car)
(00000A8E 47 1 5 3 32 32		edit-file-history-add)
;;;def nil 2708
(00000A94 20 0 0 0 0)
(00000A99 3 4 3		*load-path*)
(00000A9C 22		ret)
;;;def nil 2717
(00000A9D 20 1 1 1 0)
(00000AA2 53 0 111 3 1 32		alesmaint?)
(00000AA8 61 12 0		nil->JMP 00000AB7)
(00000AAB 5 0		UnVar0)
(00000AAD 3 4 3		*load-path*)
(00000AB0 81 2 3 3 1 0		equal)
(00000AB6 35		not)
(00000AB7 63		nil->ret)
(00000AB8 3 98 3		*trace-output*)
(00000ABB 9 2 3		"~& *load-path* redefined:~%\tfrom\t ~s")
(00000ABE 3 4 3		*load-path*)
(00000AC1 53 3 1 3 1 32		format)
(00000AC7 10)
(00000AC8 5 0		UnVar0)
(00000ACA 6 4 3		*load-path*)
(00000ACD 3 98 3		*trace-output*)
(00000AD0 9 0 3		"~%\tto\t ~s~%~!")
(00000AD3 5 0		UnVar0)
(00000AD5 47 3 1 3 32 32		format)
;;;def auto-restore-apex-and-size 2779
(00000ADB 20 1 1 1 0)
(00000AE0 5 0		UnVar0)
(00000AE2 40		car)
(00000AE3 6 255 2		apex)
(00000AE6 5 0		UnVar0)
(00000AE8 41		cdr)
(00000AE9 6 254 2		size)
(00000AEC 3 255 2		apex)
(00000AEF 81 1 253 2 1 0		ipoint-h)
(00000AF5 53 1 252 2 1 32		auto-restore-x)
(00000AFB 3 255 2		apex)
(00000AFE 81 1 251 2 1 0		ipoint-v)
(00000B04 53 1 250 2 1 32		auto-restore-y)
(00000B0A 81 2 249 2 1 0		make-ipoint)
(00000B10 6 255 2		apex)
(00000B13 3 254 2		size)
(00000B16 81 1 253 2 1 0		ipoint-h)
(00000B1C 53 1 252 2 1 32		auto-restore-x)
(00000B22 3 254 2		size)
(00000B25 81 1 251 2 1 0		ipoint-v)
(00000B2B 53 1 250 2 1 32		auto-restore-y)
(00000B31 81 2 249 2 1 0		make-ipoint)
(00000B37 6 254 2		size)
(00000B3A 3 255 2		apex)
(00000B3D 3 254 2		size)
(00000B40 42		cons)
(00000B41 22		ret)
;;;def judge-and-restore-apex-and-size 2882
(00000B42 20 1 1 1 0)
(00000B47 5 0		UnVar0)
(00000B49 9 248 2		':MINIMIZED)
(00000B4C 38		=)
(00000B4D 14 15 0		T->JMP 00000B5F)
(00000B50 5 0		UnVar0)
(00000B52 9 247 2		':MAXIMIZED)
(00000B55 38		=)
(00000B56 14 6 0		T->JMP 00000B5F)
(00000B59 5 0		UnVar0)
(00000B5B 9 32 3		':NORMAL)
(00000B5E 38		=)
(00000B5F 13 3 0		nil->JMP 00000B65)
(00000B62 5 0		UnVar0)
(00000B64 22		ret)
(00000B65 5 0		UnVar0)
(00000B67 97 1 224 10 0 0		offset 00000AE0)
;;;def auto-scale-apex-and-size 2925
(00000B6D 20 1 1 1 0)
(00000B72 5 0		UnVar0)
(00000B74 40		car)
(00000B75 6 255 2		apex)
(00000B78 5 0		UnVar0)
(00000B7A 41		cdr)
(00000B7B 6 254 2		size)
(00000B7E 3 255 2		apex)
(00000B81 81 1 253 2 1 0		ipoint-h)
(00000B87 53 1 246 2 1 32		auto-scale-x)
(00000B8D 3 255 2		apex)
(00000B90 81 1 251 2 1 0		ipoint-v)
(00000B96 53 1 245 2 1 32		auto-scale-y)
(00000B9C 81 2 249 2 1 0		make-ipoint)
(00000BA2 6 255 2		apex)
(00000BA5 3 254 2		size)
(00000BA8 81 1 253 2 1 0		ipoint-h)
(00000BAE 53 1 246 2 1 32		auto-scale-x)
(00000BB4 3 254 2		size)
(00000BB7 81 1 251 2 1 0		ipoint-v)
(00000BBD 53 1 245 2 1 32		auto-scale-y)
(00000BC3 81 2 249 2 1 0		make-ipoint)
(00000BC9 6 254 2		size)
(00000BCC 3 255 2		apex)
(00000BCF 3 254 2		size)
(00000BD2 42		cons)
(00000BD3 22		ret)
;;;def judge-and-scale-apex-and-size 3028
(00000BD4 20 1 1 1 0)
(00000BD9 5 0		UnVar0)
(00000BDB 9 248 2		':MINIMIZED)
(00000BDE 38		=)
(00000BDF 14 15 0		T->JMP 00000BF1)
(00000BE2 5 0		UnVar0)
(00000BE4 9 247 2		':MAXIMIZED)
(00000BE7 38		=)
(00000BE8 14 6 0		T->JMP 00000BF1)
(00000BEB 5 0		UnVar0)
(00000BED 9 32 3		':NORMAL)
(00000BF0 38		=)
(00000BF1 13 3 0		nil->JMP 00000BF7)
(00000BF4 5 0		UnVar0)
(00000BF6 22		ret)
(00000BF7 5 0		UnVar0)
(00000BF9 97 1 114 11 0 0		offset 00000B72)
;;;def win-frame.apex-and-size-100 3071
(00000BFF 20 1 0 1 0)
(00000C04 5 0		UnVar0)
(00000C06 13 20 0		nil->JMP 00000C1D)
(00000C09 5 0		UnVar0)
(00000C0B 95 1 212 11 0 0		judge-and-scale-apex-and-size)
(00000C11 81 1 244 2 1 0		win-frame.apex-and-size)
(00000C17 97 1 71 11 0 0		offset 00000B47)
(00000C1D 81 0 244 2 1 0		win-frame.apex-and-size)
(00000C23 97 1 71 11 0 0		offset 00000B47)
;;;def get-desktop-window-sample 3113
(00000C29 20 2 1 1 0)
(00000C2E 100 1		UNVar1)
(00000C30 5 0		UnVar0)
(00000C32 81 1 135 3 1 0		TWinp)
(00000C38 60 12 0		T->JMP 00000C47)
(00000C3B 9 243 2		"twinp:")
(00000C3E 5 0		UnVar0)
(00000C40 81 2 242 2 1 0		_bat-err)
(00000C46 10)
(00000C47 9 241 2		':FGC)
(00000C4A 5 0		UnVar0)
(00000C4C 81 1 240 2 1 0		TWin.fcolor)
(00000C52 9 239 2		':BGC)
(00000C55 5 0		UnVar0)
(00000C57 81 1 238 2 1 0		TWin.bcolor)
(00000C5D 9 237 2		':LXC)
(00000C60 5 0		UnVar0)
(00000C62 9 236 2		'lex-color-p)
(00000C65 81 2 86 3 1 0		slot-value)
(00000C6B 9 235 2		':CLV)
(00000C6E 5 0		UnVar0)
(00000C70 9 234 2		'color-vector)
(00000C73 81 2 86 3 1 0		slot-value)
(00000C79 9 233 2		':TW)
(00000C7C 5 0		UnVar0)
(00000C7E 81 1 232 2 1 0		TWin.tab-width)
(00000C84 9 231 2		':LM)
(00000C87 5 0		UnVar0)
(00000C89 81 1 230 2 1 0		TWin.left-margin)
(00000C8F 57 12 0		list)
(00000C92 22		ret)
;;;def update-attributes-by-model-window 3219
(00000C93 20 5 3 3 0)
(00000C98 81 0 93 3 1 0		list-mdiwindows-with-host-spouse)
(00000C9E 8 3		UnVar3)
(00000CA0 100 4		UNVar4)
(00000CA2 15 68 0		JMP 00000CE9)
(00000CA5 5 3		UnVar3)
(00000CA7 40		car)
(00000CA8 8 4		UnVar4)
(00000CAA 5 3		UnVar3)
(00000CAC 41		cdr)
(00000CAD 8 3		UnVar3)
(00000CAF 5 4		UnVar4)
(00000CB1 81 1 126 3 1 0		type-of)
(00000CB7 5 0		UnVar0)
(00000CB9 38		=)
(00000CBA 61 20 0		nil->JMP 00000CD1)
(00000CBD 5 4		UnVar4)
(00000CBF 9 229 2		'l-context)
(00000CC2 81 2 86 3 1 0		slot-value)
(00000CC8 53 1 228 2 1 32		object-id)
(00000CCE 5 1		UnVar1)
(00000CD0 38		=)
(00000CD1 13 21 0		nil->JMP 00000CE9)
(00000CD4 5 4		UnVar4)
(00000CD6 5 2		UnVar2)
(00000CD8 53 2 104 3 1 32		twin.update-attributes)
(00000CDE 10)
(00000CDF 5 4		UnVar4)
(00000CE1 2		T)
(00000CE2 53 2 102 3 1 32		update-host-spouse)
(00000CE8 10)
(00000CE9 5 3		UnVar3)
(00000CEB 60 183 255		T->JMP 00000CA5)
(00000CEE 1		nil)
(00000CEF 22		ret)
;;;def _ass-sample& 3312
(00000CF0 20 2 1 1 0)
(00000CF5 5 0		UnVar0)
(00000CF7 8 1		UnVar1)
(00000CF9 5 1		UnVar1)
(00000CFB 9 116 3		'editor)
(00000CFE 38		=)
(00000CFF 13 4 0		nil->JMP 00000D06)
(00000D02 9 227 2		'*editor-sample-window*)
(00000D05 22		ret)
(00000D06 1		nil)
(00000D07 22		ret)
;;;def _ass-sample/cntx 3336
(00000D08 20 5 3 3 0)
(00000D0D 100 3		UNVar3)
(00000D0F 100 4		UNVar4)
(00000D11 5 0		UnVar0)
(00000D13 95 1 240 12 0 0		_ass-sample&)
(00000D19 8 4		UnVar4)
(00000D1B 5 4		UnVar4)
(00000D1D 13 18 0		nil->JMP 00000D32)
(00000D20 5 1		UnVar1)
(00000D22 5 4		UnVar4)
(00000D24 81 1 226 2 1 0		symbol-value)
(00000D2A 81 2 16 3 1 0		assq)
(00000D30 8 3		UnVar3)
(00000D32 5 3		UnVar3)
(00000D34 9 107 3		"VLMSG.DLL")
(00000D37 51 102 83 0 0		21350)
(00000D3C 81 2 106 3 1 0		string-resource)
(00000D42 53 2 17 3 1 32		assert)
(00000D48 10)
(00000D49 5 3		UnVar3)
(00000D4B 5 2		UnVar2)
(00000D4D 81 2 225 2 1 0		setcdr)
(00000D53 22		ret)
;;;def _ass-sample 3412
(00000D54 20 4 2 2 0)
(00000D59 100 2		UNVar2)
(00000D5B 100 3		UNVar3)
(00000D5D 5 0		UnVar0)
(00000D5F 95 1 240 12 0 0		_ass-sample&)
(00000D65 11)
(00000D66 8 3		UnVar3)
(00000D68 63		nil->ret)
(00000D69 5 1		UnVar1)
(00000D6B 5 3		UnVar3)
(00000D6D 81 1 226 2 1 0		symbol-value)
(00000D73 81 2 16 3 1 0		assq)
(00000D79 8 2		UnVar2)
(00000D7B 5 2		UnVar2)
(00000D7D 9 107 3		"VLMSG.DLL")
(00000D80 51 102 83 0 0		21350)
(00000D85 81 2 106 3 1 0		string-resource)
(00000D8B 53 2 17 3 1 32		assert)
(00000D91 10)
(00000D92 5 2		UnVar2)
(00000D94 41		cdr)
(00000D95 22		ret)
;;;def !wa-set-prototype 3478
(00000D96 20 2 1 1 0)
(00000D9B 5 0		UnVar0)
(00000D9D 81 1 126 3 1 0		type-of)
(00000DA3 5 0		UnVar0)
(00000DA5 9 229 2		'l-context)
(00000DA8 81 2 86 3 1 0		slot-value)
(00000DAE 53 1 228 2 1 32		object-id)
(00000DB4 95 2 84 13 0 0		_ass-sample)
(00000DBA 8 1		UnVar1)
(00000DBC 5 0		UnVar0)
(00000DBE 53 1 89 3 1 32		mdiwindow-show-up)
(00000DC4 10)
(00000DC5 5 1		UnVar1)
(00000DC7 61 34 0		nil->JMP 00000DEC)
(00000DCA 9 107 3		"VLMSG.DLL")
(00000DCD 51 112 83 0 0		21360)
(00000DD2 81 2 106 3 1 0		string-resource)
(00000DD8 5 0		UnVar0)
(00000DDA 81 1 126 3 1 0		type-of)
(00000DE0 81 1 224 2 1 0		string-upcase)
(00000DE6 53 2 223 2 1 32		yes-or-no-p)
(00000DEC 63		nil->ret)
(00000DED 5 0		UnVar0)
(00000DEF 81 1 126 3 1 0		type-of)
(00000DF5 5 0		UnVar0)
(00000DF7 9 229 2		'l-context)
(00000DFA 81 2 86 3 1 0		slot-value)
(00000E00 53 1 228 2 1 32		object-id)
(00000E06 5 0		UnVar0)
(00000E08 95 1 41 12 0 0		get-desktop-window-sample)
(00000E0E 95 3 8 13 0 0		_ass-sample/cntx)
(00000E14 10)
(00000E15 5 0		UnVar0)
(00000E17 95 1 95 14 0 0		!wa-all-to-prototype)
(00000E1D 10)
(00000E1E 2		T)
(00000E1F 22		ret)
;;;def !wa-curr-to-prototype 3616
(00000E20 20 2 1 1 0)
(00000E25 5 0		UnVar0)
(00000E27 81 1 126 3 1 0		type-of)
(00000E2D 5 0		UnVar0)
(00000E2F 9 229 2		'l-context)
(00000E32 81 2 86 3 1 0		slot-value)
(00000E38 53 1 228 2 1 32		object-id)
(00000E3E 95 2 84 13 0 0		_ass-sample)
(00000E44 8 1		UnVar1)
(00000E46 5 1		UnVar1)
(00000E48 13 11 0		nil->JMP 00000E56)
(00000E4B 5 0		UnVar0)
(00000E4D 5 1		UnVar1)
(00000E4F 53 2 104 3 1 32		twin.update-attributes)
(00000E55 10)
(00000E56 5 0		UnVar0)
(00000E58 2		T)
(00000E59 47 2 102 3 32 32		update-host-spouse)
;;;def !wa-all-to-prototype 3679
(00000E5F 20 1 1 1 0)
(00000E64 5 0		UnVar0)
(00000E66 81 1 126 3 1 0		type-of)
(00000E6C 5 0		UnVar0)
(00000E6E 9 229 2		'l-context)
(00000E71 81 2 86 3 1 0		slot-value)
(00000E77 53 1 228 2 1 32		object-id)
(00000E7D 5 0		UnVar0)
(00000E7F 81 1 126 3 1 0		type-of)
(00000E85 5 0		UnVar0)
(00000E87 9 229 2		'l-context)
(00000E8A 81 2 86 3 1 0		slot-value)
(00000E90 53 1 228 2 1 32		object-id)
(00000E96 95 2 84 13 0 0		_ass-sample)
(00000E9C 95 3 147 12 0 0		update-attributes-by-model-window)
(00000EA2 10)
(00000EA3 5 0		UnVar0)
(00000EA5 47 1 89 3 32 32		mdiwindow-show-up)
;;;def _psi-unw-fun 3755
(00000EAB 21 6 6 6 0)
(00000EB0 15 101 0		JMP 00000F18)
(00000EB3 20 0 0 0 0)
(00000EB8 4 1 0		UpVar1-0)
(00000EBB 81 1 222 2 1 0		input-streamp)
(00000EC1 13 10 0		nil->JMP 00000ECE)
(00000EC4 4 1 0		UpVar1-0)
(00000EC7 81 1 61 3 1 0		close)
(00000ECD 10)
(00000ECE 4 1 1		UpVar1-1)
(00000ED1 4 1 2		UpVar1-2)
(00000ED4 9 87 3		'caption)
(00000ED7 81 3 78 3 1 0		slot-value<-)
(00000EDD 10)
(00000EDE 4 1 1		UpVar1-1)
(00000EE1 4 1 3		UpVar1-3)
(00000EE4 9 81 3		'is-loaded)
(00000EE7 81 3 78 3 1 0		slot-value<-)
(00000EED 10)
(00000EEE 4 1 4		UpVar1-4)
(00000EF1 13 16 0		nil->JMP 00000F04)
(00000EF4 4 1 4		UpVar1-4)
(00000EF7 4 1 5		UpVar1-5)
(00000EFA 53 2 221 2 1 32		seat<-)
(00000F00 10)
(00000F01 15 11 0		JMP 00000F0F)
(00000F04 4 1 1		UpVar1-1)
(00000F07 1		nil)
(00000F08 81 2 220 2 1 0		TBuf.ro-tmark<-)
(00000F0E 10)
(00000F0F 4 1 1		UpVar1-1)
(00000F12 47 1 102 3 32 32		update-host-spouse)
(00000F18 12 195 3		'(3763 nil))
(00000F1B 22		ret)
;;;def process-selection-istream 3868
(00000F1C 21 12 2 5 0)
(00000F21 5 0		UnVar0)
(00000F23 53 1 91 3 1 32		editorp)
(00000F29 60 12 0		T->JMP 00000F38)
(00000F2C 9 219 2		"editorp:")
(00000F2F 5 0		UnVar0)
(00000F31 81 2 242 2 1 0		_bat-err)
(00000F37 10)
(00000F38 5 3		UnVar3)
(00000F3A 13 3 0		nil->JMP 00000F40)
(00000F3D 15 24 0		JMP 00000F58)
(00000F40 5 0		UnVar0)
(00000F42 81 1 218 2 1 0		TWin.has-selection-p)
(00000F48 13 13 0		nil->JMP 00000F58)
(00000F4B 5 0		UnVar0)
(00000F4D 53 1 217 2 1 32		selection)
(00000F53 8 3		UnVar3)
(00000F55 15 0 0		JMP 00000F58)
(00000F58 5 3		UnVar3)
(00000F5A 13 115 1		nil->JMP 000010D0)
(00000F5D 5 0		UnVar0)
(00000F5F 5 3		UnVar3)
(00000F61 40		car)
(00000F62 5 3		UnVar3)
(00000F64 41		cdr)
(00000F65 81 3 216 2 1 0		make-tbuf-istream)
(00000F6B 8 5		UnVar5)
(00000F6D 5 0		UnVar0)
(00000F6F 81 1 215 2 1 0		tbuf.ro-tmark)
(00000F75 8 6		UnVar6)
(00000F77 5 0		UnVar0)
(00000F79 9 87 3		'caption)
(00000F7C 81 2 86 3 1 0		slot-value)
(00000F82 8 7		UnVar7)
(00000F84 5 0		UnVar0)
(00000F86 9 81 3		'is-loaded)
(00000F89 81 2 86 3 1 0		slot-value)
(00000F8F 8 8		UnVar8)
(00000F91 3 56 3		_%sys-error-hook%)
(00000F94 8 9		UnVar9)
(00000F96 100 10		UNVar10)
(00000F98 100 11		UNVar11)
(00000F9A 5 2		UnVar2)
(00000F9C 60 19 0		T->JMP 00000FB2)
(00000F9F 5 0		UnVar0)
(00000FA1 9 229 2		'l-context)
(00000FA4 81 2 86 3 1 0		slot-value)
(00000FAA 14 3 0		T->JMP 00000FB0)
(00000FAD 3 214 2		_%curr-rep-cntx%)
(00000FB0 8 2		UnVar2)
(00000FB2 5 0		UnVar0)
(00000FB4 2		T)
(00000FB5 9 81 3		'is-loaded)
(00000FB8 81 3 78 3 1 0		slot-value<-)
(00000FBE 10)
(00000FBF 5 0		UnVar0)
(00000FC1 5 8		UnVar8)
(00000FC3 13 14 0		nil->JMP 00000FD4)
(00000FC6 5 7		UnVar7)
(00000FC8 9 213 2		" ...")
(00000FCB 81 2 75 3 1 0		concat)
(00000FD1 15 28 0		JMP 00000FF0)
(00000FD4 9 107 3		"VLMSG.DLL")
(00000FD7 51 106 119 0 0		30570)
(00000FDC 81 2 106 3 1 0		string-resource)
(00000FE2 5 7		UnVar7)
(00000FE4 81 1 24 3 1 0		string)
(00000FEA 81 2 23 3 1 0		_win-format-message)
(00000FF0 9 87 3		'caption)
(00000FF3 81 3 78 3 1 0		slot-value<-)
(00000FF9 10)
(00000FFA 5 6		UnVar6)
(00000FFC 13 23 0		nil->JMP 00001016)
(00000FFF 5 6		UnVar6)
(00001001 53 1 212 2 1 32		seat)
(00001007 8 11		UnVar11)
(00001009 5 6		UnVar6)
(0000100B 1		nil)
(0000100C 53 2 221 2 1 32		seat<-)
(00001012 10)
(00001013 15 10 0		JMP 00001020)
(00001016 5 0		UnVar0)
(00001018 2		T)
(00001019 81 2 220 2 1 0		TBuf.ro-tmark<-)
(0000101F 10)
(00001020 5 0		UnVar0)
(00001022 53 1 102 3 1 32		update-host-spouse)
(00001028 10)
(00001029 5 5		UnVar5)
(0000102B 5 0		UnVar0)
(0000102D 5 7		UnVar7)
(0000102F 5 8		UnVar8)
(00001031 5 6		UnVar6)
(00001033 5 11		UnVar11)
(00001035 53 6 211 2 1 32		_psi-unw-fun)
(0000103B 8 10		UnVar10)
(0000103D 5 4		UnVar4)
(0000103F 13 32 0		nil->JMP 00001062)
(00001042 5 2		UnVar2)
(00001044 53 1 210 2 1 32		cntx-window-show-up)
(0000104A 11)
(0000104B 8 4		UnVar4)
(0000104D 13 18 0		nil->JMP 00001062)
(00001050 5 4		UnVar4)
(00001052 5 4		UnVar4)
(00001054 81 1 209 2 1 0		TBuf.length)
(0000105A 1		nil)
(0000105B 81 3 208 2 1 0		TWin.cpos<-)
(00001061 10)
(00001062 15 14 0		JMP 00001073)
(00001065 20 0 0 0 0)
(0000106A 4 1 11		UpVar1-11)
(0000106D 63		nil->ret)
(0000106E 4 1 10		UpVar1-10)
(00001071 46 0		invoke+ret)
(00001073 12 194 3		'(4197 -unwind-cleanup-))
(00001076 15 73 0		JMP 000010C2)
(00001079 20 0 0 0 0)
(0000107E 9 56 3		'_%sys-error-hook%)
(00001081 15 32 0		JMP 000010A4)
(00001084 20 1 1 1 0)
(00001089 4 2 9		UpVar2-9)
(0000108C 6 56 3		_%sys-error-hook%)
(0000108F 4 2 10		UpVar2-10)
(00001092 52 0 0		)
(00001095 1		nil)
(00001096 7 2 11		UpVar2-11)
(00001099 3 56 3		_%sys-error-hook%)
(0000109C 63		nil->ret)
(0000109D 5 0		UnVar0)
(0000109F 3 56 3		_%sys-error-hook%)
(000010A2 46 1		invoke+ret)
(000010A4 12 193 3		'(4228 nil))
(000010A7 24 2 0)
(000010AA 2		T)
(000010AB 7 1 11		UpVar1-11)
(000010AE 4 1 5		UpVar1-5)
(000010B1 4 1 2		UpVar1-2)
(000010B4 4 1 1		UpVar1-1)
(000010B7 52 2 1		)
(000010BA 11)
(000010BB 7 1 3		UpVar1-3)
(000010BE 25 1 0)
(000010C1 22		ret)
(000010C2 12 192 3		'(4217 -unwind-protect-))
(000010C5 1		nil)
(000010C6 81 3 117 3 1 0		_unwinded-apply)
(000010CC 10)
(000010CD 15 10 0		JMP 000010DA)
(000010D0 3 207 2		*stop-beep*)
(000010D3 81 1 206 2 1 0		message-beep)
(000010D9 10)
(000010DA 5 3		UnVar3)
(000010DC 22		ret)
;;;def eval-selection! 4317
(000010DD 20 1 0 1 0)
(000010E2 5 0		UnVar0)
(000010E4 81 1 135 3 1 0		TWinp)
(000010EA 13 3 0		nil->JMP 000010F0)
(000010ED 15 5 0		JMP 000010F5)
(000010F0 3 205 2		*active-mdiwindow*)
(000010F3 8 0		UnVar0)
(000010F5 5 0		UnVar0)
(000010F7 15 42 0		JMP 00001124)
(000010FA 20 2 2 2 0)
(000010FF 9 204 2		'*load-print*)
(00001102 2		T)
(00001103 24 2 0)
(00001106 5 1		UnVar1)
(00001108 13 13 0		nil->JMP 00001118)
(0000110B 5 1		UnVar1)
(0000110D 5 0		UnVar0)
(0000110F 53 2 203 2 1 32		rep-cntx.load-stream)
(00001115 15 8 0		JMP 00001120)
(00001118 5 0		UnVar0)
(0000111A 81 1 202 2 1 0		load)
(00001120 25 1 0)
(00001123 22		ret)
(00001124 9 191 3		'(4346 nil))
(00001127 5 0		UnVar0)
(00001129 9 229 2		'l-context)
(0000112C 81 2 86 3 1 0		slot-value)
(00001132 14 3 0		T->JMP 00001138)
(00001135 3 214 2		_%curr-rep-cntx%)
(00001138 1		nil)
(00001139 2		T)
(0000113A 47 5 201 2 32 32		process-selection-istream)
;;;def load-buffer! 4416
(00001140 21 1 0 1 0)
(00001145 5 0		UnVar0)
(00001147 81 1 135 3 1 0		TWinp)
(0000114D 13 3 0		nil->JMP 00001153)
(00001150 15 5 0		JMP 00001158)
(00001153 3 205 2		*active-mdiwindow*)
(00001156 8 0		UnVar0)
(00001158 5 0		UnVar0)
(0000115A 15 57 0		JMP 00001196)
(0000115D 20 2 2 2 0)
(00001162 9 200 2		'*load-verbose*)
(00001165 2		T)
(00001166 9 199 2		'*load-filename*)
(00001169 4 1 0		UpVar1-0)
(0000116C 9 79 3		'filename)
(0000116F 81 2 86 3 1 0		slot-value)
(00001175 24 4 0)
(00001178 5 1		UnVar1)
(0000117A 13 13 0		nil->JMP 0000118A)
(0000117D 5 1		UnVar1)
(0000117F 5 0		UnVar0)
(00001181 53 2 203 2 1 32		rep-cntx.load-stream)
(00001187 15 8 0		JMP 00001192)
(0000118A 5 0		UnVar0)
(0000118C 81 1 202 2 1 0		load)
(00001192 25 2 0)
(00001195 22		ret)
(00001196 12 190 3		'(4445 nil))
(00001199 5 0		UnVar0)
(0000119B 9 229 2		'l-context)
(0000119E 81 2 86 3 1 0		slot-value)
(000011A4 14 3 0		T->JMP 000011AA)
(000011A7 3 214 2		_%curr-rep-cntx%)
(000011AA 50 0		0)
(000011AC 5 0		UnVar0)
(000011AE 81 1 209 2 1 0		TBuf.length)
(000011B4 42		cons)
(000011B5 2		T)
(000011B6 47 5 201 2 32 32		process-selection-istream)
;;;def filename-from-selection? 4540
(000011BC 20 3 1 1 0)
(000011C1 100 1		UNVar1)
(000011C3 5 0		UnVar0)
(000011C5 81 1 135 3 1 0		TWinp)
(000011CB 13 3 0		nil->JMP 000011D1)
(000011CE 15 5 0		JMP 000011D6)
(000011D1 3 205 2		*active-mdiwindow*)
(000011D4 8 0		UnVar0)
(000011D6 5 0		UnVar0)
(000011D8 51 0 1 0 0		256)
(000011DD 53 2 198 2 1 32		twin-active-selection)
(000011E3 11)
(000011E4 8 1		UnVar1)
(000011E6 63		nil->ret)
(000011E7 9 41 3		"")
(000011EA 9 197 2		" \t\n\r<>:|")
(000011ED 5 1		UnVar1)
(000011EF 81 2 196 2 1 0		string-trim)
(000011F5 11)
(000011F6 8 1		UnVar1)
(000011F8 81 2 3 3 1 0		equal)
(000011FE 13 2 0		nil->JMP 00001203)
(00001201 1		nil)
(00001202 22		ret)
(00001203 5 1		UnVar1)
(00001205 50 0		0)
(00001207 81 2 195 2 1 0		char)
(0000120D 50 34		34)
(0000120F 38		=)
(00001210 61 27 0		nil->JMP 0000122E)
(00001213 5 1		UnVar1)
(00001215 81 1 194 2 1 0		make-string-input-stream)
(0000121B 8 2		UnVar2)
(0000121D 5 2		UnVar2)
(0000121F 81 1 193 2 1 0		read-char)
(00001225 10)
(00001226 5 2		UnVar2)
(00001228 81 1 192 2 1 0		_parse-string)
(0000122E 62		T->ret)
(0000122F 5 1		UnVar1)
(00001231 22		ret)
;;;def get-filename-to-load 4658
(00001232 20 7 1 3 0)
(00001237 100 3		UNVar3)
(00001239 100 4		UNVar4)
(0000123B 100 5		UNVar5)
(0000123D 5 1		UnVar1)
(0000123F 13 3 0		nil->JMP 00001245)
(00001242 15 16 0		JMP 00001255)
(00001245 9 107 3		"VLMSG.DLL")
(00001248 51 6 84 0 0		21510)
(0000124D 81 2 106 3 1 0		string-resource)
(00001253 8 1		UnVar1)
(00001255 5 0		UnVar0)
(00001257 9 229 2		'l-context)
(0000125A 81 2 86 3 1 0		slot-value)
(00001260 14 3 0		T->JMP 00001266)
(00001263 3 214 2		_%curr-rep-cntx%)
(00001266 53 1 228 2 1 32		object-id)
(0000126C 8 5		UnVar5)
(0000126E 5 0		UnVar0)
(00001270 53 1 191 2 1 32		ed-dflt-dir?)
(00001276 14 12 0		T->JMP 00001285)
(00001279 3 190 2		%last-file-to-load-dir%)
(0000127C 14 6 0		T->JMP 00001285)
(0000127F 81 0 49 3 1 0		chdir)
(00001285 8 4		UnVar4)
(00001287 5 0		UnVar0)
(00001289 95 1 188 17 0 0		filename-from-selection?)
(0000128F 11)
(00001290 8 3		UnVar3)
(00001292 13 107 0		nil->JMP 00001300)
(00001295 5 5		UnVar5)
(00001297 9 15 3		':AUTOLISP)
(0000129A 38		=)
(0000129B 13 35 0		nil->JMP 000012C1)
(0000129E 5 3		UnVar3)
(000012A0 9 189 2		".LSP")
(000012A3 9 188 2		".MNL")
(000012A6 5 2		UnVar2)
(000012A8 13 4 0		nil->JMP 000012AF)
(000012AB 1		nil)
(000012AC 15 3 0		JMP 000012B2)
(000012AF 9 187 2		'(".FAS" ".VLX"))
(000012B2 81 3 186 2 1 0		list*)
(000012B8 53 2 185 2 1 32		al-find-lib-file)
(000012BE 15 36 0		JMP 000012E5)
(000012C1 5 3		UnVar3)
(000012C3 5 4		UnVar4)
(000012C5 3 4 3		*load-path*)
(000012C8 42		cons)
(000012C9 5 2		UnVar2)
(000012CB 13 4 0		nil->JMP 000012D2)
(000012CE 1		nil)
(000012CF 15 3 0		JMP 000012D5)
(000012D2 9 184 2		'(".FSL" ".OBX"))
(000012D5 3 183 2		*lisp-source-ext-list*)
(000012D8 81 2 182 2 1 0		append)
(000012DE 2		T)
(000012DF 81 4 47 3 1 0		find-file)
(000012E5 11)
(000012E6 8 3		UnVar3)
(000012E8 13 21 0		nil->JMP 00001300)
(000012EB 9 181 2		"~a:\n~a ?")
(000012EE 5 1		UnVar1)
(000012F0 5 3		UnVar3)
(000012F2 53 3 223 2 1 32		yes-or-no-p)
(000012F8 13 3 0		nil->JMP 000012FE)
(000012FB 15 2 0		JMP 00001300)
(000012FE 100 3		UNVar3)
(00001300 5 3		UnVar3)
(00001302 13 3 0		nil->JMP 00001308)
(00001305 15 142 0		JMP 00001396)
(00001308 5 1		UnVar1)
(0000130A 50 2		2)
(0000130C 3 180 2		*source-file-filters*)
(0000130F 81 2 179 2 1 0		nth)
(00001315 50 3		3)
(00001317 3 180 2		*source-file-filters*)
(0000131A 81 2 179 2 1 0		nth)
(00001320 57 2 0		list)
(00001323 5 2		UnVar2)
(00001325 13 4 0		nil->JMP 0000132C)
(00001328 1		nil)
(00001329 15 69 0		JMP 00001371)
(0000132C 5 5		UnVar5)
(0000132E 9 15 3		':AUTOLISP)
(00001331 38		=)
(00001332 13 40 0		nil->JMP 0000135D)
(00001335 9 107 3		"VLMSG.DLL")
(00001338 51 16 84 0 0		21520)
(0000133D 81 2 106 3 1 0		string-resource)
(00001343 9 178 2		"*.FAS")
(00001346 9 107 3		"VLMSG.DLL")
(00001349 51 26 84 0 0		21530)
(0000134E 81 2 106 3 1 0		string-resource)
(00001354 9 177 2		"*.VLX")
(00001357 57 4 0		list)
(0000135A 15 20 0		JMP 00001371)
(0000135D 9 107 3		"VLMSG.DLL")
(00001360 51 36 84 0 0		21540)
(00001365 81 2 106 3 1 0		string-resource)
(0000136B 9 176 2		"*.FSL;*.OBX")
(0000136E 57 2 0		list)
(00001371 9 107 3		"VLMSG.DLL")
(00001374 51 46 84 0 0		21550)
(00001379 81 2 106 3 1 0		string-resource)
(0000137F 9 175 2		"*.*")
(00001382 57 2 0		list)
(00001385 81 3 174 2 1 0		nconc)
(0000138B 2		T)
(0000138C 5 4		UnVar4)
(0000138E 81 4 173 2 1 0		choose-file-dialog)
(00001394 8 3		UnVar3)
(00001396 5 3		UnVar3)
(00001398 13 134 0		nil->JMP 00001421)
(0000139B 5 3		UnVar3)
(0000139D 53 1 46 3 1 32		file-absolute-name)
(000013A3 8 3		UnVar3)
(000013A5 5 3		UnVar3)
(000013A7 81 1 172 2 1 0		filename-directory)
(000013AD 6 190 2		%last-file-to-load-dir%)
(000013B0 5 3		UnVar3)
(000013B2 53 1 105 3 1 32		find-opened-editor)
(000013B8 8 0		UnVar0)
(000013BA 5 0		UnVar0)
(000013BC 61 8 0		nil->JMP 000013C7)
(000013BF 5 0		UnVar0)
(000013C1 53 1 90 3 1 32		needs-save-p)
(000013C7 13 87 0		nil->JMP 00001421)
(000013CA 5 0		UnVar0)
(000013CC 53 1 89 3 1 32		mdiwindow-show-up)
(000013D2 10)
(000013D3 3 88 3		*yes-no-cancel-alert*)
(000013D6 9 107 3		"VLMSG.DLL")
(000013D9 51 56 84 0 0		21560)
(000013DE 81 2 106 3 1 0		string-resource)
(000013E4 5 3		UnVar3)
(000013E6 53 3 85 3 1 32		alert)
(000013EC 8 4		UnVar4)
(000013EE 5 4		UnVar4)
(000013F0 8 6		UnVar6)
(000013F2 5 6		UnVar6)
(000013F4 9 84 3		':YES)
(000013F7 38		=)
(000013F8 13 12 0		nil->JMP 00001407)
(000013FB 5 0		UnVar0)
(000013FD 53 1 83 3 1 32		save!)
(00001403 10)
(00001404 15 26 0		JMP 00001421)
(00001407 5 6		UnVar6)
(00001409 9 82 3		':NO)
(0000140C 38		=)
(0000140D 13 3 0		nil->JMP 00001413)
(00001410 15 14 0		JMP 00001421)
(00001413 5 6		UnVar6)
(00001415 9 72 3		':CANCEL)
(00001418 38		=)
(00001419 13 5 0		nil->JMP 00001421)
(0000141C 100 3		UNVar3)
(0000141E 15 0 0		JMP 00001421)
(00001421 5 3		UnVar3)
(00001423 22		ret)
;;;def load-file! 5156
(00001424 21 5 1 1 0)
(00001429 100 1		UNVar1)
(0000142B 100 2		UNVar2)
(0000142D 5 0		UnVar0)
(0000142F 81 1 135 3 1 0		TWinp)
(00001435 13 3 0		nil->JMP 0000143B)
(00001438 15 5 0		JMP 00001440)
(0000143B 3 205 2		*active-mdiwindow*)
(0000143E 8 0		UnVar0)
(00001440 5 0		UnVar0)
(00001442 9 107 3		"VLMSG.DLL")
(00001445 51 66 84 0 0		21570)
(0000144A 81 2 106 3 1 0		string-resource)
(00001450 95 2 50 18 0 0		get-filename-to-load)
(00001456 11)
(00001457 8 2		UnVar2)
(00001459 63		nil->ret)
(0000145A 5 0		UnVar0)
(0000145C 9 229 2		'l-context)
(0000145F 81 2 86 3 1 0		slot-value)
(00001465 14 3 0		T->JMP 0000146B)
(00001468 3 214 2		_%curr-rep-cntx%)
(0000146B 8 1		UnVar1)
(0000146D 5 1		UnVar1)
(0000146F 53 1 210 2 1 32		cntx-window-show-up)
(00001475 10)
(00001476 9 200 2		'*load-verbose*)
(00001479 2		T)
(0000147A 24 2 0)
(0000147D 5 1		UnVar1)
(0000147F 13 128 0		nil->JMP 00001502)
(00001482 5 1		UnVar1)
(00001484 53 1 228 2 1 32		object-id)
(0000148A 9 15 3		':AUTOLISP)
(0000148D 38		=)
(0000148E 13 11 0		nil->JMP 0000149C)
(00001491 5 2		UnVar2)
(00001493 53 1 171 2 1 32		as:load-file)
(00001499 15 99 0		JMP 000014FF)
(0000149C 9 199 2		'*load-filename*)
(0000149F 5 2		UnVar2)
(000014A1 24 2 0)
(000014A4 5 2		UnVar2)
(000014A6 9 44 3		':INPUT)
(000014A9 81 2 64 3 1 0		open)
(000014AF 8 3		UnVar3)
(000014B1 5 3		UnVar3)
(000014B3 8 4		UnVar4)
(000014B5 15 35 0		JMP 000014DB)
(000014B8 20 0 0 0 0)
(000014BD 4 1 3		UpVar1-3)
(000014C0 81 1 63 3 1 0		streamp)
(000014C6 63		nil->ret)
(000014C7 4 1 3		UpVar1-3)
(000014CA 81 1 62 3 1 0		open-streamp)
(000014D0 63		nil->ret)
(000014D1 4 1 3		UpVar1-3)
(000014D4 81 1 61 3 1 0		close)
(000014DA 22		ret)
(000014DB 12 189 3		'(5304 -unwind-cleanup-))
(000014DE 15 17 0		JMP 000014F2)
(000014E1 20 0 0 0 0)
(000014E6 4 1 1		UpVar1-1)
(000014E9 4 1 4		UpVar1-4)
(000014EC 47 2 203 2 32 32		rep-cntx.load-stream)
(000014F2 12 188 3		'(5345 -unwind-protect-))
(000014F5 1		nil)
(000014F6 81 3 117 3 1 0		_unwinded-apply)
(000014FC 25 1 0)
(000014FF 15 8 0		JMP 0000150A)
(00001502 5 2		UnVar2)
(00001504 81 1 202 2 1 0		load)
(0000150A 25 1 0)
(0000150D 22		ret)
;;;def !?editor-revert 5390
(0000150E 20 2 1 1 0)
(00001513 100 1		UNVar1)
(00001515 5 0		UnVar0)
(00001517 81 1 170 2 1 0		class-of)
(0000151D 9 79 3		'filename)
(00001520 81 2 169 2 1 0		slot-index?)
(00001526 11)
(00001527 8 1		UnVar1)
(00001529 63		nil->ret)
(0000152A 5 0		UnVar0)
(0000152C 5 1		UnVar1)
(0000152E 81 2 168 2 1 0		slot-value-by-index)
(00001534 63		nil->ret)
(00001535 2		T)
(00001536 22		ret)
;;;def >@editor-revert 5431
(00001537 20 1 1 1 0)
(0000153C 3 205 2		*active-mdiwindow*)
(0000153F 95 1 14 21 0 0		!?editor-revert)
(00001545 35		not)
(00001546 5 0		UnVar0)
(00001548 45 5		IDFun5)
(0000154A 22		ret)
;;;def !editor-revert 5451
(0000154B 20 3 1 1 0)
(00001550 100 1		UNVar1)
(00001552 100 2		UNVar2)
(00001554 5 0		UnVar0)
(00001556 53 1 89 3 1 32		mdiwindow-show-up)
(0000155C 10)
(0000155D 5 0		UnVar0)
(0000155F 9 79 3		'filename)
(00001562 81 2 86 3 1 0		slot-value)
(00001568 11)
(00001569 8 2		UnVar2)
(0000156B 13 224 0		nil->JMP 0000164E)
(0000156E 5 0		UnVar0)
(00001570 9 81 3		'is-loaded)
(00001573 81 2 86 3 1 0		slot-value)
(00001579 13 34 0		nil->JMP 0000159E)
(0000157C 3 22 3		*stop-alert*)
(0000157F 9 107 3		"VLMSG.DLL")
(00001582 51 86 84 0 0		21590)
(00001587 81 2 106 3 1 0		string-resource)
(0000158D 5 0		UnVar0)
(0000158F 9 87 3		'caption)
(00001592 81 2 86 3 1 0		slot-value)
(00001598 47 3 85 3 32 32		alert)
(0000159E 5 2		UnVar2)
(000015A0 1		nil)
(000015A1 1		nil)
(000015A2 2		T)
(000015A3 81 4 47 3 1 0		find-file)
(000015A9 11)
(000015AA 8 2		UnVar2)
(000015AC 13 125 0		nil->JMP 0000162C)
(000015AF 9 107 3		"VLMSG.DLL")
(000015B2 51 106 84 0 0		21610)
(000015B7 81 2 106 3 1 0		string-resource)
(000015BD 5 2		UnVar2)
(000015BF 53 2 223 2 1 32		yes-or-no-p)
(000015C5 13 98 0		nil->JMP 0000162A)
(000015C8 5 0		UnVar0)
(000015CA 81 1 167 2 1 0		TWin.cpos)
(000015D0 8 1		UnVar1)
(000015D2 5 0		UnVar0)
(000015D4 1		nil)
(000015D5 9 166 2		'mark-ring)
(000015D8 81 3 78 3 1 0		slot-value<-)
(000015DE 10)
(000015DF 5 0		UnVar0)
(000015E1 5 2		UnVar2)
(000015E3 53 2 165 2 1 32		read-from-file)
(000015E9 60 23 0		T->JMP 00001603)
(000015EC 9 107 3		"VLMSG.DLL")
(000015EF 51 116 84 0 0		21620)
(000015F4 81 2 106 3 1 0		string-resource)
(000015FA 5 2		UnVar2)
(000015FC 81 2 109 3 1 0		_msg-err)
(00001602 10)
(00001603 5 0		UnVar0)
(00001605 1		nil)
(00001606 81 2 73 3 1 0		TBuf.set-mod-tick)
(0000160C 10)
(0000160D 5 0		UnVar0)
(0000160F 81 1 164 2 1 0		TBuf.undo-reset)
(00001615 10)
(00001616 5 0		UnVar0)
(00001618 5 1		UnVar1)
(0000161A 1		nil)
(0000161B 81 3 208 2 1 0		TWin.cpos<-)
(00001621 10)
(00001622 5 0		UnVar0)
(00001624 47 1 102 3 32 32		update-host-spouse)
(0000162A 1		nil)
(0000162B 22		ret)
(0000162C 3 22 3		*stop-alert*)
(0000162F 9 107 3		"VLMSG.DLL")
(00001632 51 96 84 0 0		21600)
(00001637 81 2 106 3 1 0		string-resource)
(0000163D 5 0		UnVar0)
(0000163F 9 79 3		'filename)
(00001642 81 2 86 3 1 0		slot-value)
(00001648 47 3 85 3 32 32		alert)
(0000164E 3 22 3		*stop-alert*)
(00001651 9 107 3		"VLMSG.DLL")
(00001654 51 76 84 0 0		21580)
(00001659 81 2 106 3 1 0		string-resource)
(0000165F 47 2 85 3 32 32		alert)
;;;def new-editor! 5733
(00001665 20 2 1 1 0)
(0000166A 100 1		UNVar1)
(0000166C 5 0		UnVar0)
(0000166E 81 1 135 3 1 0		TWinp)
(00001674 60 5 0		T->JMP 0000167C)
(00001677 3 205 2		*active-mdiwindow*)
(0000167A 8 0		UnVar0)
(0000167C 9 163 2		':CAPTION)
(0000167F 9 107 3		"VLMSG.DLL")
(00001682 51 116 119 0 0		30580)
(00001687 81 2 106 3 1 0		string-resource)
(0000168D 3 162 2		*untitled-num*)
(00001690 81 2 23 3 1 0		_win-format-message)
(00001696 9 20 3		':L-CONTEXT)
(00001699 5 0		UnVar0)
(0000169B 9 229 2		'l-context)
(0000169E 81 2 86 3 1 0		slot-value)
(000016A4 14 3 0		T->JMP 000016AA)
(000016A7 3 214 2		_%curr-rep-cntx%)
(000016AA 53 4 116 3 1 32		editor)
(000016B0 8 1		UnVar1)
(000016B2 3 162 2		*untitled-num*)
(000016B5 79		1+)
(000016B6 6 162 2		*untitled-num*)
(000016B9 5 1		UnVar1)
(000016BB 5 0		UnVar0)
(000016BD 9 31 3		'state)
(000016C0 81 2 86 3 1 0		slot-value)
(000016C6 9 247 2		':MAXIMIZED)
(000016C9 38		=)
(000016CA 47 2 89 3 32 32		mdiwindow-show-up)
;;;def open-editor! 5840
(000016D0 20 4 1 1 0)
(000016D5 100 1		UNVar1)
(000016D7 100 2		UNVar2)
(000016D9 100 3		UNVar3)
(000016DB 5 0		UnVar0)
(000016DD 81 1 135 3 1 0		TWinp)
(000016E3 60 5 0		T->JMP 000016EB)
(000016E6 3 205 2		*active-mdiwindow*)
(000016E9 8 0		UnVar0)
(000016EB 5 0		UnVar0)
(000016ED 53 1 191 2 1 32		ed-dflt-dir?)
(000016F3 14 12 0		T->JMP 00001702)
(000016F6 3 161 2		%last-editor-open-dir%)
(000016F9 14 6 0		T->JMP 00001702)
(000016FC 81 0 49 3 1 0		chdir)
(00001702 8 3		UnVar3)
(00001704 5 0		UnVar0)
(00001706 95 1 188 17 0 0		filename-from-selection?)
(0000170C 11)
(0000170D 8 1		UnVar1)
(0000170F 13 26 0		nil->JMP 0000172C)
(00001712 5 1		UnVar1)
(00001714 5 3		UnVar3)
(00001716 3 160 2		*lisp-source-path*)
(00001719 14 3 0		T->JMP 0000171F)
(0000171C 3 4 3		*load-path*)
(0000171F 42		cons)
(00001720 3 183 2		*lisp-source-ext-list*)
(00001723 2		T)
(00001724 81 4 47 3 1 0		find-file)
(0000172A 8 2		UnVar2)
(0000172C 5 2		UnVar2)
(0000172E 13 3 0		nil->JMP 00001734)
(00001731 15 73 0		JMP 0000177D)
(00001734 5 1		UnVar1)
(00001736 14 2 0		T->JMP 0000173B)
(00001739 5 3		UnVar3)
(0000173B 9 107 3		"VLMSG.DLL")
(0000173E 51 136 84 0 0		21640)
(00001743 81 2 106 3 1 0		string-resource)
(00001749 5 1		UnVar1)
(0000174B 13 4 0		nil->JMP 00001752)
(0000174E 1		nil)
(0000174F 15 34 0		JMP 00001774)
(00001752 5 0		UnVar0)
(00001754 53 1 91 3 1 32		editorp)
(0000175A 61 23 0		nil->JMP 00001774)
(0000175D 5 0		UnVar0)
(0000175F 9 79 3		'filename)
(00001762 81 2 86 3 1 0		slot-value)
(00001768 14 3 0		T->JMP 0000176E)
(0000176B 9 41 3		"")
(0000176E 81 1 159 2 1 0		filename-extension)
(00001774 2		T)
(00001775 53 4 158 2 1 32		choose-editor-file-dialog)
(0000177B 8 2		UnVar2)
(0000177D 5 2		UnVar2)
(0000177F 37 2		consp)
(00001781 13 11 0		nil->JMP 0000178F)
(00001784 5 2		UnVar2)
(00001786 40		car)
(00001787 8 2		UnVar2)
(00001789 2		T)
(0000178A 8 3		UnVar3)
(0000178C 15 2 0		JMP 00001791)
(0000178F 100 3		UNVar3)
(00001791 5 2		UnVar2)
(00001793 13 25 0		nil->JMP 000017AF)
(00001796 5 2		UnVar2)
(00001798 81 1 172 2 1 0		filename-directory)
(0000179E 6 161 2		%last-editor-open-dir%)
(000017A1 5 2		UnVar2)
(000017A3 5 0		UnVar0)
(000017A5 5 3		UnVar3)
(000017A7 95 3 126 24 0 0		open-fresh-editor)
(000017AD 8 1		UnVar1)
(000017AF 5 1		UnVar1)
(000017B1 22		ret)
;;;def fresh-file-editor 6066
(000017B2 20 4 1 3 0)
(000017B7 100 3		UNVar3)
(000017B9 100 3		UNVar3)
(000017BB 5 0		UnVar0)
(000017BD 37 4		stringp)
(000017BF 9 157 2		"VLisp internal: filename should be string")
(000017C2 5 0		UnVar0)
(000017C4 53 3 17 3 1 32		assert)
(000017CA 10)
(000017CB 5 0		UnVar0)
(000017CD 81 1 100 3 1 0		file-readable-p)
(000017D3 13 109 0		nil->JMP 00001843)
(000017D6 5 0		UnVar0)
(000017D8 53 1 105 3 1 32		find-opened-editor)
(000017DE 11)
(000017DF 8 3		UnVar3)
(000017E1 13 58 0		nil->JMP 0000181E)
(000017E4 5 1		UnVar1)
(000017E6 5 3		UnVar3)
(000017E8 9 229 2		'l-context)
(000017EB 81 2 86 3 1 0		slot-value)
(000017F1 38		=)
(000017F2 13 3 0		nil->JMP 000017F8)
(000017F5 15 15 0		JMP 00001807)
(000017F8 3 156 2		*info-alert*)
(000017FB 9 155 2		"Inconsistent context:~% ~a")
(000017FE 5 0		UnVar0)
(00001800 53 3 85 3 1 32		alert)
(00001806 10)
(00001807 5 3		UnVar3)
(00001809 53 1 154 2 1 32		editor.mod-flag)
(0000180F 13 9 0		nil->JMP 0000181B)
(00001812 5 3		UnVar3)
(00001814 95 1 75 21 0 0		!editor-revert)
(0000181A 10)
(0000181B 15 34 0		JMP 00001840)
(0000181E 1		nil)
(0000181F 53 1 68 3 1 32		_purge-*editors*)
(00001825 10)
(00001826 81 0 153 2 1 0		gc)
(0000182C 10)
(0000182D 5 0		UnVar0)
(0000182F 5 1		UnVar1)
(00001831 14 3 0		T->JMP 00001837)
(00001834 3 214 2		_%curr-rep-cntx%)
(00001837 2		T)
(00001838 53 3 152 2 1 32		open-editor)
(0000183E 8 3		UnVar3)
(00001840 15 26 0		JMP 0000185D)
(00001843 3 156 2		*info-alert*)
(00001846 9 107 3		"VLMSG.DLL")
(00001849 51 146 84 0 0		21650)
(0000184E 81 2 106 3 1 0		string-resource)
(00001854 5 0		UnVar0)
(00001856 53 3 85 3 1 32		alert)
(0000185C 10)
(0000185D 5 3		UnVar3)
(0000185F 13 25 0		nil->JMP 0000187B)
(00001862 5 3		UnVar3)
(00001864 9 81 3		'is-loaded)
(00001867 81 2 86 3 1 0		slot-value)
(0000186D 60 11 0		T->JMP 0000187B)
(00001870 5 3		UnVar3)
(00001872 5 2		UnVar2)
(00001874 53 2 74 3 1 32		tbuf.read-only<-)
(0000187A 10)
(0000187B 5 3		UnVar3)
(0000187D 22		ret)
;;;def open-fresh-editor 6270
(0000187E 20 5 1 3 0)
(00001883 100 3		UNVar3)
(00001885 5 1		UnVar1)
(00001887 13 3 0		nil->JMP 0000188D)
(0000188A 15 5 0		JMP 00001892)
(0000188D 3 205 2		*active-mdiwindow*)
(00001890 8 1		UnVar1)
(00001892 5 1		UnVar1)
(00001894 8 4		UnVar4)
(00001896 5 0		UnVar0)
(00001898 5 4		UnVar4)
(0000189A 44 10		IDFun10)
(0000189C 5 2		UnVar2)
(0000189E 95 3 178 23 0 0		fresh-file-editor)
(000018A4 11)
(000018A5 8 3		UnVar3)
(000018A7 63		nil->ret)
(000018A8 5 3		UnVar3)
(000018AA 5 4		UnVar4)
(000018AC 44 1		IDFun1)
(000018AE 9 247 2		':MAXIMIZED)
(000018B1 38		=)
(000018B2 53 2 89 3 1 32		mdiwindow-show-up)
(000018B8 10)
(000018B9 5 3		UnVar3)
(000018BB 22		ret)
;;;def !?save-all-editors 6332
(000018BC 20 3 0 1 0)
(000018C1 3 151 2		*editors*)
(000018C4 8 1		UnVar1)
(000018C6 100 2		UNVar2)
(000018C8 15 5 0		JMP 000018D0)
(000018CB 5 1		UnVar1)
(000018CD 41		cdr)
(000018CE 8 1		UnVar1)
(000018D0 5 1		UnVar1)
(000018D2 61 13 0		nil->JMP 000018E2)
(000018D5 5 1		UnVar1)
(000018D7 40		car)
(000018D8 53 1 90 3 1 32		needs-save-p)
(000018DE 11)
(000018DF 8 2		UnVar2)
(000018E1 35		not)
(000018E2 60 230 255		T->JMP 000018CB)
(000018E5 5 2		UnVar2)
(000018E7 22		ret)
;;;def >@save-all-editors 6376
(000018E8 20 1 1 1 0)
(000018ED 95 0 188 24 0 0		!?save-all-editors)
(000018F3 35		not)
(000018F4 5 0		UnVar0)
(000018F6 45 5		IDFun5)
(000018F8 22		ret)
;;;def save-all-editors! 6393
(000018F9 20 3 0 1 0)
(000018FE 81 0 150 2 1 0		_vill-demo-p)
(00001904 13 20 0		nil->JMP 0000191B)
(00001907 9 107 3		"VLMSG.DLL")
(0000190A 51 156 84 0 0		21660)
(0000190F 81 2 106 3 1 0		string-resource)
(00001915 47 1 149 2 32 32		_demov-nocmd)
(0000191B 81 0 93 3 1 0		list-mdiwindows-with-host-spouse)
(00001921 8 1		UnVar1)
(00001923 100 2		UNVar2)
(00001925 15 41 0		JMP 00001951)
(00001928 5 1		UnVar1)
(0000192A 40		car)
(0000192B 8 2		UnVar2)
(0000192D 5 1		UnVar1)
(0000192F 41		cdr)
(00001930 8 1		UnVar1)
(00001932 5 2		UnVar2)
(00001934 53 1 91 3 1 32		editorp)
(0000193A 61 8 0		nil->JMP 00001945)
(0000193D 5 2		UnVar2)
(0000193F 53 1 90 3 1 32		needs-save-p)
(00001945 13 9 0		nil->JMP 00001951)
(00001948 5 2		UnVar2)
(0000194A 53 1 83 3 1 32		save!)
(00001950 10)
(00001951 5 1		UnVar1)
(00001953 60 210 255		T->JMP 00001928)
(00001956 1		nil)
(00001957 22		ret)
;;;def exit! 6488
(00001958 20 1 0 1 0)
(0000195D 81 0 148 2 1 0		in-ads-check)
(00001963 13 42 0		nil->JMP 00001990)
(00001966 53 0 147 2 1 32		debug-quit!?)
(0000196C 13 12 0		nil->JMP 0000197B)
(0000196F 9 146 2		"Reset break loop to close IDE?")
(00001972 53 1 223 2 1 32		yes-or-no-p)
(00001978 15 1 0		JMP 0000197C)
(0000197B 2		T)
(0000197C 63		nil->ret)
(0000197D 95 0 201 86 0 0		hide-vlisp-windows)
(00001983 10)
(00001984 2		T)
(00001985 6 145 2		*exit_to_acad_var*)
(00001988 2		T)
(00001989 81 1 144 2 1 0		_protected-context-restore)
(0000198F 22		ret)
(00001990 81 0 143 2 1 0		query-end-session)
(00001996 22		ret)
;;;def nil 6551
(00001997 20 0 0 0 0)
(0000199C 3 33 3		*desktop-autosave*)
(0000199F 13 51 0		nil->JMP 000019D5)
(000019A2 9 107 3		"VLMSG.DLL")
(000019A5 51 186 84 0 0		21690)
(000019AA 81 2 106 3 1 0		string-resource)
(000019B0 81 1 45 3 1 0		ales-prompt-msg)
(000019B6 10)
(000019B7 1		nil)
(000019B8 2		T)
(000019B9 95 2 131 4 0 0		lpp-save-config)
(000019BF 10)
(000019C0 9 107 3		"VLMSG.DLL")
(000019C3 51 196 84 0 0		21700)
(000019C8 81 2 106 3 1 0		string-resource)
(000019CE 81 1 45 3 1 0		ales-prompt-msg)
(000019D4 10)
(000019D5 47 0 142 2 32 32		mktemp-cleanup)
;;;def !vkeys-flags-info 6619
(000019DB 20 1 1 1 0)
(000019E0 1		nil)
(000019E1 22		ret)
;;;def vkeys-Shift-p 6626
(000019E2 20 0 0 0 0)
(000019E7 3 141 2		__tcmd-stor__)
(000019EA 81 1 140 2 1 0		test-command)
(000019F0 63		nil->ret)
(000019F1 3 141 2		__tcmd-stor__)
(000019F4 40		car)
(000019F5 9 139 2		'!vkeys-flags-info)
(000019F8 38		=)
(000019F9 63		nil->ret)
(000019FA 50 0		0)
(000019FC 3 141 2		__tcmd-stor__)
(000019FF 41		cdr)
(00001A00 50 4		4)
(00001A02 81 2 138 2 1 0		logand)
(00001A08 81 2 137 2 1 0		/=&)
(00001A0E 22		ret)
;;;def vkeys-Ctrl-p 6671
(00001A0F 20 0 0 0 0)
(00001A14 3 141 2		__tcmd-stor__)
(00001A17 81 1 140 2 1 0		test-command)
(00001A1D 63		nil->ret)
(00001A1E 3 141 2		__tcmd-stor__)
(00001A21 40		car)
(00001A22 9 139 2		'!vkeys-flags-info)
(00001A25 38		=)
(00001A26 63		nil->ret)
(00001A27 50 0		0)
(00001A29 3 141 2		__tcmd-stor__)
(00001A2C 41		cdr)
(00001A2D 50 8		8)
(00001A2F 81 2 138 2 1 0		logand)
(00001A35 81 2 137 2 1 0		/=&)
(00001A3B 22		ret)
;;;def expand-selection 6716
(00001A3C 20 6 3 3 0)
(00001A41 100 3		UNVar3)
(00001A43 100 4		UNVar4)
(00001A45 100 5		UNVar5)
(00001A47 5 0		UnVar0)
(00001A49 53 1 217 2 1 32		selection)
(00001A4F 8 5		UnVar5)
(00001A51 5 5		UnVar5)
(00001A53 41		cdr)
(00001A54 8 4		UnVar4)
(00001A56 5 5		UnVar5)
(00001A58 40		car)
(00001A59 8 3		UnVar3)
(00001A5B 5 5		UnVar5)
(00001A5D 5 1		UnVar1)
(00001A5F 5 2		UnVar2)
(00001A61 5 4		UnVar4)
(00001A63 5 3		UnVar3)
(00001A65 81 4 136 2 1 0		MIN)
(00001A6B 81 2 135 2 1 0		setcar)
(00001A71 10)
(00001A72 5 5		UnVar5)
(00001A74 5 1		UnVar1)
(00001A76 5 2		UnVar2)
(00001A78 5 4		UnVar4)
(00001A7A 5 3		UnVar3)
(00001A7C 81 4 134 2 1 0		MAX)
(00001A82 81 2 225 2 1 0		setcdr)
(00001A88 10)
(00001A89 5 4		UnVar4)
(00001A8B 5 5		UnVar5)
(00001A8D 40		car)
(00001A8E 71		-)
(00001A8F 5 5		UnVar5)
(00001A91 41		cdr)
(00001A92 5 4		UnVar4)
(00001A94 71		-)
(00001A95 76		<)
(00001A96 13 28 0		nil->JMP 00001AB5)
(00001A99 5 5		UnVar5)
(00001A9B 40		car)
(00001A9C 8 4		UnVar4)
(00001A9E 5 5		UnVar5)
(00001AA0 5 5		UnVar5)
(00001AA2 41		cdr)
(00001AA3 81 2 135 2 1 0		setcar)
(00001AA9 10)
(00001AAA 5 5		UnVar5)
(00001AAC 5 4		UnVar4)
(00001AAE 81 2 225 2 1 0		setcdr)
(00001AB4 10)
(00001AB5 5 0		UnVar0)
(00001AB7 5 5		UnVar5)
(00001AB9 47 2 133 2 32 32		selection<-)
;;;def nil 6847
(00001ABF 20 10 4 4 0)
(00001AC4 100 4		UNVar4)
(00001AC6 100 5		UNVar5)
(00001AC8 100 6		UNVar6)
(00001ACA 100 7		UNVar7)
(00001ACC 100 8		UNVar8)
(00001ACE 100 9		UNVar9)
(00001AD0 5 0		UnVar0)
(00001AD2 81 1 132 2 1 0		TBuf.lex-scanner-id)
(00001AD8 11)
(00001AD9 8 9		UnVar9)
(00001ADB 13 90 0		nil->JMP 00001B38)
(00001ADE 5 1		UnVar1)
(00001AE0 50 0		0)
(00001AE2 75		>)
(00001AE3 13 82 0		nil->JMP 00001B38)
(00001AE6 5 0		UnVar0)
(00001AE8 5 1		UnVar1)
(00001AEA 53 2 131 2 1 32		lex-token-at-left)
(00001AF0 11)
(00001AF1 8 8		UnVar8)
(00001AF3 13 66 0		nil->JMP 00001B38)
(00001AF6 5 8		UnVar8)
(00001AF8 41		cdr)
(00001AF9 41		cdr)
(00001AFA 13 53 0		nil->JMP 00001B32)
(00001AFD 5 8		UnVar8)
(00001AFF 40		car)
(00001B00 9 130 2		'(:STR :COMM2 :COMM1))
(00001B03 81 2 114 3 1 0		memq)
(00001B09 61 7 0		nil->JMP 00001B13)
(00001B0C 5 8		UnVar8)
(00001B0E 41		cdr)
(00001B0F 41		cdr)
(00001B10 5 1		UnVar1)
(00001B12 75		>)
(00001B13 14 25 0		T->JMP 00001B2F)
(00001B16 5 8		UnVar8)
(00001B18 40		car)
(00001B19 9 129 2		':COMM1)
(00001B1C 38		=)
(00001B1D 61 15 0		nil->JMP 00001B2F)
(00001B20 5 1		UnVar1)
(00001B22 5 0		UnVar0)
(00001B24 5 8		UnVar8)
(00001B26 41		cdr)
(00001B27 40		car)
(00001B28 81 2 128 2 1 0		TBuf.EOL-pos)
(00001B2E 78		<=)
(00001B2F 15 1 0		JMP 00001B33)
(00001B32 2		T)
(00001B33 13 2 0		nil->JMP 00001B38)
(00001B36 100 9		UNVar9)
(00001B38 5 0		UnVar0)
(00001B3A 5 1		UnVar1)
(00001B3C 81 2 127 2 1 0		TBuf.char-at)
(00001B42 8 6		UnVar6)
(00001B44 5 1		UnVar1)
(00001B46 50 0		0)
(00001B48 75		>)
(00001B49 61 18 0		nil->JMP 00001B5E)
(00001B4C 5 0		UnVar0)
(00001B4E 5 0		UnVar0)
(00001B50 5 1		UnVar1)
(00001B52 81 2 126 2 1 0		TBuf.prev-pos)
(00001B58 81 2 127 2 1 0		TBuf.char-at)
(00001B5E 8 5		UnVar5)
(00001B60 5 9		UnVar9)
(00001B62 13 3 0		nil->JMP 00001B68)
(00001B65 15 154 0		JMP 00001C02)
(00001B68 5 6		UnVar6)
(00001B6A 9 125 2		"([{")
(00001B6D 81 2 124 2 1 0		string-position)
(00001B73 13 17 0		nil->JMP 00001B87)
(00001B76 5 0		UnVar0)
(00001B78 5 1		UnVar1)
(00001B7A 1		nil)
(00001B7B 2		T)
(00001B7C 81 4 123 2 1 0		TBuf.sexp-end-pos)
(00001B82 8 4		UnVar4)
(00001B84 15 123 0		JMP 00001C02)
(00001B87 5 6		UnVar6)
(00001B89 50 34		34)
(00001B8B 38		=)
(00001B8C 13 44 0		nil->JMP 00001BBB)
(00001B8F 5 0		UnVar0)
(00001B91 9 122 2		"\"")
(00001B94 2		T)
(00001B95 5 0		UnVar0)
(00001B97 5 1		UnVar1)
(00001B99 81 2 121 2 1 0		TBuf.next-pos)
(00001B9F 81 4 120 2 1 0		TBuf.scan-chars-forward)
(00001BA5 8 4		UnVar4)
(00001BA7 5 4		UnVar4)
(00001BA9 13 12 0		nil->JMP 00001BB8)
(00001BAC 5 0		UnVar0)
(00001BAE 5 4		UnVar4)
(00001BB0 81 2 121 2 1 0		TBuf.next-pos)
(00001BB6 8 4		UnVar4)
(00001BB8 15 71 0		JMP 00001C02)
(00001BBB 5 5		UnVar5)
(00001BBD 61 11 0		nil->JMP 00001BCB)
(00001BC0 5 5		UnVar5)
(00001BC2 9 119 2		"}])")
(00001BC5 81 2 124 2 1 0		string-position)
(00001BCB 13 17 0		nil->JMP 00001BDF)
(00001BCE 5 0		UnVar0)
(00001BD0 5 1		UnVar1)
(00001BD2 1		nil)
(00001BD3 2		T)
(00001BD4 81 4 118 2 1 0		TBuf.sexp-beg-pos)
(00001BDA 8 4		UnVar4)
(00001BDC 15 35 0		JMP 00001C02)
(00001BDF 5 5		UnVar5)
(00001BE1 50 34		34)
(00001BE3 38		=)
(00001BE4 13 27 0		nil->JMP 00001C02)
(00001BE7 5 0		UnVar0)
(00001BE9 9 122 2		"\"")
(00001BEC 2		T)
(00001BED 5 0		UnVar0)
(00001BEF 5 1		UnVar1)
(00001BF1 81 2 126 2 1 0		TBuf.prev-pos)
(00001BF7 81 4 117 2 1 0		TBuf.scan-chars-backward)
(00001BFD 8 4		UnVar4)
(00001BFF 15 0 0		JMP 00001C02)
(00001C02 5 9		UnVar9)
(00001C04 61 3 0		nil->JMP 00001C0A)
(00001C07 5 4		UnVar4)
(00001C09 35		not)
(00001C0A 13 124 0		nil->JMP 00001C89)
(00001C0D 5 0		UnVar0)
(00001C0F 5 1		UnVar1)
(00001C11 81 2 116 2 1 0		TBuf.scan-lex-token)
(00001C17 8 7		UnVar7)
(00001C19 5 7		UnVar7)
(00001C1B 9 115 2		'(1 9))
(00001C1E 81 2 114 3 1 0		memq)
(00001C24 13 8 0		nil->JMP 00001C2F)
(00001C27 9 114 2		':beep)
(00001C2A 8 4		UnVar4)
(00001C2C 15 90 0		JMP 00001C89)
(00001C2F 5 7		UnVar7)
(00001C31 50 10		10)
(00001C33 81 2 8 3 1 0		eqcar)
(00001C39 13 35 0		nil->JMP 00001C5F)
(00001C3C 5 6		UnVar6)
(00001C3E 9 125 2		"([{")
(00001C41 81 2 124 2 1 0		string-position)
(00001C47 13 18 0		nil->JMP 00001C5C)
(00001C4A 5 0		UnVar0)
(00001C4C 5 1		UnVar1)
(00001C4E 81 2 123 2 1 0		TBuf.sexp-end-pos)
(00001C54 14 3 0		T->JMP 00001C5A)
(00001C57 9 114 2		':beep)
(00001C5A 8 4		UnVar4)
(00001C5C 15 42 0		JMP 00001C89)
(00001C5F 5 7		UnVar7)
(00001C61 50 1		1)
(00001C63 81 2 8 3 1 0		eqcar)
(00001C69 13 8 0		nil->JMP 00001C74)
(00001C6C 5 7		UnVar7)
(00001C6E 41		cdr)
(00001C6F 8 4		UnVar4)
(00001C71 15 21 0		JMP 00001C89)
(00001C74 5 7		UnVar7)
(00001C76 50 9		9)
(00001C78 81 2 8 3 1 0		eqcar)
(00001C7E 13 8 0		nil->JMP 00001C89)
(00001C81 5 7		UnVar7)
(00001C83 41		cdr)
(00001C84 8 4		UnVar4)
(00001C86 15 0 0		JMP 00001C89)
(00001C89 5 4		UnVar4)
(00001C8B 13 4 0		nil->JMP 00001C92)
(00001C8E 1		nil)
(00001C8F 15 19 0		JMP 00001CA5)
(00001C92 5 8		UnVar8)
(00001C94 41		cdr)
(00001C95 41		cdr)
(00001C96 61 12 0		nil->JMP 00001CA5)
(00001C99 5 1		UnVar1)
(00001C9B 5 8		UnVar8)
(00001C9D 41		cdr)
(00001C9E 41		cdr)
(00001C9F 81 2 113 2 1 0		=&)
(00001CA5 13 96 0		nil->JMP 00001D08)
(00001CA8 5 8		UnVar8)
(00001CAA 9 112 2		':PAREN)
(00001CAD 81 2 8 3 1 0		eqcar)
(00001CB3 13 35 0		nil->JMP 00001CD9)
(00001CB6 5 5		UnVar5)
(00001CB8 9 119 2		"}])")
(00001CBB 81 2 124 2 1 0		string-position)
(00001CC1 13 18 0		nil->JMP 00001CD6)
(00001CC4 5 0		UnVar0)
(00001CC6 5 1		UnVar1)
(00001CC8 81 2 118 2 1 0		TBuf.sexp-beg-pos)
(00001CCE 14 3 0		T->JMP 00001CD4)
(00001CD1 9 114 2		':beep)
(00001CD4 8 4		UnVar4)
(00001CD6 15 47 0		JMP 00001D08)
(00001CD9 5 8		UnVar8)
(00001CDB 40		car)
(00001CDC 9 111 2		'(:STR :COMM2))
(00001CDF 81 2 114 3 1 0		memq)
(00001CE5 13 9 0		nil->JMP 00001CF1)
(00001CE8 5 8		UnVar8)
(00001CEA 41		cdr)
(00001CEB 40		car)
(00001CEC 8 4		UnVar4)
(00001CEE 15 23 0		JMP 00001D08)
(00001CF1 5 8		UnVar8)
(00001CF3 40		car)
(00001CF4 9 110 2		'(:SYM :INT :REAL :NUM))
(00001CF7 81 2 114 3 1 0		memq)
(00001CFD 13 8 0		nil->JMP 00001D08)
(00001D00 5 8		UnVar8)
(00001D02 41		cdr)
(00001D03 8 4		UnVar4)
(00001D05 15 0 0		JMP 00001D08)
(00001D08 5 4		UnVar4)
(00001D0A 13 3 0		nil->JMP 00001D10)
(00001D0D 15 18 0		JMP 00001D22)
(00001D10 5 0		UnVar0)
(00001D12 5 1		UnVar1)
(00001D14 53 2 109 2 1 32		word-at-pos)
(00001D1A 14 3 0		T->JMP 00001D20)
(00001D1D 9 114 2		':beep)
(00001D20 8 4		UnVar4)
(00001D22 5 4		UnVar4)
(00001D24 9 114 2		':beep)
(00001D27 38		=)
(00001D28 13 7 0		nil->JMP 00001D32)
(00001D2B 81 0 206 2 1 0		message-beep)
(00001D31 22		ret)
(00001D32 5 4		UnVar4)
(00001D34 37 2		consp)
(00001D36 13 73 0		nil->JMP 00001D82)
(00001D39 5 2		UnVar2)
(00001D3B 13 14 0		nil->JMP 00001D4C)
(00001D3E 5 0		UnVar0)
(00001D40 5 4		UnVar4)
(00001D42 40		car)
(00001D43 5 4		UnVar4)
(00001D45 41		cdr)
(00001D46 97 3 65 26 0 0		offset 00001A41)
(00001D4C 5 1		UnVar1)
(00001D4E 5 4		UnVar4)
(00001D50 40		car)
(00001D51 71		-)
(00001D52 5 4		UnVar4)
(00001D54 41		cdr)
(00001D55 5 1		UnVar1)
(00001D57 71		-)
(00001D58 76		<)
(00001D59 13 28 0		nil->JMP 00001D78)
(00001D5C 5 4		UnVar4)
(00001D5E 40		car)
(00001D5F 8 1		UnVar1)
(00001D61 5 4		UnVar4)
(00001D63 5 4		UnVar4)
(00001D65 41		cdr)
(00001D66 81 2 135 2 1 0		setcar)
(00001D6C 10)
(00001D6D 5 4		UnVar4)
(00001D6F 5 1		UnVar1)
(00001D71 81 2 225 2 1 0		setcdr)
(00001D77 10)
(00001D78 5 0		UnVar0)
(00001D7A 5 4		UnVar4)
(00001D7C 47 2 133 2 32 32		selection<-)
(00001D82 5 2		UnVar2)
(00001D84 13 12 0		nil->JMP 00001D93)
(00001D87 5 0		UnVar0)
(00001D89 5 1		UnVar1)
(00001D8B 5 4		UnVar4)
(00001D8D 97 3 65 26 0 0		offset 00001A41)
(00001D93 5 0		UnVar0)
(00001D95 5 4		UnVar4)
(00001D97 5 1		UnVar1)
(00001D99 42		cons)
(00001D9A 47 2 133 2 32 32		selection<-)
;;;def left-button-dblclk! 7584
(00001DA0 20 7 1 1 0)
(00001DA5 100 1		UNVar1)
(00001DA7 100 2		UNVar2)
(00001DA9 100 3		UNVar3)
(00001DAB 100 4		UNVar4)
(00001DAD 95 0 226 25 0 0		vkeys-Shift-p)
(00001DB3 8 3		UnVar3)
(00001DB5 95 0 15 26 0 0		vkeys-Ctrl-p)
(00001DBB 8 2		UnVar2)
(00001DBD 5 0		UnVar0)
(00001DBF 81 1 167 2 1 0		TWin.cpos)
(00001DC5 8 4		UnVar4)
(00001DC7 5 3		UnVar3)
(00001DC9 14 34 0		T->JMP 00001DEE)
(00001DCC 5 2		UnVar2)
(00001DCE 14 29 0		T->JMP 00001DEE)
(00001DD1 5 0		UnVar0)
(00001DD3 81 1 126 3 1 0		type-of)
(00001DD9 9 116 3		'editor)
(00001DDC 38		=)
(00001DDD 14 14 0		T->JMP 00001DEE)
(00001DE0 5 0		UnVar0)
(00001DE2 5 4		UnVar4)
(00001DE4 81 2 108 2 1 0		TWin.position-colors)
(00001DEA 11)
(00001DEB 8 1		UnVar1)
(00001DED 35		not)
(00001DEE 13 14 0		nil->JMP 00001DFF)
(00001DF1 5 0		UnVar0)
(00001DF3 5 4		UnVar4)
(00001DF5 5 3		UnVar3)
(00001DF7 5 2		UnVar2)
(00001DF9 96 4 191 26 0 0		func 00001ABF)
(00001DFF 5 1		UnVar1)
(00001E01 8 5		UnVar5)
(00001E03 100 6		UNVar6)
(00001E05 15 30 0		JMP 00001E26)
(00001E08 5 5		UnVar5)
(00001E0A 40		car)
(00001E0B 8 6		UnVar6)
(00001E0D 5 5		UnVar5)
(00001E0F 41		cdr)
(00001E10 8 5		UnVar5)
(00001E12 5 6		UnVar6)
(00001E14 53 1 107 2 1 32		message-mark-p)
(00001E1A 13 9 0		nil->JMP 00001E26)
(00001E1D 5 6		UnVar6)
(00001E1F 53 1 106 2 1 32		process-message)
(00001E25 10)
(00001E26 5 5		UnVar5)
(00001E28 60 221 255		T->JMP 00001E08)
(00001E2B 1		nil)
(00001E2C 22		ret)
;;;def !goto-bow 7725
(00001E2D 20 3 1 2 0)
(00001E32 100 2		UNVar2)
(00001E34 5 0		UnVar0)
(00001E36 81 1 167 2 1 0		TWin.cpos)
(00001E3C 50 0		0)
(00001E3E 75		>)
(00001E3F 63		nil->ret)
(00001E40 5 0		UnVar0)
(00001E42 5 0		UnVar0)
(00001E44 9 229 2		'l-context)
(00001E47 81 2 86 3 1 0		slot-value)
(00001E4D 53 1 105 2 1 32		cntx-wsep)
(00001E53 50 255		-1)
(00001E55 81 3 104 2 1 0		TBuf.scan-words)
(00001E5B 8 2		UnVar2)
(00001E5D 5 2		UnVar2)
(00001E5F 37 2		consp)
(00001E61 13 4 0		nil->JMP 00001E68)
(00001E64 50 0		0)
(00001E66 8 2		UnVar2)
(00001E68 5 0		UnVar0)
(00001E6A 5 2		UnVar2)
(00001E6C 5 1		UnVar1)
(00001E6E 81 3 208 2 1 0		TWin.cpos<-)
(00001E74 22		ret)
;;;def !select-to-bow 7797
(00001E75 20 1 1 1 0)
(00001E7A 5 0		UnVar0)
(00001E7C 2		T)
(00001E7D 96 2 45 30 0 0		!goto-bow)
;;;def !goto-eow 7811
(00001E83 20 3 1 2 0)
(00001E88 100 2		UNVar2)
(00001E8A 5 0		UnVar0)
(00001E8C 81 1 167 2 1 0		TWin.cpos)
(00001E92 5 0		UnVar0)
(00001E94 81 1 209 2 1 0		TBuf.length)
(00001E9A 76		<)
(00001E9B 63		nil->ret)
(00001E9C 5 0		UnVar0)
(00001E9E 5 0		UnVar0)
(00001EA0 9 229 2		'l-context)
(00001EA3 81 2 86 3 1 0		slot-value)
(00001EA9 53 1 105 2 1 32		cntx-wsep)
(00001EAF 50 1		1)
(00001EB1 81 3 104 2 1 0		TBuf.scan-words)
(00001EB7 8 2		UnVar2)
(00001EB9 5 2		UnVar2)
(00001EBB 37 2		consp)
(00001EBD 13 10 0		nil->JMP 00001ECA)
(00001EC0 5 0		UnVar0)
(00001EC2 81 1 209 2 1 0		TBuf.length)
(00001EC8 8 2		UnVar2)
(00001ECA 5 0		UnVar0)
(00001ECC 5 2		UnVar2)
(00001ECE 5 1		UnVar1)
(00001ED0 81 3 208 2 1 0		TWin.cpos<-)
(00001ED6 22		ret)
;;;def !select-to-eow 7895
(00001ED7 20 1 1 1 0)
(00001EDC 5 0		UnVar0)
(00001EDE 2		T)
(00001EDF 96 2 131 30 0 0		!goto-eow)
;;;def !del-word-bw 7909
(00001EE5 20 5 1 1 0)
(00001EEA 100 1		UNVar1)
(00001EEC 100 2		UNVar2)
(00001EEE 100 3		UNVar3)
(00001EF0 5 0		UnVar0)
(00001EF2 9 229 2		'l-context)
(00001EF5 81 2 86 3 1 0		slot-value)
(00001EFB 53 1 105 2 1 32		cntx-wsep)
(00001F01 8 3		UnVar3)
(00001F03 5 0		UnVar0)
(00001F05 81 1 167 2 1 0		TWin.cpos)
(00001F0B 8 2		UnVar2)
(00001F0D 5 0		UnVar0)
(00001F0F 5 3		UnVar3)
(00001F11 50 255		-1)
(00001F13 81 3 104 2 1 0		TBuf.scan-words)
(00001F19 8 1		UnVar1)
(00001F1B 5 1		UnVar1)
(00001F1D 37 2		consp)
(00001F1F 13 7 0		nil->JMP 00001F29)
(00001F22 50 0		0)
(00001F24 8 1		UnVar1)
(00001F26 15 28 0		JMP 00001F45)
(00001F29 5 0		UnVar0)
(00001F2B 5 3		UnVar3)
(00001F2D 50 1		1)
(00001F2F 5 1		UnVar1)
(00001F31 81 4 104 2 1 0		TBuf.scan-words)
(00001F37 8 4		UnVar4)
(00001F39 5 2		UnVar2)
(00001F3B 5 4		UnVar4)
(00001F3D 75		>)
(00001F3E 13 4 0		nil->JMP 00001F45)
(00001F41 5 4		UnVar4)
(00001F43 8 1		UnVar1)
(00001F45 5 0		UnVar0)
(00001F47 1		nil)
(00001F48 5 1		UnVar1)
(00001F4A 5 2		UnVar2)
(00001F4C 71		-)
(00001F4D 81 3 103 2 1 0		TBuf.delete)
(00001F53 62		T->ret)
(00001F54 81 0 206 2 1 0		message-beep)
(00001F5A 22		ret)
;;;def !del-word-fw 8027
(00001F5B 20 5 1 1 0)
(00001F60 100 1		UNVar1)
(00001F62 100 2		UNVar2)
(00001F64 100 3		UNVar3)
(00001F66 5 0		UnVar0)
(00001F68 9 229 2		'l-context)
(00001F6B 81 2 86 3 1 0		slot-value)
(00001F71 53 1 105 2 1 32		cntx-wsep)
(00001F77 8 3		UnVar3)
(00001F79 5 0		UnVar0)
(00001F7B 81 1 167 2 1 0		TWin.cpos)
(00001F81 8 2		UnVar2)
(00001F83 5 0		UnVar0)
(00001F85 5 3		UnVar3)
(00001F87 50 1		1)
(00001F89 81 3 104 2 1 0		TBuf.scan-words)
(00001F8F 8 1		UnVar1)
(00001F91 5 1		UnVar1)
(00001F93 37 2		consp)
(00001F95 13 13 0		nil->JMP 00001FA5)
(00001F98 5 0		UnVar0)
(00001F9A 81 1 209 2 1 0		TBuf.length)
(00001FA0 8 1		UnVar1)
(00001FA2 15 39 0		JMP 00001FCC)
(00001FA5 5 0		UnVar0)
(00001FA7 5 3		UnVar3)
(00001FA9 50 255		-1)
(00001FAB 5 1		UnVar1)
(00001FAD 81 4 104 2 1 0		TBuf.scan-words)
(00001FB3 8 4		UnVar4)
(00001FB5 5 4		UnVar4)
(00001FB7 37 2		consp)
(00001FB9 13 4 0		nil->JMP 00001FC0)
(00001FBC 50 0		0)
(00001FBE 8 4		UnVar4)
(00001FC0 5 4		UnVar4)
(00001FC2 5 2		UnVar2)
(00001FC4 75		>)
(00001FC5 13 4 0		nil->JMP 00001FCC)
(00001FC8 5 4		UnVar4)
(00001FCA 8 1		UnVar1)
(00001FCC 5 0		UnVar0)
(00001FCE 1		nil)
(00001FCF 5 1		UnVar1)
(00001FD1 5 2		UnVar2)
(00001FD3 71		-)
(00001FD4 81 3 103 2 1 0		TBuf.delete)
(00001FDA 62		T->ret)
(00001FDB 81 0 206 2 1 0		message-beep)
(00001FE1 22		ret)
;;;def kill-chars 8162
(00001FE2 20 5 2 3 0)
(00001FE7 100 3		UNVar3)
(00001FE9 100 4		UNVar4)
(00001FEB 5 0		UnVar0)
(00001FED 5 1		UnVar1)
(00001FEF 1		nil)
(00001FF0 5 2		UnVar2)
(00001FF2 81 4 117 2 1 0		TBuf.scan-chars-backward)
(00001FF8 8 4		UnVar4)
(00001FFA 5 4		UnVar4)
(00001FFC 13 6 0		nil->JMP 00002005)
(00001FFF 5 4		UnVar4)
(00002001 79		1+)
(00002002 15 2 0		JMP 00002007)
(00002005 50 0		0)
(00002007 8 4		UnVar4)
(00002009 5 0		UnVar0)
(0000200B 5 1		UnVar1)
(0000200D 1		nil)
(0000200E 5 2		UnVar2)
(00002010 81 4 120 2 1 0		TBuf.scan-chars-forward)
(00002016 14 8 0		T->JMP 00002021)
(00002019 5 0		UnVar0)
(0000201B 81 1 209 2 1 0		TBuf.length)
(00002021 8 3		UnVar3)
(00002023 5 0		UnVar0)
(00002025 5 4		UnVar4)
(00002027 5 3		UnVar3)
(00002029 5 4		UnVar4)
(0000202B 71		-)
(0000202C 81 3 103 2 1 0		TBuf.delete)
(00002032 22		ret)
;;;def !newline-and-indent 8243
(00002033 20 3 1 2 0)
(00002038 100 2		UNVar2)
(0000203A 5 0		UnVar0)
(0000203C 81 1 135 3 1 0		TWinp)
(00002042 13 3 0		nil->JMP 00002048)
(00002045 15 5 0		JMP 0000204D)
(00002048 3 205 2		*active-mdiwindow*)
(0000204B 8 0		UnVar0)
(0000204D 5 0		UnVar0)
(0000204F 1		nil)
(00002050 1		nil)
(00002051 81 3 208 2 1 0		TWin.cpos<-)
(00002057 10)
(00002058 5 0		UnVar0)
(0000205A 9 102 2		" \t")
(0000205D 1		nil)
(0000205E 5 1		UnVar1)
(00002060 81 4 117 2 1 0		TBuf.scan-chars-backward)
(00002066 8 1		UnVar1)
(00002068 5 1		UnVar1)
(0000206A 13 6 0		nil->JMP 00002073)
(0000206D 5 1		UnVar1)
(0000206F 79		1+)
(00002070 15 2 0		JMP 00002075)
(00002073 50 0		0)
(00002075 8 1		UnVar1)
(00002077 5 0		UnVar0)
(00002079 5 1		UnVar1)
(0000207B 81 2 101 2 1 0		TBuf.editablep)
(00002081 13 153 0		nil->JMP 0000211D)
(00002084 5 0		UnVar0)
(00002086 9 102 2		" \t")
(00002089 5 1		UnVar1)
(0000208B 95 3 226 31 0 0		kill-chars)
(00002091 10)
(00002092 5 0		UnVar0)
(00002094 5 1		UnVar1)
(00002096 81 2 100 2 1 0		TBuf.BOL-pos-p)
(0000209C 13 12 0		nil->JMP 000020AB)
(0000209F 5 0		UnVar0)
(000020A1 5 1		UnVar1)
(000020A3 81 2 126 2 1 0		TBuf.prev-pos)
(000020A9 8 1		UnVar1)
(000020AB 15 12 0		JMP 000020BA)
(000020AE 5 0		UnVar0)
(000020B0 5 1		UnVar1)
(000020B2 81 2 126 2 1 0		TBuf.prev-pos)
(000020B8 8 1		UnVar1)
(000020BA 5 0		UnVar0)
(000020BC 5 1		UnVar1)
(000020BE 81 2 99 2 1 0		TBuf.BOL-pos)
(000020C4 11)
(000020C5 8 1		UnVar1)
(000020C7 50 0		0)
(000020C9 75		>)
(000020CA 61 10 0		nil->JMP 000020D7)
(000020CD 5 0		UnVar0)
(000020CF 5 1		UnVar1)
(000020D1 81 2 98 2 1 0		TBuf.EOL-pos-p)
(000020D7 60 212 255		T->JMP 000020AE)
(000020DA 5 0		UnVar0)
(000020DC 9 102 2		" \t")
(000020DF 1		nil)
(000020E0 5 1		UnVar1)
(000020E2 81 4 120 2 1 0		TBuf.scan-chars-forward)
(000020E8 14 8 0		T->JMP 000020F3)
(000020EB 5 0		UnVar0)
(000020ED 81 1 209 2 1 0		TBuf.length)
(000020F3 8 2		UnVar2)
(000020F5 5 0		UnVar0)
(000020F7 1		nil)
(000020F8 9 97 2		"\r\n")
(000020FB 5 0		UnVar0)
(000020FD 5 1		UnVar1)
(000020FF 5 2		UnVar2)
(00002101 81 3 96 2 1 0		TBuf.subseq)
(00002107 81 2 75 3 1 0		concat)
(0000210D 81 3 80 3 1 0		TBuf.insert)
(00002113 10)
(00002114 5 0		UnVar0)
(00002116 81 1 95 2 1 0		TWin.set-view)
(0000211C 22		ret)
(0000211D 81 0 206 2 1 0		message-beep)
(00002123 22		ret)
;;;def !drop-files 8484
(00002124 20 4 1 1 0)
(00002129 100 1		UNVar1)
(0000212B 3 205 2		*active-mdiwindow*)
(0000212E 14 3 0		T->JMP 00002134)
(00002131 3 92 3		*console*)
(00002134 8 1		UnVar1)
(00002136 5 0		UnVar0)
(00002138 37 4		stringp)
(0000213A 13 7 0		nil->JMP 00002144)
(0000213D 5 0		UnVar0)
(0000213F 57 1 0		list)
(00002142 8 0		UnVar0)
(00002144 5 0		UnVar0)
(00002146 8 2		UnVar2)
(00002148 100 3		UNVar3)
(0000214A 15 59 0		JMP 00002188)
(0000214D 5 2		UnVar2)
(0000214F 40		car)
(00002150 8 3		UnVar3)
(00002152 5 2		UnVar2)
(00002154 41		cdr)
(00002155 8 2		UnVar2)
(00002157 5 3		UnVar3)
(00002159 37 4		stringp)
(0000215B 13 42 0		nil->JMP 00002188)
(0000215E 5 3		UnVar3)
(00002160 81 1 100 3 1 0		file-readable-p)
(00002166 13 28 0		nil->JMP 00002185)
(00002169 5 3		UnVar3)
(0000216B 81 1 94 2 1 0		file-directory-p)
(00002171 13 3 0		nil->JMP 00002177)
(00002174 15 11 0		JMP 00002182)
(00002177 5 3		UnVar3)
(00002179 5 1		UnVar1)
(0000217B 95 2 126 24 0 0		open-fresh-editor)
(00002181 10)
(00002182 15 0 0		JMP 00002185)
(00002185 15 0 0		JMP 00002188)
(00002188 5 2		UnVar2)
(0000218A 60 192 255		T->JMP 0000214D)
(0000218D 1		nil)
(0000218E 22		ret)
;;;def _fine-stringp 8591
(0000218F 20 1 1 1 0)
(00002194 5 0		UnVar0)
(00002196 37 4		stringp)
(00002198 63		nil->ret)
(00002199 5 0		UnVar0)
(0000219B 81 1 93 2 1 0		string-length)
(000021A1 50 0		0)
(000021A3 75		>)
(000021A4 22		ret)
;;;def nil 8613
(000021A5 20 2 2 2 0)
(000021AA 5 0		UnVar0)
(000021AC 95 1 143 33 0 0		_fine-stringp)
(000021B2 9 92 2		"bad string to search:")
(000021B5 5 0		UnVar0)
(000021B7 53 3 17 3 1 32		assert)
(000021BD 10)
(000021BE 5 1		UnVar1)
(000021C0 81 1 135 3 1 0		TWinp)
(000021C6 14 8 0		T->JMP 000021D1)
(000021C9 5 1		UnVar1)
(000021CB 81 1 91 2 1 0		TBufp)
(000021D1 9 90 2		"bad text window for search:")
(000021D4 5 1		UnVar1)
(000021D6 47 3 17 3 32 32		assert)
;;;def editor-selection-match-p 8668
(000021DC 20 5 2 3 0)
(000021E1 100 3		UNVar3)
(000021E3 5 0		UnVar0)
(000021E5 5 1		UnVar1)
(000021E7 95 2 165 33 0 0		func 000021A5)
(000021ED 10)
(000021EE 5 2		UnVar2)
(000021F0 13 3 0		nil->JMP 000021F6)
(000021F3 15 10 0		JMP 00002200)
(000021F6 5 1		UnVar1)
(000021F8 53 1 217 2 1 32		selection)
(000021FE 8 2		UnVar2)
(00002200 5 1		UnVar1)
(00002202 5 2		UnVar2)
(00002204 40		car)
(00002205 5 2		UnVar2)
(00002207 41		cdr)
(00002208 81 3 96 2 1 0		TBuf.subseq)
(0000220E 11)
(0000220F 8 3		UnVar3)
(00002211 63		nil->ret)
(00002212 3 89 2		*editor-match-case*)
(00002215 13 13 0		nil->JMP 00002225)
(00002218 5 3		UnVar3)
(0000221A 5 0		UnVar0)
(0000221C 81 2 39 3 1 0		string=)
(00002222 15 10 0		JMP 0000222F)
(00002225 5 3		UnVar3)
(00002227 5 0		UnVar0)
(00002229 81 2 88 2 1 0		string-equal)
(0000222F 63		nil->ret)
(00002230 3 87 2		*editor-match-whole-word*)
(00002233 13 57 0		nil->JMP 0000226F)
(00002236 5 1		UnVar1)
(00002238 5 2		UnVar2)
(0000223A 40		car)
(0000223B 53 2 109 2 1 32		word-at-pos)
(00002241 8 4		UnVar4)
(00002243 5 2		UnVar2)
(00002245 40		car)
(00002246 5 2		UnVar2)
(00002248 41		cdr)
(00002249 81 2 136 2 1 0		MIN)
(0000224F 5 4		UnVar4)
(00002251 40		car)
(00002252 81 2 86 2 1 0		=)
(00002258 63		nil->ret)
(00002259 5 2		UnVar2)
(0000225B 40		car)
(0000225C 5 2		UnVar2)
(0000225E 41		cdr)
(0000225F 81 2 134 2 1 0		MAX)
(00002265 5 4		UnVar4)
(00002267 41		cdr)
(00002268 81 2 86 2 1 0		=)
(0000226E 22		ret)
(0000226F 2		T)
(00002270 22		ret)
;;;def nil 8817
(00002271 20 6 4 4 0)
(00002276 100 4		UNVar4)
(00002278 100 5		UNVar5)
(0000227A 3 85 2		*editor-forward-search*)
(0000227D 13 21 0		nil->JMP 00002295)
(00002280 5 1		UnVar1)
(00002282 5 0		UnVar0)
(00002284 3 89 2		*editor-match-case*)
(00002287 35		not)
(00002288 5 2		UnVar2)
(0000228A 5 3		UnVar3)
(0000228C 81 5 84 2 1 0		TBuf.search-forward)
(00002292 15 18 0		JMP 000022A7)
(00002295 5 1		UnVar1)
(00002297 5 0		UnVar0)
(00002299 3 89 2		*editor-match-case*)
(0000229C 35		not)
(0000229D 5 2		UnVar2)
(0000229F 5 3		UnVar3)
(000022A1 81 5 83 2 1 0		TBuf.search-backward)
(000022A7 8 2		UnVar2)
(000022A9 5 2		UnVar2)
(000022AB 63		nil->ret)
(000022AC 3 85 2		*editor-forward-search*)
(000022AF 13 15 0		nil->JMP 000022C1)
(000022B2 5 2		UnVar2)
(000022B4 5 2		UnVar2)
(000022B6 5 0		UnVar0)
(000022B8 81 1 82 2 1 0		strlen)
(000022BE 70		+)
(000022BF 42		cons)
(000022C0 22		ret)
(000022C1 5 2		UnVar2)
(000022C3 5 0		UnVar0)
(000022C5 81 1 82 2 1 0		strlen)
(000022CB 70		+)
(000022CC 5 2		UnVar2)
(000022CE 42		cons)
(000022CF 22		ret)
;;;def editor-search 8912
(000022D0 20 6 3 4 0)
(000022D5 100 4		UNVar4)
(000022D7 100 5		UNVar5)
(000022D9 5 0		UnVar0)
(000022DB 5 1		UnVar1)
(000022DD 95 2 165 33 0 0		func 000021A5)
(000022E3 10)
(000022E4 15 5 0		JMP 000022EC)
(000022E7 5 4		UnVar4)
(000022E9 41		cdr)
(000022EA 8 2		UnVar2)
(000022EC 5 0		UnVar0)
(000022EE 5 1		UnVar1)
(000022F0 5 2		UnVar2)
(000022F2 5 3		UnVar3)
(000022F4 95 4 113 34 0 0		func 00002271)
(000022FA 11)
(000022FB 8 4		UnVar4)
(000022FD 61 16 0		nil->JMP 00002310)
(00002300 5 0		UnVar0)
(00002302 5 1		UnVar1)
(00002304 5 4		UnVar4)
(00002306 95 3 220 33 0 0		editor-selection-match-p)
(0000230C 11)
(0000230D 8 5		UnVar5)
(0000230F 35		not)
(00002310 60 212 255		T->JMP 000022E7)
(00002313 5 4		UnVar4)
(00002315 61 2 0		nil->JMP 0000231A)
(00002318 5 5		UnVar5)
(0000231A 63		nil->ret)
(0000231B 5 4		UnVar4)
(0000231D 22		ret)
;;;def !editor-find-command 8990
(0000231E 20 2 1 1 0)
(00002323 100 1		UNVar1)
(00002325 2		T)
(00002326 6 81 2		*next-is-find*)
(00002329 5 0		UnVar0)
(0000232B 53 1 80 2 1 32		verified-sync-down)
(00002331 10)
(00002332 95 0 68 41 0 0		update-find-hist)
(00002338 10)
(00002339 1		nil)
(0000233A 2		T)
(0000233B 1		nil)
(0000233C 1		nil)
(0000233D 2		T)
(0000233E 95 5 62 36 0 0		next-find/replace!)
(00002344 63		nil->ret)
(00002345 5 0		UnVar0)
(00002347 47 1 94 3 32 32		destroy-host-spouse)
;;;def _editor-find2-command 9037
(0000234D 20 2 1 1 0)
(00002352 100 1		UNVar1)
(00002354 2		T)
(00002355 6 81 2		*next-is-find*)
(00002358 5 0		UnVar0)
(0000235A 53 1 80 2 1 32		verified-sync-down)
(00002360 10)
(00002361 95 0 68 41 0 0		update-find-hist)
(00002367 10)
(00002368 1		nil)
(00002369 2		T)
(0000236A 1		nil)
(0000236B 1		nil)
(0000236C 2		T)
(0000236D 96 5 62 36 0 0		next-find/replace!)
;;;def _editor-replace-command 9075
(00002373 20 1 1 1 0)
(00002378 1		nil)
(00002379 6 81 2		*next-is-find*)
(0000237C 5 0		UnVar0)
(0000237E 53 1 80 2 1 32		verified-sync-down)
(00002384 10)
(00002385 95 0 68 41 0 0		update-find-hist)
(0000238B 10)
(0000238C 1		nil)
(0000238D 1		nil)
(0000238E 1		nil)
(0000238F 1		nil)
(00002390 2		T)
(00002391 96 5 62 36 0 0		next-find/replace!)
;;;def _editor-replace-all-command 9111
(00002397 20 2 1 1 0)
(0000239C 100 1		UNVar1)
(0000239E 1		nil)
(0000239F 6 81 2		*next-is-find*)
(000023A2 5 0		UnVar0)
(000023A4 53 1 80 2 1 32		verified-sync-down)
(000023AA 10)
(000023AB 95 0 68 41 0 0		update-find-hist)
(000023B1 10)
(000023B2 95 0 46 46 0 0		replace-all!)
(000023B8 63		nil->ret)
(000023B9 5 0		UnVar0)
(000023BB 47 1 94 3 32 32		destroy-host-spouse)
;;;def nil 9153
(000023C1 20 1 1 1 0)
(000023C6 3 156 2		*info-alert*)
(000023C9 9 107 3		"VLMSG.DLL")
(000023CC 51 198 92 0 0		23750)
(000023D1 81 2 106 3 1 0		string-resource)
(000023D7 47 2 85 3 32 32		alert)
;;;def nil 9181
(000023DD 20 1 1 1 0)
(000023E2 5 0		UnVar0)
(000023E4 53 1 94 3 1 32		destroy-host-spouse)
(000023EA 10)
(000023EB 2		T)
(000023EC 22		ret)
;;;def swap-selection 9197
(000023ED 20 2 1 1 0)
(000023F2 5 0		UnVar0)
(000023F4 81 1 218 2 1 0		TWin.has-selection-p)
(000023FA 63		nil->ret)
(000023FB 5 0		UnVar0)
(000023FD 53 1 217 2 1 32		selection)
(00002403 8 1		UnVar1)
(00002405 5 1		UnVar1)
(00002407 40		car)
(00002408 5 1		UnVar1)
(0000240A 41		cdr)
(0000240B 81 2 79 2 1 0		<)
(00002411 13 23 0		nil->JMP 0000242B)
(00002414 3 85 2		*editor-forward-search*)
(00002417 13 2 0		nil->JMP 0000241C)
(0000241A 1		nil)
(0000241B 22		ret)
(0000241C 5 0		UnVar0)
(0000241E 5 1		UnVar1)
(00002420 41		cdr)
(00002421 5 1		UnVar1)
(00002423 40		car)
(00002424 42		cons)
(00002425 47 2 133 2 32 32		selection<-)
(0000242B 3 85 2		*editor-forward-search*)
(0000242E 63		nil->ret)
(0000242F 5 0		UnVar0)
(00002431 5 1		UnVar1)
(00002433 41		cdr)
(00002434 5 1		UnVar1)
(00002436 40		car)
(00002437 42		cons)
(00002438 47 2 133 2 32 32		selection<-)
;;;def next-find/replace! 9278
(0000243E 20 7 0 5 0)
(00002443 100 5		UNVar5)
(00002445 100 6		UNVar6)
(00002447 5 0		UnVar0)
(00002449 81 1 135 3 1 0		TWinp)
(0000244F 13 3 0		nil->JMP 00002455)
(00002452 15 5 0		JMP 0000245A)
(00002455 3 205 2		*active-mdiwindow*)
(00002458 8 0		UnVar0)
(0000245A 5 2		UnVar2)
(0000245C 13 3 0		nil->JMP 00002462)
(0000245F 15 5 0		JMP 00002467)
(00002462 3 78 2		*editor-find-what*)
(00002465 8 2		UnVar2)
(00002467 5 3		UnVar3)
(00002469 13 3 0		nil->JMP 0000246F)
(0000246C 15 5 0		JMP 00002474)
(0000246F 3 77 2		*editor-replace-with*)
(00002472 8 3		UnVar3)
(00002474 3 76 2		*editor-search-margins*)
(00002477 13 62 0		nil->JMP 000024B8)
(0000247A 3 85 2		*editor-forward-search*)
(0000247D 61 14 0		nil->JMP 0000248E)
(00002480 3 76 2		*editor-search-margins*)
(00002483 40		car)
(00002484 3 76 2		*editor-search-margins*)
(00002487 41		cdr)
(00002488 81 2 75 2 1 0		>)
(0000248E 14 24 0		T->JMP 000024A9)
(00002491 3 85 2		*editor-forward-search*)
(00002494 13 4 0		nil->JMP 0000249B)
(00002497 1		nil)
(00002498 15 14 0		JMP 000024A9)
(0000249B 3 76 2		*editor-search-margins*)
(0000249E 40		car)
(0000249F 3 76 2		*editor-search-margins*)
(000024A2 41		cdr)
(000024A3 81 2 79 2 1 0		<)
(000024A9 13 12 0		nil->JMP 000024B8)
(000024AC 3 76 2		*editor-search-margins*)
(000024AF 41		cdr)
(000024B0 3 76 2		*editor-search-margins*)
(000024B3 40		car)
(000024B4 42		cons)
(000024B5 6 76 2		*editor-search-margins*)
(000024B8 5 1		UnVar1)
(000024BA 14 3 0		T->JMP 000024C0)
(000024BD 3 81 2		*next-is-find*)
(000024C0 8 1		UnVar1)
(000024C2 3 76 2		*editor-search-margins*)
(000024C5 13 7 0		nil->JMP 000024CF)
(000024C8 3 76 2		*editor-search-margins*)
(000024CB 40		car)
(000024CC 15 8 0		JMP 000024D7)
(000024CF 5 0		UnVar0)
(000024D1 81 1 167 2 1 0		TWin.cpos)
(000024D7 8 6		UnVar6)
(000024D9 5 1		UnVar1)
(000024DB 13 11 0		nil->JMP 000024E9)
(000024DE 5 0		UnVar0)
(000024E0 95 1 143 41 0 0		!?find)
(000024E6 15 8 0		JMP 000024F1)
(000024E9 5 0		UnVar0)
(000024EB 95 1 180 41 0 0		!?replace)
(000024F1 13 22 0		nil->JMP 0000250A)
(000024F4 5 2		UnVar2)
(000024F6 5 0		UnVar0)
(000024F8 5 6		UnVar6)
(000024FA 5 1		UnVar1)
(000024FC 5 3		UnVar3)
(000024FE 5 4		UnVar4)
(00002500 95 6 154 43 0 0		func 00002B9A)
(00002506 10)
(00002507 15 7 0		JMP 00002511)
(0000250A 81 0 206 2 1 0		message-beep)
(00002510 10)
(00002511 3 74 2		*editor-find-dialog*)
(00002514 53 1 103 3 1 32		host-spouse-exists-p)
(0000251A 13 5 0		nil->JMP 00002522)
(0000251D 3 74 2		*editor-find-dialog*)
(00002520 8 5		UnVar5)
(00002522 3 73 2		*editor-replace-dialog*)
(00002525 53 1 103 3 1 32		host-spouse-exists-p)
(0000252B 13 5 0		nil->JMP 00002533)
(0000252E 3 73 2		*editor-replace-dialog*)
(00002531 8 5		UnVar5)
(00002533 5 5		UnVar5)
(00002535 63		nil->ret)
(00002536 3 72 2		*editor-find-modes*)
(00002539 41		cdr)
(0000253A 40		car)
(0000253B 6 71 2		*editor-find-mode*)
(0000253E 5 5		UnVar5)
(00002540 53 1 70 2 1 32		sync-up)
(00002546 10)
(00002547 5 5		UnVar5)
(00002549 53 1 102 3 1 32		update-host-spouse)
(0000254F 10)
(00002550 2		T)
(00002551 22		ret)
;;;def find! 9554
(00002552 20 9 0 1 0)
(00002557 100 1		UNVar1)
(00002559 5 0		UnVar0)
(0000255B 81 1 135 3 1 0		TWinp)
(00002561 13 3 0		nil->JMP 00002567)
(00002564 15 5 0		JMP 0000256C)
(00002567 3 205 2		*active-mdiwindow*)
(0000256A 8 0		UnVar0)
(0000256C 3 74 2		*editor-find-dialog*)
(0000256F 9 107 3		"VLMSG.DLL")
(00002572 51 92 88 0 0		22620)
(00002577 81 2 106 3 1 0		string-resource)
(0000257D 9 87 3		'caption)
(00002580 81 3 78 3 1 0		slot-value<-)
(00002586 10)
(00002587 3 74 2		*editor-find-dialog*)
(0000258A 3 69 2		*editor-find-dialog-items*)
(0000258D 9 68 2		'items)
(00002590 81 3 78 3 1 0		slot-value<-)
(00002596 10)
(00002597 3 74 2		*editor-find-dialog*)
(0000259A 3 67 2		*ed-find-size*)
(0000259D 40		car)
(0000259E 3 67 2		*ed-find-size*)
(000025A1 41		cdr)
(000025A2 81 2 249 2 1 0		make-ipoint)
(000025A8 9 254 2		'size)
(000025AB 81 3 78 3 1 0		slot-value<-)
(000025B1 10)
(000025B2 100 2		UNVar2)
(000025B4 100 3		UNVar3)
(000025B6 50 255		-1)
(000025B8 51 10 4 0 0		1034)
(000025BD 51 240 3 0 0		1008)
(000025C2 51 241 3 0 0		1009)
(000025C7 51 242 3 0 0		1010)
(000025CC 51 243 3 0 0		1011)
(000025D1 51 235 3 0 0		1003)
(000025D6 51 237 3 0 0		1005)
(000025DB 51 238 3 0 0		1006)
(000025E0 51 236 3 0 0		1004)
(000025E5 51 244 3 0 0		1012)
(000025EA 51 245 3 0 0		1013)
(000025EF 51 246 3 0 0		1014)
(000025F4 51 231 3 0 0		999)
(000025F9 50 2		2)
(000025FB 57 15 0		list)
(000025FE 8 2		UnVar2)
(00002600 3 74 2		*editor-find-dialog*)
(00002603 9 68 2		'items)
(00002606 81 2 86 3 1 0		slot-value)
(0000260C 8 4		UnVar4)
(0000260E 5 2		UnVar2)
(00002610 8 5		UnVar5)
(00002612 100 6		UNVar6)
(00002614 15 31 0		JMP 00002636)
(00002617 5 4		UnVar4)
(00002619 40		car)
(0000261A 8 7		UnVar7)
(0000261C 5 5		UnVar5)
(0000261E 40		car)
(0000261F 8 8		UnVar8)
(00002621 5 7		UnVar7)
(00002623 40		car)
(00002624 5 8		UnVar8)
(00002626 42		cons)
(00002627 5 6		UnVar6)
(00002629 42		cons)
(0000262A 8 6		UnVar6)
(0000262C 5 4		UnVar4)
(0000262E 41		cdr)
(0000262F 8 4		UnVar4)
(00002631 5 5		UnVar5)
(00002633 41		cdr)
(00002634 8 5		UnVar5)
(00002636 5 4		UnVar4)
(00002638 61 2 0		nil->JMP 0000263D)
(0000263B 5 5		UnVar5)
(0000263D 60 215 255		T->JMP 00002617)
(00002640 5 6		UnVar6)
(00002642 81 1 12 3 1 0		nreverse)
(00002648 8 3		UnVar3)
(0000264A 3 74 2		*editor-find-dialog*)
(0000264D 9 66 2		"vldlg.dll")
(00002650 50 107		107)
(00002652 5 3		UnVar3)
(00002654 53 4 65 2 1 32		dialog-update-from-res)
(0000265A 10)
(0000265B 3 74 2		*editor-find-dialog*)
(0000265E 9 254 2		'size)
(00002661 81 2 86 3 1 0		slot-value)
(00002667 81 1 253 2 1 0		ipoint-h)
(0000266D 3 74 2		*editor-find-dialog*)
(00002670 9 254 2		'size)
(00002673 81 2 86 3 1 0		slot-value)
(00002679 81 1 251 2 1 0		ipoint-v)
(0000267F 42		cons)
(00002680 6 67 2		*ed-find-size*)
(00002683 5 0		UnVar0)
(00002685 95 1 143 41 0 0		!?find)
(0000268B 13 75 0		nil->JMP 000026D9)
(0000268E 9 76 2		'*editor-search-margins*)
(00002691 1		nil)
(00002692 24 2 0)
(00002695 5 0		UnVar0)
(00002697 15 47 0		JMP 000026C9)
(0000269A 20 3 2 3 0)
(0000269F 5 0		UnVar0)
(000026A1 13 5 0		nil->JMP 000026A9)
(000026A4 5 0		UnVar0)
(000026A6 6 78 2		*editor-find-what*)
(000026A9 3 74 2		*editor-find-dialog*)
(000026AC 95 1 224 38 0 0		!editor-selection-p)
(000026B2 10)
(000026B3 3 74 2		*editor-find-dialog*)
(000026B6 3 71 2		*editor-find-mode*)
(000026B9 95 2 234 39 0 0		_set-find-mode)
(000026BF 10)
(000026C0 3 74 2		*editor-find-dialog*)
(000026C3 47 1 64 2 32 32		modal-dialog!!)
(000026C9 9 187 3		'(9882 nil))
(000026CC 50 64		64)
(000026CE 2		T)
(000026CF 53 4 63 2 1 32		execute-in-mdiwindow-context)
(000026D5 25 1 0)
(000026D8 22		ret)
(000026D9 81 0 206 2 1 0		message-beep)
(000026DF 22		ret)
;;;def !editor-selection-p 9952
(000026E0 20 9 1 2 0)
(000026E5 100 2		UNVar2)
(000026E7 100 3		UNVar3)
(000026E9 100 4		UNVar4)
(000026EB 5 0		UnVar0)
(000026ED 8 5		UnVar5)
(000026EF 5 5		UnVar5)
(000026F1 44 11		IDFun11)
(000026F3 8 6		UnVar6)
(000026F5 5 5		UnVar5)
(000026F7 5 6		UnVar6)
(000026F9 9 62 2		':sel-box)
(000026FC 53 3 61 2 1 32		_label-getf)
(00002702 8 7		UnVar7)
(00002704 5 5		UnVar5)
(00002706 5 6		UnVar6)
(00002708 9 60 2		':sel-box-replace)
(0000270B 53 3 61 2 1 32		_label-getf)
(00002711 8 8		UnVar8)
(00002713 5 1		UnVar1)
(00002715 13 5 0		nil->JMP 0000271D)
(00002718 5 8		UnVar8)
(0000271A 15 2 0		JMP 0000271F)
(0000271D 5 7		UnVar7)
(0000271F 8 2		UnVar2)
(00002721 3 205 2		*active-mdiwindow*)
(00002724 53 1 217 2 1 32		selection)
(0000272A 8 3		UnVar3)
(0000272C 5 3		UnVar3)
(0000272E 40		car)
(0000272F 5 3		UnVar3)
(00002731 41		cdr)
(00002732 81 2 59 2 1 0		-)
(00002738 81 1 58 2 1 0		ABS)
(0000273E 50 64		64)
(00002740 81 2 75 2 1 0		>)
(00002746 8 4		UnVar4)
(00002748 5 4		UnVar4)
(0000274A 13 7 0		nil->JMP 00002754)
(0000274D 3 72 2		*editor-find-modes*)
(00002750 40		car)
(00002751 15 5 0		JMP 00002759)
(00002754 3 72 2		*editor-find-modes*)
(00002757 41		cdr)
(00002758 40		car)
(00002759 6 71 2		*editor-find-mode*)
(0000275C 5 2		UnVar2)
(0000275E 40		car)
(0000275F 5 3		UnVar3)
(00002761 40		car)
(00002762 5 3		UnVar3)
(00002764 41		cdr)
(00002765 81 2 86 2 1 0		=)
(0000276B 47 2 57 2 32 32		lazy-disable)
;;;def !editor-use-selection 10097
(00002771 20 3 1 1 0)
(00002776 100 1		UNVar1)
(00002778 100 2		UNVar2)
(0000277A 3 205 2		*active-mdiwindow*)
(0000277D 81 1 218 2 1 0		TWin.has-selection-p)
(00002783 63		nil->ret)
(00002784 3 205 2		*active-mdiwindow*)
(00002787 53 1 217 2 1 32		selection)
(0000278D 11)
(0000278E 6 76 2		*editor-search-margins*)
(00002791 22		ret)
;;;def !editor-drop-selection 10130
(00002792 20 1 1 1 0)
(00002797 1		nil)
(00002798 11)
(00002799 6 76 2		*editor-search-margins*)
(0000279C 22		ret)
;;;def _tune-find-command 10141
(0000279D 20 5 1 1 0)
(000027A2 5 0		UnVar0)
(000027A4 8 1		UnVar1)
(000027A6 5 1		UnVar1)
(000027A8 44 11		IDFun11)
(000027AA 8 2		UnVar2)
(000027AC 5 1		UnVar1)
(000027AE 5 2		UnVar2)
(000027B0 9 62 2		':sel-box)
(000027B3 53 3 61 2 1 32		_label-getf)
(000027B9 8 3		UnVar3)
(000027BB 5 3		UnVar3)
(000027BD 8 4		UnVar4)
(000027BF 15 15 0		JMP 000027D1)
(000027C2 5 4		UnVar4)
(000027C4 40		car)
(000027C5 53 1 56 2 1 32		sync-down)
(000027CB 10)
(000027CC 5 4		UnVar4)
(000027CE 41		cdr)
(000027CF 8 4		UnVar4)
(000027D1 5 4		UnVar4)
(000027D3 60 236 255		T->JMP 000027C2)
(000027D6 5 0		UnVar0)
(000027D8 3 71 2		*editor-find-mode*)
(000027DB 95 2 234 39 0 0		_set-find-mode)
(000027E1 10)
(000027E2 5 0		UnVar0)
(000027E4 47 1 102 3 32 32		update-host-spouse)
;;;def _set-find-mode 10218
(000027EA 20 6 2 2 0)
(000027EF 100 2		UNVar2)
(000027F1 5 0		UnVar0)
(000027F3 8 3		UnVar3)
(000027F5 5 3		UnVar3)
(000027F7 44 11		IDFun11)
(000027F9 8 4		UnVar4)
(000027FB 5 3		UnVar3)
(000027FD 5 4		UnVar4)
(000027FF 9 55 2		':EDITOR-FIND-PUSH-BUTTON)
(00002802 53 3 61 2 1 32		_label-getf)
(00002808 8 5		UnVar5)
(0000280A 3 74 2		*editor-find-dialog*)
(0000280D 9 68 2		'items)
(00002810 81 2 86 3 1 0		slot-value)
(00002816 5 1		UnVar1)
(00002818 40		car)
(00002819 81 1 226 2 1 0		symbol-value)
(0000281F 38		=)
(00002820 13 3 0		nil->JMP 00002826)
(00002823 15 22 0		JMP 0000283C)
(00002826 3 74 2		*editor-find-dialog*)
(00002829 5 1		UnVar1)
(0000282B 40		car)
(0000282C 81 1 226 2 1 0		symbol-value)
(00002832 9 68 2		'items)
(00002835 81 3 78 3 1 0		slot-value<-)
(0000283B 10)
(0000283C 5 5		UnVar5)
(0000283E 5 1		UnVar1)
(00002840 41		cdr)
(00002841 40		car)
(00002842 81 1 226 2 1 0		symbol-value)
(00002848 9 54 2		'command)
(0000284B 81 3 78 3 1 0		slot-value<-)
(00002851 10)
(00002852 5 1		UnVar1)
(00002854 41		cdr)
(00002855 41		cdr)
(00002856 40		car)
(00002857 81 1 226 2 1 0		symbol-value)
(0000285D 8 2		UnVar2)
(0000285F 3 74 2		*editor-find-dialog*)
(00002862 5 2		UnVar2)
(00002864 40		car)
(00002865 5 2		UnVar2)
(00002867 41		cdr)
(00002868 81 2 249 2 1 0		make-ipoint)
(0000286E 9 254 2		'size)
(00002871 81 3 78 3 1 0		slot-value<-)
(00002877 10)
(00002878 5 1		UnVar1)
(0000287A 41		cdr)
(0000287B 41		cdr)
(0000287C 41		cdr)
(0000287D 63		nil->ret)
(0000287E 5 0		UnVar0)
(00002880 5 1		UnVar1)
(00002882 41		cdr)
(00002883 41		cdr)
(00002884 41		cdr)
(00002885 40		car)
(00002886 46 1		invoke+ret)
;;;def _switch-to-replace 10376
(00002888 20 1 1 1 0)
(0000288D 5 0		UnVar0)
(0000288F 9 107 3		"VLMSG.DLL")
(00002892 51 102 88 0 0		22630)
(00002897 81 2 106 3 1 0		string-resource)
(0000289D 9 87 3		'caption)
(000028A0 81 3 78 3 1 0		slot-value<-)
(000028A6 10)
(000028A7 5 0		UnVar0)
(000028A9 3 53 2		*editor-replace-dialog-items*)
(000028AC 9 68 2		'items)
(000028AF 81 3 78 3 1 0		slot-value<-)
(000028B5 10)
(000028B6 5 0		UnVar0)
(000028B8 3 52 2		*ed-replace-size*)
(000028BB 40		car)
(000028BC 3 52 2		*ed-replace-size*)
(000028BF 41		cdr)
(000028C0 81 2 249 2 1 0		make-ipoint)
(000028C6 9 254 2		'size)
(000028C9 81 3 78 3 1 0		slot-value<-)
(000028CF 10)
(000028D0 5 0		UnVar0)
(000028D2 2		T)
(000028D3 95 2 224 38 0 0		!editor-selection-p)
(000028D9 10)
(000028DA 5 0		UnVar0)
(000028DC 47 1 102 3 32 32		update-host-spouse)
;;;def _tune-replace-command 10466
(000028E2 20 5 1 1 0)
(000028E7 5 0		UnVar0)
(000028E9 8 1		UnVar1)
(000028EB 5 1		UnVar1)
(000028ED 44 11		IDFun11)
(000028EF 8 2		UnVar2)
(000028F1 5 1		UnVar1)
(000028F3 5 2		UnVar2)
(000028F5 9 60 2		':sel-box-replace)
(000028F8 53 3 61 2 1 32		_label-getf)
(000028FE 8 3		UnVar3)
(00002900 5 3		UnVar3)
(00002902 8 4		UnVar4)
(00002904 15 15 0		JMP 00002916)
(00002907 5 4		UnVar4)
(00002909 40		car)
(0000290A 53 1 56 2 1 32		sync-down)
(00002910 10)
(00002911 5 4		UnVar4)
(00002913 41		cdr)
(00002914 8 4		UnVar4)
(00002916 5 4		UnVar4)
(00002918 60 236 255		T->JMP 00002907)
(0000291B 5 0		UnVar0)
(0000291D 3 71 2		*editor-find-mode*)
(00002920 95 2 47 41 0 0		_set-replace-mode)
(00002926 10)
(00002927 5 0		UnVar0)
(00002929 47 1 102 3 32 32		update-host-spouse)
;;;def _set-replace-mode 10543
(0000292F 20 2 2 2 0)
(00002934 5 1		UnVar1)
(00002936 41		cdr)
(00002937 41		cdr)
(00002938 41		cdr)
(00002939 63		nil->ret)
(0000293A 5 0		UnVar0)
(0000293C 5 1		UnVar1)
(0000293E 41		cdr)
(0000293F 41		cdr)
(00002940 41		cdr)
(00002941 40		car)
(00002942 46 1		invoke+ret)
;;;def update-find-hist 10564
(00002944 20 0 0 0 0)
(00002949 3 78 2		*editor-find-what*)
(0000294C 95 1 143 33 0 0		_fine-stringp)
(00002952 63		nil->ret)
(00002953 3 51 2		*lb-find-next*)
(00002956 53 1 70 2 1 32		sync-up)
(0000295C 10)
(0000295D 3 51 2		*lb-find-next*)
(00002960 51 150 0 0 0		150)
(00002965 53 1 246 2 1 32		auto-scale-x)
(0000296B 51 200 0 0 0		200)
(00002970 53 1 245 2 1 32		auto-scale-y)
(00002976 81 2 249 2 1 0		make-ipoint)
(0000297C 9 254 2		'size)
(0000297F 81 3 78 3 1 0		slot-value<-)
(00002985 10)
(00002986 3 51 2		*lb-find-next*)
(00002989 47 1 102 3 32 32		update-host-spouse)
;;;def !?find 10639
(0000298F 20 1 1 1 0)
(00002994 5 0		UnVar0)
(00002996 81 1 209 2 1 0		TBuf.length)
(0000299C 50 0		0)
(0000299E 75		>)
(0000299F 22		ret)
;;;def >@find 10656
(000029A0 20 1 1 1 0)
(000029A5 3 205 2		*active-mdiwindow*)
(000029A8 95 1 143 41 0 0		!?find)
(000029AE 35		not)
(000029AF 5 0		UnVar0)
(000029B1 45 5		IDFun5)
(000029B3 22		ret)
;;;def !?replace 10676
(000029B4 20 1 1 1 0)
(000029B9 5 0		UnVar0)
(000029BB 53 1 50 2 1 32		tbuf.read-only)
(000029C1 13 2 0		nil->JMP 000029C6)
(000029C4 1		nil)
(000029C5 22		ret)
(000029C6 5 0		UnVar0)
(000029C8 81 1 209 2 1 0		TBuf.length)
(000029CE 50 0		0)
(000029D0 75		>)
(000029D1 22		ret)
;;;def nil 10706
(000029D2 20 4 2 2 0)
(000029D7 100 2		UNVar2)
(000029D9 100 3		UNVar3)
(000029DB 5 0		UnVar0)
(000029DD 81 1 215 2 1 0		tbuf.ro-tmark)
(000029E3 8 3		UnVar3)
(000029E5 5 3		UnVar3)
(000029E7 13 22 0		nil->JMP 00002A00)
(000029EA 5 3		UnVar3)
(000029EC 53 1 212 2 1 32		seat)
(000029F2 11)
(000029F3 8 2		UnVar2)
(000029F5 13 6 0		nil->JMP 000029FE)
(000029F8 5 2		UnVar2)
(000029FA 5 1		UnVar1)
(000029FC 76		<)
(000029FD 22		ret)
(000029FE 1		nil)
(000029FF 22		ret)
(00002A00 2		T)
(00002A01 22		ret)
;;;def >@replace 10754
(00002A02 20 1 1 1 0)
(00002A07 3 205 2		*active-mdiwindow*)
(00002A0A 95 1 180 41 0 0		!?replace)
(00002A10 35		not)
(00002A11 5 0		UnVar0)
(00002A13 45 5		IDFun5)
(00002A15 22		ret)
;;;def replace! 10774
(00002A16 20 9 0 1 0)
(00002A1B 100 1		UNVar1)
(00002A1D 5 0		UnVar0)
(00002A1F 81 1 135 3 1 0		TWinp)
(00002A25 13 3 0		nil->JMP 00002A2B)
(00002A28 15 5 0		JMP 00002A30)
(00002A2B 3 205 2		*active-mdiwindow*)
(00002A2E 8 0		UnVar0)
(00002A30 5 0		UnVar0)
(00002A32 95 1 180 41 0 0		!?replace)
(00002A38 13 41 1		nil->JMP 00002B64)
(00002A3B 9 76 2		'*editor-search-margins*)
(00002A3E 1		nil)
(00002A3F 24 2 0)
(00002A42 3 73 2		*editor-replace-dialog*)
(00002A45 8 2		UnVar2)
(00002A47 5 2		UnVar2)
(00002A49 44 11		IDFun11)
(00002A4B 8 3		UnVar3)
(00002A4D 5 2		UnVar2)
(00002A4F 5 3		UnVar3)
(00002A51 9 55 2		':EDITOR-FIND-PUSH-BUTTON)
(00002A54 53 3 61 2 1 32		_label-getf)
(00002A5A 8 4		UnVar4)
(00002A5C 5 4		UnVar4)
(00002A5E 9 186 3		'(9037 _editor-find2-command))
(00002A61 9 54 2		'command)
(00002A64 81 3 78 3 1 0		slot-value<-)
(00002A6A 10)
(00002A6B 100 2		UNVar2)
(00002A6D 100 3		UNVar3)
(00002A6F 51 242 4 0 0		1266)
(00002A74 51 244 4 0 0		1268)
(00002A79 51 243 4 0 0		1267)
(00002A7E 51 72 4 0 0		1096)
(00002A83 51 247 4 0 0		1271)
(00002A88 51 248 4 0 0		1272)
(00002A8D 51 246 4 0 0		1270)
(00002A92 51 56 4 0 0		1080)
(00002A97 51 57 4 0 0		1081)
(00002A9C 51 245 4 0 0		1269)
(00002AA1 51 249 4 0 0		1273)
(00002AA6 51 250 4 0 0		1274)
(00002AAB 51 251 4 0 0		1275)
(00002AB0 51 252 4 0 0		1276)
(00002AB5 51 253 4 0 0		1277)
(00002ABA 50 2		2)
(00002ABC 57 16 0		list)
(00002ABF 8 2		UnVar2)
(00002AC1 3 73 2		*editor-replace-dialog*)
(00002AC4 9 68 2		'items)
(00002AC7 81 2 86 3 1 0		slot-value)
(00002ACD 8 4		UnVar4)
(00002ACF 5 2		UnVar2)
(00002AD1 8 5		UnVar5)
(00002AD3 100 6		UNVar6)
(00002AD5 15 31 0		JMP 00002AF7)
(00002AD8 5 4		UnVar4)
(00002ADA 40		car)
(00002ADB 8 7		UnVar7)
(00002ADD 5 5		UnVar5)
(00002ADF 40		car)
(00002AE0 8 8		UnVar8)
(00002AE2 5 7		UnVar7)
(00002AE4 40		car)
(00002AE5 5 8		UnVar8)
(00002AE7 42		cons)
(00002AE8 5 6		UnVar6)
(00002AEA 42		cons)
(00002AEB 8 6		UnVar6)
(00002AED 5 4		UnVar4)
(00002AEF 41		cdr)
(00002AF0 8 4		UnVar4)
(00002AF2 5 5		UnVar5)
(00002AF4 41		cdr)
(00002AF5 8 5		UnVar5)
(00002AF7 5 4		UnVar4)
(00002AF9 61 2 0		nil->JMP 00002AFE)
(00002AFC 5 5		UnVar5)
(00002AFE 60 215 255		T->JMP 00002AD8)
(00002B01 5 6		UnVar6)
(00002B03 81 1 12 3 1 0		nreverse)
(00002B09 8 3		UnVar3)
(00002B0B 3 73 2		*editor-replace-dialog*)
(00002B0E 9 66 2		"vldlg.dll")
(00002B11 51 148 0 0 0		148)
(00002B16 5 3		UnVar3)
(00002B18 53 4 65 2 1 32		dialog-update-from-res)
(00002B1E 10)
(00002B1F 5 0		UnVar0)
(00002B21 15 48 0		JMP 00002B54)
(00002B24 20 3 2 3 0)
(00002B29 5 0		UnVar0)
(00002B2B 13 5 0		nil->JMP 00002B33)
(00002B2E 5 0		UnVar0)
(00002B30 6 78 2		*editor-find-what*)
(00002B33 3 74 2		*editor-find-dialog*)
(00002B36 2		T)
(00002B37 95 2 224 38 0 0		!editor-selection-p)
(00002B3D 10)
(00002B3E 3 73 2		*editor-replace-dialog*)
(00002B41 3 71 2		*editor-find-mode*)
(00002B44 95 2 47 41 0 0		_set-replace-mode)
(00002B4A 10)
(00002B4B 3 73 2		*editor-replace-dialog*)
(00002B4E 47 1 64 2 32 32		modal-dialog!!)
(00002B54 9 185 3		'(11044 nil))
(00002B57 50 64		64)
(00002B59 2		T)
(00002B5A 53 4 63 2 1 32		execute-in-mdiwindow-context)
(00002B60 25 1 0)
(00002B63 22		ret)
(00002B64 81 0 206 2 1 0		message-beep)
(00002B6A 22		ret)
;;;def !?next-find/replace 11115
(00002B6B 20 1 0 1 0)
(00002B70 3 81 2		*next-is-find*)
(00002B73 13 8 0		nil->JMP 00002B7E)
(00002B76 5 0		UnVar0)
(00002B78 97 1 148 41 0 0		offset 00002994)
(00002B7E 5 0		UnVar0)
(00002B80 97 1 185 41 0 0		offset 000029B9)
;;;def >@next-find/replace 11142
(00002B86 20 1 1 1 0)
(00002B8B 3 205 2		*active-mdiwindow*)
(00002B8E 95 1 107 43 0 0		!?next-find/replace)
(00002B94 35		not)
(00002B95 5 0		UnVar0)
(00002B97 45 5		IDFun5)
(00002B99 22		ret)
;;;def nil 11162
(00002B9A 20 9 4 6 0)
(00002B9F 100 6		UNVar6)
(00002BA1 100 7		UNVar7)
(00002BA3 100 8		UNVar8)
(00002BA5 5 0		UnVar0)
(00002BA7 95 1 143 33 0 0		_fine-stringp)
(00002BAD 13 32 1		nil->JMP 00002CD0)
(00002BB0 5 4		UnVar4)
(00002BB2 13 3 0		nil->JMP 00002BB8)
(00002BB5 15 5 0		JMP 00002BBD)
(00002BB8 9 41 3		"")
(00002BBB 8 4		UnVar4)
(00002BBD 5 0		UnVar0)
(00002BBF 5 1		UnVar1)
(00002BC1 95 2 220 33 0 0		editor-selection-match-p)
(00002BC7 13 135 0		nil->JMP 00002C51)
(00002BCA 5 1		UnVar1)
(00002BCC 95 1 237 35 0 0		swap-selection)
(00002BD2 41		cdr)
(00002BD3 14 2 0		T->JMP 00002BD8)
(00002BD6 5 2		UnVar2)
(00002BD8 8 2		UnVar2)
(00002BDA 5 3		UnVar3)
(00002BDC 60 89 0		T->JMP 00002C38)
(00002BDF 5 1		UnVar1)
(00002BE1 5 2		UnVar2)
(00002BE3 95 2 210 41 0 0		func 000029D2)
(00002BE9 13 45 0		nil->JMP 00002C19)
(00002BEC 5 5		UnVar5)
(00002BEE 13 6 0		nil->JMP 00002BF7)
(00002BF1 2		T)
(00002BF2 8 7		UnVar7)
(00002BF4 15 31 0		JMP 00002C16)
(00002BF7 3 88 3		*yes-no-cancel-alert*)
(00002BFA 9 107 3		"VLMSG.DLL")
(00002BFD 51 132 93 0 0		23940)
(00002C02 81 2 106 3 1 0		string-resource)
(00002C08 5 4		UnVar4)
(00002C0A 53 3 85 3 1 32		alert)
(00002C10 9 84 3		':YES)
(00002C13 38		=)
(00002C14 8 7		UnVar7)
(00002C16 15 31 0		JMP 00002C38)
(00002C19 81 0 206 2 1 0		message-beep)
(00002C1F 10)
(00002C20 9 107 3		"VLMSG.DLL")
(00002C23 51 122 93 0 0		23930)
(00002C28 81 2 106 3 1 0		string-resource)
(00002C2E 81 1 45 3 1 0		ales-prompt-msg)
(00002C34 10)
(00002C35 2		T)
(00002C36 8 6		UnVar6)
(00002C38 5 7		UnVar7)
(00002C3A 13 20 0		nil->JMP 00002C51)
(00002C3D 5 1		UnVar1)
(00002C3F 5 1		UnVar1)
(00002C41 53 1 217 2 1 32		selection)
(00002C47 5 4		UnVar4)
(00002C49 95 3 19 48 0 0		_replace-selection)
(00002C4F 8 2		UnVar2)
(00002C51 5 6		UnVar6)
(00002C53 13 2 0		nil->JMP 00002C58)
(00002C56 1		nil)
(00002C57 22		ret)
(00002C58 9 107 3		"VLMSG.DLL")
(00002C5B 51 142 93 0 0		23950)
(00002C60 81 2 106 3 1 0		string-resource)
(00002C66 81 1 45 3 1 0		ales-prompt-msg)
(00002C6C 10)
(00002C6D 5 0		UnVar0)
(00002C6F 5 1		UnVar1)
(00002C71 5 2		UnVar2)
(00002C73 3 76 2		*editor-search-margins*)
(00002C76 41		cdr)
(00002C77 95 4 208 34 0 0		editor-search)
(00002C7D 8 8		UnVar8)
(00002C7F 1		nil)
(00002C80 81 1 45 3 1 0		ales-prompt-msg)
(00002C86 10)
(00002C87 5 8		UnVar8)
(00002C89 13 25 0		nil->JMP 00002CA5)
(00002C8C 3 49 2		*editor-mark-found*)
(00002C8F 13 9 0		nil->JMP 00002C9B)
(00002C92 5 1		UnVar1)
(00002C94 53 1 48 2 1 32		!mark-ring-add)
(00002C9A 10)
(00002C9B 5 1		UnVar1)
(00002C9D 5 8		UnVar8)
(00002C9F 47 2 133 2 32 32		selection<-)
(00002CA5 3 76 2		*editor-search-margins*)
(00002CA8 13 21 0		nil->JMP 00002CC0)
(00002CAB 5 0		UnVar0)
(00002CAD 5 1		UnVar1)
(00002CAF 5 3		UnVar3)
(00002CB1 5 4		UnVar4)
(00002CB3 95 4 121 45 0 0		func 00002D79)
(00002CB9 10)
(00002CBA 1		nil)
(00002CBB 11)
(00002CBC 6 76 2		*editor-search-margins*)
(00002CBF 22		ret)
(00002CC0 5 0		UnVar0)
(00002CC2 5 1		UnVar1)
(00002CC4 5 2		UnVar2)
(00002CC6 5 3		UnVar3)
(00002CC8 5 4		UnVar4)
(00002CCA 97 5 220 44 0 0		offset 00002CDC)
(00002CD0 81 0 206 2 1 0		message-beep)
(00002CD6 22		ret)
;;;def nil 11479
(00002CD7 20 6 4 5 0)
(00002CDC 100 5		UNVar5)
(00002CDE 3 85 2		*editor-forward-search*)
(00002CE1 13 5 0		nil->JMP 00002CE9)
(00002CE4 50 0		0)
(00002CE6 15 8 0		JMP 00002CF1)
(00002CE9 5 1		UnVar1)
(00002CEB 81 1 209 2 1 0		TBuf.length)
(00002CF1 8 5		UnVar5)
(00002CF3 5 2		UnVar2)
(00002CF5 5 5		UnVar5)
(00002CF7 81 2 86 2 1 0		=)
(00002CFD 13 28 0		nil->JMP 00002D1C)
(00002D00 3 156 2		*info-alert*)
(00002D03 9 107 3		"VLMSG.DLL")
(00002D06 51 152 93 0 0		23960)
(00002D0B 81 2 106 3 1 0		string-resource)
(00002D11 5 0		UnVar0)
(00002D13 53 3 85 3 1 32		alert)
(00002D19 10)
(00002D1A 1		nil)
(00002D1B 22		ret)
(00002D1C 9 47 2		':OK)
(00002D1F 3 46 2		*confirm-alert*)
(00002D22 9 107 3		"VLMSG.DLL")
(00002D25 51 162 93 0 0		23970)
(00002D2A 81 2 106 3 1 0		string-resource)
(00002D30 3 85 2		*editor-forward-search*)
(00002D33 13 17 0		nil->JMP 00002D47)
(00002D36 9 107 3		"VLMSG.DLL")
(00002D39 51 172 93 0 0		23980)
(00002D3E 81 2 106 3 1 0		string-resource)
(00002D44 15 14 0		JMP 00002D55)
(00002D47 9 107 3		"VLMSG.DLL")
(00002D4A 51 182 93 0 0		23990)
(00002D4F 81 2 106 3 1 0		string-resource)
(00002D55 81 2 75 3 1 0		concat)
(00002D5B 5 0		UnVar0)
(00002D5D 53 3 85 3 1 32		alert)
(00002D63 38		=)
(00002D64 13 16 0		nil->JMP 00002D77)
(00002D67 5 0		UnVar0)
(00002D69 5 1		UnVar1)
(00002D6B 5 5		UnVar5)
(00002D6D 5 3		UnVar3)
(00002D6F 5 4		UnVar4)
(00002D71 96 5 154 43 0 0		func 00002B9A)
(00002D77 1		nil)
(00002D78 22		ret)
;;;def nil 11641
(00002D79 20 6 3 4 0)
(00002D7E 100 4		UNVar4)
(00002D80 100 5		UNVar5)
(00002D82 3 76 2		*editor-search-margins*)
(00002D85 41		cdr)
(00002D86 8 4		UnVar4)
(00002D88 3 85 2		*editor-forward-search*)
(00002D8B 13 11 0		nil->JMP 00002D99)
(00002D8E 5 1		UnVar1)
(00002D90 81 1 209 2 1 0		TBuf.length)
(00002D96 15 2 0		JMP 00002D9B)
(00002D99 50 0		0)
(00002D9B 8 5		UnVar5)
(00002D9D 5 4		UnVar4)
(00002D9F 5 5		UnVar5)
(00002DA1 81 2 86 2 1 0		=)
(00002DA7 13 28 0		nil->JMP 00002DC6)
(00002DAA 3 156 2		*info-alert*)
(00002DAD 9 107 3		"VLMSG.DLL")
(00002DB0 51 152 93 0 0		23960)
(00002DB5 81 2 106 3 1 0		string-resource)
(00002DBB 5 0		UnVar0)
(00002DBD 53 3 85 3 1 32		alert)
(00002DC3 10)
(00002DC4 1		nil)
(00002DC5 22		ret)
(00002DC6 9 47 2		':OK)
(00002DC9 3 46 2		*confirm-alert*)
(00002DCC 9 107 3		"VLMSG.DLL")
(00002DCF 51 162 93 0 0		23970)
(00002DD4 81 2 106 3 1 0		string-resource)
(00002DDA 3 85 2		*editor-forward-search*)
(00002DDD 13 17 0		nil->JMP 00002DF1)
(00002DE0 9 107 3		"VLMSG.DLL")
(00002DE3 51 192 93 0 0		24000)
(00002DE8 81 2 106 3 1 0		string-resource)
(00002DEE 15 14 0		JMP 00002DFF)
(00002DF1 9 107 3		"VLMSG.DLL")
(00002DF4 51 202 93 0 0		24010)
(00002DF9 81 2 106 3 1 0		string-resource)
(00002DFF 81 2 75 3 1 0		concat)
(00002E05 5 0		UnVar0)
(00002E07 53 3 85 3 1 32		alert)
(00002E0D 38		=)
(00002E0E 13 27 0		nil->JMP 00002E2C)
(00002E11 9 76 2		'*editor-search-margins*)
(00002E14 1		nil)
(00002E15 24 2 0)
(00002E18 5 0		UnVar0)
(00002E1A 5 1		UnVar1)
(00002E1C 5 4		UnVar4)
(00002E1E 5 2		UnVar2)
(00002E20 5 3		UnVar3)
(00002E22 95 5 154 43 0 0		func 00002B9A)
(00002E28 25 1 0)
(00002E2B 22		ret)
(00002E2C 1		nil)
(00002E2D 22		ret)
;;;def replace-all! 11822
(00002E2E 20 10 0 5 0)
(00002E33 100 5		UNVar5)
(00002E35 100 6		UNVar6)
(00002E37 100 7		UNVar7)
(00002E39 100 8		UNVar8)
(00002E3B 5 0		UnVar0)
(00002E3D 81 1 135 3 1 0		TWinp)
(00002E43 13 3 0		nil->JMP 00002E49)
(00002E46 15 5 0		JMP 00002E4E)
(00002E49 3 205 2		*active-mdiwindow*)
(00002E4C 8 0		UnVar0)
(00002E4E 5 1		UnVar1)
(00002E50 13 3 0		nil->JMP 00002E56)
(00002E53 15 5 0		JMP 00002E5B)
(00002E56 3 78 2		*editor-find-what*)
(00002E59 8 1		UnVar1)
(00002E5B 5 2		UnVar2)
(00002E5D 13 3 0		nil->JMP 00002E63)
(00002E60 15 5 0		JMP 00002E68)
(00002E63 3 77 2		*editor-replace-with*)
(00002E66 8 2		UnVar2)
(00002E68 5 4		UnVar4)
(00002E6A 13 3 0		nil->JMP 00002E70)
(00002E6D 15 22 0		JMP 00002E86)
(00002E70 3 76 2		*editor-search-margins*)
(00002E73 13 16 0		nil->JMP 00002E86)
(00002E76 3 76 2		*editor-search-margins*)
(00002E79 40		car)
(00002E7A 3 76 2		*editor-search-margins*)
(00002E7D 41		cdr)
(00002E7E 81 2 134 2 1 0		MAX)
(00002E84 8 4		UnVar4)
(00002E86 5 3		UnVar3)
(00002E88 13 3 0		nil->JMP 00002E8E)
(00002E8B 15 27 0		JMP 00002EA9)
(00002E8E 3 76 2		*editor-search-margins*)
(00002E91 13 17 0		nil->JMP 00002EA5)
(00002E94 3 76 2		*editor-search-margins*)
(00002E97 40		car)
(00002E98 3 76 2		*editor-search-margins*)
(00002E9B 41		cdr)
(00002E9C 81 2 136 2 1 0		MIN)
(00002EA2 15 2 0		JMP 00002EA7)
(00002EA5 50 0		0)
(00002EA7 8 3		UnVar3)
(00002EA9 5 3		UnVar3)
(00002EAB 8 8		UnVar8)
(00002EAD 5 0		UnVar0)
(00002EAF 95 1 180 41 0 0		!?replace)
(00002EB5 13 12 0		nil->JMP 00002EC4)
(00002EB8 5 1		UnVar1)
(00002EBA 95 1 143 33 0 0		_fine-stringp)
(00002EC0 35		not)
(00002EC1 15 1 0		JMP 00002EC5)
(00002EC4 2		T)
(00002EC5 13 7 0		nil->JMP 00002ECF)
(00002EC8 81 0 206 2 1 0		message-beep)
(00002ECE 22		ret)
(00002ECF 9 85 2		'*editor-forward-search*)
(00002ED2 2		T)
(00002ED3 24 2 0)
(00002ED6 5 2		UnVar2)
(00002ED8 13 7 0		nil->JMP 00002EE2)
(00002EDB 5 2		UnVar2)
(00002EDD 37 4		stringp)
(00002EDF 15 1 0		JMP 00002EE3)
(00002EE2 2		T)
(00002EE3 9 107 3		"VLMSG.DLL")
(00002EE6 51 212 93 0 0		24020)
(00002EEB 81 2 106 3 1 0		string-resource)
(00002EF1 5 2		UnVar2)
(00002EF3 53 3 17 3 1 32		assert)
(00002EF9 10)
(00002EFA 5 4		UnVar4)
(00002EFC 13 18 0		nil->JMP 00002F11)
(00002EFF 9 45 2		':OWNER)
(00002F02 5 0		UnVar0)
(00002F04 9 44 2		':SEAT)
(00002F07 5 4		UnVar4)
(00002F09 53 4 43 2 1 32		tmark)
(00002F0F 8 5		UnVar5)
(00002F11 5 0		UnVar0)
(00002F13 5 0		UnVar0)
(00002F15 53 1 217 2 1 32		selection)
(00002F1B 40		car)
(00002F1C 8 9		UnVar9)
(00002F1E 5 9		UnVar9)
(00002F20 5 9		UnVar9)
(00002F22 42		cons)
(00002F23 53 2 133 2 1 32		selection<-)
(00002F29 10)
(00002F2A 50 0		0)
(00002F2C 8 7		UnVar7)
(00002F2E 9 107 3		"VLMSG.DLL")
(00002F31 51 222 93 0 0		24030)
(00002F36 81 2 106 3 1 0		string-resource)
(00002F3C 81 1 45 3 1 0		ales-prompt-msg)
(00002F42 10)
(00002F43 5 0		UnVar0)
(00002F45 81 1 42 2 1 0		TBuf.undo-sta)
(00002F4B 10)
(00002F4C 15 19 0		JMP 00002F62)
(00002F4F 5 0		UnVar0)
(00002F51 5 6		UnVar6)
(00002F53 5 2		UnVar2)
(00002F55 95 3 19 48 0 0		_replace-selection)
(00002F5B 8 3		UnVar3)
(00002F5D 5 7		UnVar7)
(00002F5F 79		1+)
(00002F60 8 7		UnVar7)
(00002F62 5 1		UnVar1)
(00002F64 5 0		UnVar0)
(00002F66 5 3		UnVar3)
(00002F68 5 4		UnVar4)
(00002F6A 61 8 0		nil->JMP 00002F75)
(00002F6D 5 5		UnVar5)
(00002F6F 53 1 212 2 1 32		seat)
(00002F75 95 4 208 34 0 0		editor-search)
(00002F7B 11)
(00002F7C 8 6		UnVar6)
(00002F7E 61 20 0		nil->JMP 00002F95)
(00002F81 5 0		UnVar0)
(00002F83 5 6		UnVar6)
(00002F85 40		car)
(00002F86 5 6		UnVar6)
(00002F88 41		cdr)
(00002F89 81 2 136 2 1 0		MIN)
(00002F8F 95 2 210 41 0 0		func 000029D2)
(00002F95 60 183 255		T->JMP 00002F4F)
(00002F98 5 0		UnVar0)
(00002F9A 81 1 41 2 1 0		TBuf.undo-end)
(00002FA0 10)
(00002FA1 1		nil)
(00002FA2 81 1 45 3 1 0		ales-prompt-msg)
(00002FA8 10)
(00002FA9 5 7		UnVar7)
(00002FAB 81 1 40 2 1 0		ZEROP)
(00002FB1 13 37 0		nil->JMP 00002FD9)
(00002FB4 81 0 206 2 1 0		message-beep)
(00002FBA 10)
(00002FBB 3 156 2		*info-alert*)
(00002FBE 9 107 3		"VLMSG.DLL")
(00002FC1 51 232 93 0 0		24040)
(00002FC6 81 2 106 3 1 0		string-resource)
(00002FCC 5 1		UnVar1)
(00002FCE 53 3 85 3 1 32		alert)
(00002FD4 10)
(00002FD5 1		nil)
(00002FD6 15 54 0		JMP 0000300F)
(00002FD9 3 156 2		*info-alert*)
(00002FDC 9 107 3		"VLMSG.DLL")
(00002FDF 51 242 93 0 0		24050)
(00002FE4 81 2 106 3 1 0		string-resource)
(00002FEA 5 7		UnVar7)
(00002FEC 53 3 85 3 1 32		alert)
(00002FF2 10)
(00002FF3 5 0		UnVar0)
(00002FF5 5 4		UnVar4)
(00002FF7 13 8 0		nil->JMP 00003002)
(00002FFA 5 8		UnVar8)
(00002FFC 5 5		UnVar5)
(00002FFE 42		cons)
(00002FFF 15 5 0		JMP 00003007)
(00003002 5 8		UnVar8)
(00003004 5 8		UnVar8)
(00003006 42		cons)
(00003007 53 2 133 2 1 32		selection<-)
(0000300D 10)
(0000300E 2		T)
(0000300F 25 1 0)
(00003012 22		ret)
;;;def _replace-selection 12307
(00003013 20 5 3 3 0)
(00003018 5 1		UnVar1)
(0000301A 41		cdr)
(0000301B 5 1		UnVar1)
(0000301D 40		car)
(0000301E 81 2 136 2 1 0		MIN)
(00003024 8 3		UnVar3)
(00003026 5 1		UnVar1)
(00003028 41		cdr)
(00003029 5 1		UnVar1)
(0000302B 40		car)
(0000302C 71		-)
(0000302D 81 1 58 2 1 0		ABS)
(00003033 8 4		UnVar4)
(00003035 5 0		UnVar0)
(00003037 5 3		UnVar3)
(00003039 5 4		UnVar4)
(0000303B 81 3 103 2 1 0		TBuf.delete)
(00003041 10)
(00003042 5 2		UnVar2)
(00003044 13 13 0		nil->JMP 00003054)
(00003047 5 0		UnVar0)
(00003049 5 3		UnVar3)
(0000304B 5 2		UnVar2)
(0000304D 81 3 80 3 1 0		TBuf.insert)
(00003053 10)
(00003054 3 85 2		*editor-forward-search*)
(00003057 13 27 0		nil->JMP 00003075)
(0000305A 5 2		UnVar2)
(0000305C 13 11 0		nil->JMP 0000306A)
(0000305F 5 2		UnVar2)
(00003061 81 1 93 2 1 0		string-length)
(00003067 15 2 0		JMP 0000306C)
(0000306A 50 0		0)
(0000306C 5 3		UnVar3)
(0000306E 81 2 39 2 1 0		+)
(00003074 22		ret)
(00003075 5 3		UnVar3)
(00003077 22		ret)
;;;def !find-via-ribbon 12408
(00003078 20 1 0 1 0)
(0000307D 5 0		UnVar0)
(0000307F 81 1 135 3 1 0		TWinp)
(00003085 13 3 0		nil->JMP 0000308B)
(00003088 15 5 0		JMP 00003090)
(0000308B 3 205 2		*active-mdiwindow*)
(0000308E 8 0		UnVar0)
(00003090 5 0		UnVar0)
(00003092 95 1 143 41 0 0		!?find)
(00003098 13 49 0		nil->JMP 000030CC)
(0000309B 2		T)
(0000309C 6 81 2		*next-is-find*)
(0000309F 3 51 2		*lb-find-next*)
(000030A2 53 1 38 2 1 32		accessed-verify)
(000030A8 10)
(000030A9 3 51 2		*lb-find-next*)
(000030AC 53 1 56 2 1 32		sync-down)
(000030B2 10)
(000030B3 95 0 68 41 0 0		update-find-hist)
(000030B9 10)
(000030BA 5 0		UnVar0)
(000030BC 95 1 62 36 0 0		next-find/replace!)
(000030C2 63		nil->ret)
(000030C3 5 0		UnVar0)
(000030C5 81 1 37 2 1 0		mdiwindow-activate)
(000030CB 22		ret)
(000030CC 81 0 206 2 1 0		message-beep)
(000030D2 22		ret)
;;;def !goto-line 12499
(000030D3 20 2 1 1 0)
(000030D8 100 1		UNVar1)
(000030DA 9 107 3		"VLMSG.DLL")
(000030DD 51 252 93 0 0		24060)
(000030E2 81 2 106 3 1 0		string-resource)
(000030E8 9 36 2		nil)
(000030EB 9 35 2		'(fixnum))
(000030EE 5 0		UnVar0)
(000030F0 9 229 2		'l-context)
(000030F3 81 2 86 3 1 0		slot-value)
(000030F9 1		nil)
(000030FA 1		nil)
(000030FB 1		nil)
(000030FC 51 135 0 0 0		135)
(00003101 53 8 34 2 1 32		p-get-value-dialog)
(00003107 8 1		UnVar1)
(00003109 5 1		UnVar1)
(0000310B 81 1 33 2 1 0		fixnump)
(00003111 13 43 0		nil->JMP 0000313F)
(00003114 5 0		UnVar0)
(00003116 53 1 48 2 1 32		!mark-ring-add)
(0000311C 10)
(0000311D 5 0		UnVar0)
(0000311F 5 0		UnVar0)
(00003121 5 1		UnVar1)
(00003123 50 0		0)
(00003125 75		>)
(00003126 13 6 0		nil->JMP 0000312F)
(00003129 5 1		UnVar1)
(0000312B 80		1-)
(0000312C 15 2 0		JMP 00003131)
(0000312F 5 1		UnVar1)
(00003131 81 2 32 2 1 0		TBuf.line->pos)
(00003137 1		nil)
(00003138 81 3 208 2 1 0		TWin.cpos<-)
(0000313E 22		ret)
(0000313F 81 0 206 2 1 0		message-beep)
(00003145 22		ret)
;;;def !cursor-info 12614
(00003146 20 9 1 1 0)
(0000314B 100 1		UNVar1)
(0000314D 100 2		UNVar2)
(0000314F 100 3		UNVar3)
(00003151 100 4		UNVar4)
(00003153 100 5		UNVar5)
(00003155 100 6		UNVar6)
(00003157 5 0		UnVar0)
(00003159 81 1 135 3 1 0		TWinp)
(0000315F 13 3 0		nil->JMP 00003165)
(00003162 15 5 0		JMP 0000316A)
(00003165 3 205 2		*active-mdiwindow*)
(00003168 8 0		UnVar0)
(0000316A 5 0		UnVar0)
(0000316C 81 1 209 2 1 0		TBuf.length)
(00003172 8 6		UnVar6)
(00003174 5 0		UnVar0)
(00003176 81 1 167 2 1 0		TWin.cpos)
(0000317C 8 5		UnVar5)
(0000317E 5 0		UnVar0)
(00003180 5 5		UnVar5)
(00003182 81 2 31 2 1 0		TBuf.pos->line)
(00003188 8 4		UnVar4)
(0000318A 5 0		UnVar0)
(0000318C 5 5		UnVar5)
(0000318E 81 2 99 2 1 0		TBuf.BOL-pos)
(00003194 8 3		UnVar3)
(00003196 5 0		UnVar0)
(00003198 81 1 30 2 1 0		TWin.sel)
(0000319E 8 2		UnVar2)
(000031A0 5 2		UnVar2)
(000031A2 81 1 29 2 1 0		color-mark.length)
(000031A8 8 1		UnVar1)
(000031AA 9 107 3		"VLMSG.DLL")
(000031AD 51 6 94 0 0		24070)
(000031B2 81 2 106 3 1 0		string-resource)
(000031B8 3 28 2		MB_ICONASTERISK)
(000031BB 1		nil)
(000031BC 53 3 27 2 1 32		alert-info)
(000031C2 9 107 3		"VLMSG.DLL")
(000031C5 51 16 94 0 0		24080)
(000031CA 81 2 106 3 1 0		string-resource)
(000031D0 5 4		UnVar4)
(000031D2 79		1+)
(000031D3 5 0		UnVar0)
(000031D5 5 6		UnVar6)
(000031D7 81 2 31 2 1 0		TBuf.pos->line)
(000031DD 79		1+)
(000031DE 5 5		UnVar5)
(000031E0 5 6		UnVar6)
(000031E2 5 5		UnVar5)
(000031E4 5 3		UnVar3)
(000031E6 71		-)
(000031E7 79		1+)
(000031E8 5 0		UnVar0)
(000031EA 5 5		UnVar5)
(000031EC 81 2 128 2 1 0		TBuf.EOL-pos)
(000031F2 5 3		UnVar3)
(000031F4 71		-)
(000031F5 79		1+)
(000031F6 5 1		UnVar1)
(000031F8 50 0		0)
(000031FA 75		>)
(000031FB 13 17 0		nil->JMP 0000320F)
(000031FE 9 107 3		"VLMSG.DLL")
(00003201 51 26 94 0 0		24090)
(00003206 81 2 106 3 1 0		string-resource)
(0000320C 15 3 0		JMP 00003212)
(0000320F 9 26 2		"~*")
(00003212 5 1		UnVar1)
(00003214 50 0		0)
(00003216 75		>)
(00003217 61 78 0		nil->JMP 00003268)
(0000321A 5 2		UnVar2)
(0000321C 81 1 25 2 1 0		color-mark.start)
(00003222 8 7		UnVar7)
(00003224 100 8		UNVar8)
(00003226 5 7		UnVar7)
(00003228 5 1		UnVar1)
(0000322A 70		+)
(0000322B 8 8		UnVar8)
(0000322D 5 0		UnVar0)
(0000322F 5 8		UnVar8)
(00003231 81 2 31 2 1 0		TBuf.pos->line)
(00003237 5 0		UnVar0)
(00003239 5 7		UnVar7)
(0000323B 81 2 31 2 1 0		TBuf.pos->line)
(00003241 71		-)
(00003242 79		1+)
(00003243 5 0		UnVar0)
(00003245 5 0		UnVar0)
(00003247 9 229 2		'l-context)
(0000324A 81 2 86 3 1 0		slot-value)
(00003250 53 1 105 2 1 32		cntx-wsep)
(00003256 5 8		UnVar8)
(00003258 5 7		UnVar7)
(0000325A 5 8		UnVar8)
(0000325C 81 5 104 2 1 0		TBuf.scan-words)
(00003262 41		cdr)
(00003263 5 1		UnVar1)
(00003265 57 3 0		list)
(00003268 53 10 85 3 1 32		alert)
(0000326E 10)
(0000326F 1		nil)
(00003270 22		ret)
;;;def !find-fast 12913
(00003271 20 2 1 1 0)
(00003276 100 1		UNVar1)
(00003278 5 0		UnVar0)
(0000327A 81 1 135 3 1 0		TWinp)
(00003280 13 3 0		nil->JMP 00003286)
(00003283 15 5 0		JMP 0000328B)
(00003286 3 205 2		*active-mdiwindow*)
(00003289 8 0		UnVar0)
(0000328B 5 0		UnVar0)
(0000328D 50 64		64)
(0000328F 53 2 198 2 1 32		twin-active-selection)
(00003295 14 8 0		T->JMP 000032A0)
(00003298 5 0		UnVar0)
(0000329A 53 1 24 2 1 32		twin-active-word)
(000032A0 8 1		UnVar1)
(000032A2 5 1		UnVar1)
(000032A4 13 41 0		nil->JMP 000032D0)
(000032A7 5 1		UnVar1)
(000032A9 6 78 2		*editor-find-what*)
(000032AC 5 1		UnVar1)
(000032AE 3 23 2		*editor-find-what-hist*)
(000032B1 53 2 22 2 1 32		_add-item)
(000032B7 6 23 2		*editor-find-what-hist*)
(000032BA 2		T)
(000032BB 6 81 2		*next-is-find*)
(000032BE 95 0 68 41 0 0		update-find-hist)
(000032C4 10)
(000032C5 5 0		UnVar0)
(000032C7 2		T)
(000032C8 5 1		UnVar1)
(000032CA 96 3 62 36 0 0		next-find/replace!)
(000032D0 5 0		UnVar0)
(000032D2 96 1 82 37 0 0		find!)
;;;def nil 13016
(000032D8 20 2 2 2 0)
(000032DD 1		nil)
(000032DE 9 21 2		"\003\003\003((lambda(/ id)(setq id(LOAD_DIALOG ~s))~\n(cond((>= id 0)(if(NEW_DIALOG ~s id \"(done_dialog)\")~\n(START_DIALOG))(UNLOAD_DIALOG id))))) ")
(000032E1 5 0		UnVar0)
(000032E3 5 1		UnVar1)
(000032E5 53 4 1 3 1 32		format)
(000032EB 1		nil)
(000032EC 47 2 20 2 32 32		ACAD-cmd)
;;;def !?preview-dcl-dialog 13042
(000032F2 20 1 1 1 0)
(000032F7 5 0		UnVar0)
(000032F9 53 1 91 3 1 32		editorp)
(000032FF 63		nil->ret)
(00003300 5 0		UnVar0)
(00003302 81 1 132 2 1 0		TBuf.lex-scanner-id)
(00003308 9 19 2		'(nil :DCL))
(0000330B 81 2 114 3 1 0		memq)
(00003311 63		nil->ret)
(00003312 81 0 18 2 1 0		acad-has-window-p)
(00003318 63		nil->ret)
(00003319 3 17 2		_%in-dcl-call-back%)
(0000331C 35		not)
(0000331D 22		ret)
;;;def !preview-dcl-dialog 13086
(0000331E 20 2 1 2 0)
(00003323 5 0		UnVar0)
(00003325 81 1 135 3 1 0		TWinp)
(0000332B 60 5 0		T->JMP 00003333)
(0000332E 3 205 2		*active-mdiwindow*)
(00003331 8 0		UnVar0)
(00003333 5 1		UnVar1)
(00003335 13 20 0		nil->JMP 0000334C)
(00003338 5 0		UnVar0)
(0000333A 81 1 30 2 1 0		TWin.sel)
(00003340 53 1 212 2 1 32		seat)
(00003346 11)
(00003347 8 1		UnVar1)
(00003349 15 1 0		JMP 0000334D)
(0000334C 2		T)
(0000334D 61 8 0		nil->JMP 00003358)
(00003350 5 0		UnVar0)
(00003352 95 1 242 50 0 0		!?preview-dcl-dialog)
(00003358 13 10 0		nil->JMP 00003365)
(0000335B 5 0		UnVar0)
(0000335D 5 1		UnVar1)
(0000335F 47 2 16 2 32 32		_do-preview-dcl-dialog)
(00003365 81 0 206 2 1 0		message-beep)
(0000336B 22		ret)
;;;def _do-preview-dcl-dialog 13164
(0000336C 21 6 2 2 0)
(00003371 100 2		UNVar2)
(00003373 5 1		UnVar1)
(00003375 37 2		consp)
(00003377 13 28 0		nil->JMP 00003396)
(0000337A 5 1		UnVar1)
(0000337C 40		car)
(0000337D 5 1		UnVar1)
(0000337F 41		cdr)
(00003380 81 2 136 2 1 0		MIN)
(00003386 5 1		UnVar1)
(00003388 40		car)
(00003389 5 1		UnVar1)
(0000338B 41		cdr)
(0000338C 81 2 134 2 1 0		MAX)
(00003392 42		cons)
(00003393 15 11 0		JMP 000033A1)
(00003396 50 0		0)
(00003398 5 0		UnVar0)
(0000339A 81 1 209 2 1 0		TBuf.length)
(000033A0 42		cons)
(000033A1 8 1		UnVar1)
(000033A3 100 2		UNVar2)
(000033A5 3 15 2		*dcl-tmp-file*)
(000033A8 9 65 3		':OUTPUT)
(000033AB 1		nil)
(000033AC 81 3 64 3 1 0		open)
(000033B2 8 3		UnVar3)
(000033B4 5 3		UnVar3)
(000033B6 8 4		UnVar4)
(000033B8 15 35 0		JMP 000033DE)
(000033BB 20 0 0 0 0)
(000033C0 4 1 3		UpVar1-3)
(000033C3 81 1 63 3 1 0		streamp)
(000033C9 63		nil->ret)
(000033CA 4 1 3		UpVar1-3)
(000033CD 81 1 62 3 1 0		open-streamp)
(000033D3 63		nil->ret)
(000033D4 4 1 3		UpVar1-3)
(000033D7 81 1 61 3 1 0		close)
(000033DD 22		ret)
(000033DE 12 184 3		'(13243 -unwind-cleanup-))
(000033E1 15 80 0		JMP 00003434)
(000033E4 20 0 0 0 0)
(000033E9 4 1 4		UpVar1-4)
(000033EC 13 46 0		nil->JMP 0000341D)
(000033EF 4 1 0		UpVar1-0)
(000033F2 9 14 2		"default_dcl_settings")
(000033F5 1		nil)
(000033F6 4 1 1		UpVar1-1)
(000033F9 40		car)
(000033FA 4 1 1		UpVar1-1)
(000033FD 41		cdr)
(000033FE 81 5 84 2 1 0		TBuf.search-forward)
(00003404 13 3 0		nil->JMP 0000340A)
(00003407 15 13 0		JMP 00003417)
(0000340A 9 13 2		"dcl_settings : default_dcl_settings { audit_level = 1; }")
(0000340D 4 1 4		UpVar1-4)
(00003410 81 2 121 3 1 0		write-line)
(00003416 10)
(00003417 2		T)
(00003418 11)
(00003419 7 1 2		UpVar1-2)
(0000341C 22		ret)
(0000341D 9 107 3		"VLMSG.DLL")
(00003420 51 22 83 0 0		21270)
(00003425 81 2 106 3 1 0		string-resource)
(0000342B 3 15 2		*dcl-tmp-file*)
(0000342E 47 2 12 2 32 32		_msg-warn)
(00003434 12 183 3		'(13284 -unwind-protect-))
(00003437 1		nil)
(00003438 81 3 117 3 1 0		_unwinded-apply)
(0000343E 10)
(0000343F 5 2		UnVar2)
(00003441 13 50 0		nil->JMP 00003476)
(00003444 5 0		UnVar0)
(00003446 3 15 2		*dcl-tmp-file*)
(00003449 5 1		UnVar1)
(0000344B 40		car)
(0000344C 5 1		UnVar1)
(0000344E 41		cdr)
(0000344F 2		T)
(00003450 81 5 11 2 1 0		TBuf.write-region)
(00003456 13 3 0		nil->JMP 0000345C)
(00003459 15 26 0		JMP 00003476)
(0000345C 100 2		UNVar2)
(0000345E 9 107 3		"VLMSG.DLL")
(00003461 51 32 83 0 0		21280)
(00003466 81 2 106 3 1 0		string-resource)
(0000346C 3 15 2		*dcl-tmp-file*)
(0000346F 53 2 12 2 1 32		_msg-warn)
(00003475 10)
(00003476 5 2		UnVar2)
(00003478 63		nil->ret)
(00003479 100 2		UNVar2)
(0000347B 9 107 3		"VLMSG.DLL")
(0000347E 51 42 83 0 0		21290)
(00003483 81 2 106 3 1 0		string-resource)
(00003489 81 1 45 3 1 0		ales-prompt-msg)
(0000348F 10)
(00003490 5 0		UnVar0)
(00003492 81 1 132 2 1 0		TBuf.lex-scanner-id)
(00003498 8 5		UnVar5)
(0000349A 5 0		UnVar0)
(0000349C 9 10 2		':DCL)
(0000349F 81 2 9 2 1 0		TBuf.lex-scanner-id<-)
(000034A5 10)
(000034A6 15 18 0		JMP 000034BB)
(000034A9 20 0 0 0 0)
(000034AE 4 1 0		UpVar1-0)
(000034B1 4 1 5		UpVar1-5)
(000034B4 81 2 9 2 1 0		TBuf.lex-scanner-id<-)
(000034BA 22		ret)
(000034BB 12 182 3		'(13481 -unwind-cleanup-))
(000034BE 15 22 0		JMP 000034D7)
(000034C1 20 0 0 0 0)
(000034C6 4 1 0		UpVar1-0)
(000034C9 4 1 1		UpVar1-1)
(000034CC 40		car)
(000034CD 4 1 1		UpVar1-1)
(000034D0 41		cdr)
(000034D1 96 3 232 53 0 0		func 000035E8)
(000034D7 12 181 3		'(13505 -unwind-protect-))
(000034DA 1		nil)
(000034DB 81 3 117 3 1 0		_unwinded-apply)
(000034E1 6 8 2		*dcl-dialog-name-history*)
(000034E4 1		nil)
(000034E5 81 1 45 3 1 0		ales-prompt-msg)
(000034EB 10)
(000034EC 5 0		UnVar0)
(000034EE 15 76 0		JMP 0000353D)
(000034F1 20 3 2 3 0)
(000034F6 9 107 3		"VLMSG.DLL")
(000034F9 51 52 83 0 0		21300)
(000034FE 81 2 106 3 1 0		string-resource)
(00003504 1		nil)
(00003505 81 1 7 2 1 0		box)
(0000350B 9 6 2		'_eval-string-p)
(0000350E 3 5 2		_%al-rep-cntx%)
(00003511 3 4 2		*dcl-dialog-name-last*)
(00003514 3 8 2		*dcl-dialog-name-history*)
(00003517 81 2 3 2 1 0		member)
(0000351D 13 6 0		nil->JMP 00003526)
(00003520 3 4 2		*dcl-dialog-name-last*)
(00003523 15 4 0		JMP 0000352A)
(00003526 3 8 2		*dcl-dialog-name-history*)
(00003529 40		car)
(0000352A 9 2 2		" ")
(0000352D 9 8 2		'*dcl-dialog-name-history*)
(00003530 50 127		127)
(00003532 53 8 1 2 1 32		p-get-expr-dialog)
(00003538 11)
(00003539 7 1 2		UpVar1-2)
(0000353C 22		ret)
(0000353D 12 180 3		'(13553 nil))
(00003540 53 2 63 2 1 32		execute-in-mdiwindow-context)
(00003546 10)
(00003547 5 2		UnVar2)
(00003549 37 4		stringp)
(0000354B 63		nil->ret)
(0000354C 5 2		UnVar2)
(0000354E 6 4 2		*dcl-dialog-name-last*)
(00003551 3 15 2		*dcl-tmp-file*)
(00003554 5 2		UnVar2)
(00003556 95 2 216 50 0 0		func 000032D8)
(0000355C 10)
(0000355D 81 0 148 2 1 0		in-ads-check)
(00003563 61 12 0		nil->JMP 00003572)
(00003566 9 0 2		"ACAD.DCE")
(00003569 81 1 255 1 1 0		as:findfile)
(0000356F 11)
(00003570 8 1		UnVar1)
(00003572 63		nil->ret)
(00003573 5 1		UnVar1)
(00003575 5 0		UnVar0)
(00003577 2		T)
(00003578 96 3 126 24 0 0		open-fresh-editor)
;;;def next-sym/spec/paren 13694
(0000357E 20 7 4 5 0)
(00003583 100 5		UNVar5)
(00003585 100 6		UNVar6)
(00003587 5 0		UnVar0)
(00003589 5 1		UnVar1)
(0000358B 5 3		UnVar3)
(0000358D 5 4		UnVar4)
(0000358F 35		not)
(00003590 81 4 116 2 1 0		TBuf.scan-lex-token)
(00003596 37 2		consp)
(00003598 63		nil->ret)
(00003599 5 3		UnVar3)
(0000359B 41		cdr)
(0000359C 11)
(0000359D 8 6		UnVar6)
(0000359F 5 2		UnVar2)
(000035A1 76		<)
(000035A2 63		nil->ret)
(000035A3 5 3		UnVar3)
(000035A5 40		car)
(000035A6 11)
(000035A7 8 5		UnVar5)
(000035A9 9 254 1		'(2 3 10 11))
(000035AC 81 2 114 3 1 0		memq)
(000035B2 13 35 0		nil->JMP 000035D8)
(000035B5 5 4		UnVar4)
(000035B7 13 15 0		nil->JMP 000035C9)
(000035BA 5 3		UnVar3)
(000035BC 5 1		UnVar1)
(000035BE 5 3		UnVar3)
(000035C0 41		cdr)
(000035C1 42		cons)
(000035C2 81 2 253 1 1 0		rplacd)
(000035C8 22		ret)
(000035C9 5 0		UnVar0)
(000035CB 5 1		UnVar1)
(000035CD 5 2		UnVar2)
(000035CF 5 3		UnVar3)
(000035D1 2		T)
(000035D2 97 5 131 53 0 0		offset 00003583)
(000035D8 5 0		UnVar0)
(000035DA 5 3		UnVar3)
(000035DC 41		cdr)
(000035DD 5 2		UnVar2)
(000035DF 5 3		UnVar3)
(000035E1 1		nil)
(000035E2 97 5 131 53 0 0		offset 00003583)
;;;def nil 13800
(000035E8 20 8 1 3 0)
(000035ED 100 3		UNVar3)
(000035EF 100 4		UNVar4)
(000035F1 100 5		UNVar5)
(000035F3 100 6		UNVar6)
(000035F5 100 7		UNVar7)
(000035F7 5 0		UnVar0)
(000035F9 81 1 132 2 1 0		TBuf.lex-scanner-id)
(000035FF 9 10 2		':DCL)
(00003602 38		=)
(00003603 60 12 0		T->JMP 00003612)
(00003606 9 252 1		"should be :DCL lex-scanner-id in tbuf:")
(00003609 5 0		UnVar0)
(0000360B 81 2 109 3 1 0		_msg-err)
(00003611 10)
(00003612 5 1		UnVar1)
(00003614 60 4 0		T->JMP 0000361B)
(00003617 50 0		0)
(00003619 8 1		UnVar1)
(0000361B 5 2		UnVar2)
(0000361D 60 10 0		T->JMP 0000362A)
(00003620 5 0		UnVar0)
(00003622 81 1 209 2 1 0		TBuf.length)
(00003628 8 2		UnVar2)
(0000362A 1		nil)
(0000362B 81 1 251 1 1 0		ncons)
(00003631 8 7		UnVar7)
(00003633 100 6		UNVar6)
(00003635 100 5		UNVar5)
(00003637 15 156 0		JMP 000036D6)
(0000363A 5 7		UnVar7)
(0000363C 40		car)
(0000363D 8 4		UnVar4)
(0000363F 5 7		UnVar7)
(00003641 41		cdr)
(00003642 40		car)
(00003643 8 3		UnVar3)
(00003645 5 7		UnVar7)
(00003647 41		cdr)
(00003648 41		cdr)
(00003649 8 1		UnVar1)
(0000364B 5 4		UnVar4)
(0000364D 50 3		3)
(0000364F 38		=)
(00003650 13 20 0		nil->JMP 00003667)
(00003653 5 0		UnVar0)
(00003655 5 3		UnVar3)
(00003657 5 1		UnVar1)
(00003659 81 3 96 2 1 0		TBuf.subseq)
(0000365F 5 6		UnVar6)
(00003661 42		cons)
(00003662 8 6		UnVar6)
(00003664 15 111 0		JMP 000036D6)
(00003667 5 0		UnVar0)
(00003669 5 3		UnVar3)
(0000366B 81 2 127 2 1 0		TBuf.char-at)
(00003671 50 58		58)
(00003673 38		=)
(00003674 61 6 0		nil->JMP 0000367D)
(00003677 5 3		UnVar3)
(00003679 5 1		UnVar1)
(0000367B 80		1-)
(0000367C 38		=)
(0000367D 13 3 0		nil->JMP 00003683)
(00003680 15 83 0		JMP 000036D6)
(00003683 5 0		UnVar0)
(00003685 5 7		UnVar7)
(00003687 41		cdr)
(00003688 40		car)
(00003689 81 2 127 2 1 0		TBuf.char-at)
(0000368F 50 123		123)
(00003691 38		=)
(00003692 61 60 0		nil->JMP 000036D1)
(00003695 5 3		UnVar3)
(00003697 5 1		UnVar1)
(00003699 80		1-)
(0000369A 38		=)
(0000369B 61 51 0		nil->JMP 000036D1)
(0000369E 5 0		UnVar0)
(000036A0 5 3		UnVar3)
(000036A2 81 2 123 2 1 0		TBuf.sexp-end-pos)
(000036A8 11)
(000036A9 8 1		UnVar1)
(000036AB 61 35 0		nil->JMP 000036D1)
(000036AE 5 6		UnVar6)
(000036B0 41		cdr)
(000036B1 61 29 0		nil->JMP 000036D1)
(000036B4 5 6		UnVar6)
(000036B6 40		car)
(000036B7 9 250 1		"dialog")
(000036BA 81 2 3 3 1 0		equal)
(000036C0 61 14 0		nil->JMP 000036D1)
(000036C3 5 6		UnVar6)
(000036C5 41		cdr)
(000036C6 40		car)
(000036C7 5 5		UnVar5)
(000036C9 42		cons)
(000036CA 11)
(000036CB 8 5		UnVar5)
(000036CD 61 1 0		nil->JMP 000036D1)
(000036D0 1		nil)
(000036D1 60 2 0		T->JMP 000036D6)
(000036D4 100 6		UNVar6)
(000036D6 5 1		UnVar1)
(000036D8 61 14 0		nil->JMP 000036E9)
(000036DB 5 0		UnVar0)
(000036DD 5 1		UnVar1)
(000036DF 5 2		UnVar2)
(000036E1 5 7		UnVar7)
(000036E3 95 4 126 53 0 0		next-sym/spec/paren)
(000036E9 60 78 255		T->JMP 0000363A)
(000036EC 5 5		UnVar5)
(000036EE 9 249 1		'string<)
(000036F1 81 2 248 1 1 0		sort)
(000036F7 22		ret)
;;;def nil 14072
(000036F8 20 4 1 2 0)
(000036FD 100 2		UNVar2)
(000036FF 100 3		UNVar3)
(00003701 5 0		UnVar0)
(00003703 53 1 105 3 1 32		find-opened-editor)
(00003709 11)
(0000370A 8 3		UnVar3)
(0000370C 13 7 0		nil->JMP 00003716)
(0000370F 5 3		UnVar3)
(00003711 8 2		UnVar2)
(00003713 15 57 0		JMP 0000374F)
(00003716 5 1		UnVar1)
(00003718 81 1 91 2 1 0		TBufp)
(0000371E 13 27 0		nil->JMP 0000373C)
(00003721 5 1		UnVar1)
(00003723 81 1 247 1 1 0		TBuf.empty)
(00003729 10)
(0000372A 5 1		UnVar1)
(0000372C 8 3		UnVar3)
(0000372E 5 1		UnVar1)
(00003730 5 0		UnVar0)
(00003732 81 2 246 1 1 0		TBuf.insert-file)
(00003738 10)
(00003739 15 19 0		JMP 0000374F)
(0000373C 81 0 245 1 1 0		make-TBuf)
(00003742 8 3		UnVar3)
(00003744 5 3		UnVar3)
(00003746 5 0		UnVar0)
(00003748 81 2 246 1 1 0		TBuf.insert-file)
(0000374E 10)
(0000374F 5 2		UnVar2)
(00003751 14 11 0		T->JMP 0000375F)
(00003754 5 0		UnVar0)
(00003756 5 0		UnVar0)
(00003758 81 1 244 1 1 0		file-mod-time)
(0000375E 42		cons)
(0000375F 5 3		UnVar3)
(00003761 42		cons)
(00003762 22		ret)
;;;def grep-filelist-fn 14179
(00003763 20 13 3 3 0)
(00003768 100 3		UNVar3)
(0000376A 100 4		UNVar4)
(0000376C 100 5		UNVar5)
(0000376E 100 6		UNVar6)
(00003770 100 7		UNVar7)
(00003772 100 8		UNVar8)
(00003774 100 9		UNVar9)
(00003776 81 0 245 1 1 0		make-TBuf)
(0000377C 8 8		UnVar8)
(0000377E 5 1		UnVar1)
(00003780 8 10		UnVar10)
(00003782 100 11		UNVar11)
(00003784 15 17 1		JMP 00003898)
(00003787 5 10		UnVar10)
(00003789 40		car)
(0000378A 8 11		UnVar11)
(0000378C 5 10		UnVar10)
(0000378E 41		cdr)
(0000378F 8 10		UnVar10)
(00003791 5 11		UnVar11)
(00003793 37 4		stringp)
(00003795 13 233 0		nil->JMP 00003881)
(00003798 5 11		UnVar11)
(0000379A 81 1 94 2 1 0		file-directory-p)
(000037A0 13 26 0		nil->JMP 000037BD)
(000037A3 9 107 3		"VLMSG.DLL")
(000037A6 51 34 86 0 0		22050)
(000037AB 81 2 106 3 1 0		string-resource)
(000037B1 5 11		UnVar11)
(000037B3 95 2 241 56 0 0		grep-message)
(000037B9 10)
(000037BA 15 193 0		JMP 0000387E)
(000037BD 5 11		UnVar11)
(000037BF 81 1 100 3 1 0		file-readable-p)
(000037C5 13 159 0		nil->JMP 00003867)
(000037C8 100 3		UNVar3)
(000037CA 5 11		UnVar11)
(000037CC 5 8		UnVar8)
(000037CE 95 2 248 54 0 0		func 000036F8)
(000037D4 8 12		UnVar12)
(000037D6 5 12		UnVar12)
(000037D8 40		car)
(000037D9 8 6		UnVar6)
(000037DB 5 12		UnVar12)
(000037DD 41		cdr)
(000037DE 8 7		UnVar7)
(000037E0 5 7		UnVar7)
(000037E2 81 1 135 3 1 0		TWinp)
(000037E8 13 28 0		nil->JMP 00003807)
(000037EB 9 45 2		':OWNER)
(000037EE 5 7		UnVar7)
(000037F0 9 44 2		':SEAT)
(000037F3 50 0		0)
(000037F5 5 7		UnVar7)
(000037F7 81 1 209 2 1 0		TBuf.length)
(000037FD 42		cons)
(000037FE 53 4 243 1 1 32		rmark)
(00003804 15 2 0		JMP 00003809)
(00003807 5 6		UnVar6)
(00003809 53 1 242 1 1 32		register-istream)
(0000380F 8 5		UnVar5)
(00003811 50 0		0)
(00003813 8 9		UnVar9)
(00003815 15 58 0		JMP 00003852)
(00003818 5 3		UnVar3)
(0000381A 13 3 0		nil->JMP 00003820)
(0000381D 15 15 0		JMP 0000382F)
(00003820 9 241 1		"~&~a~%~!")
(00003823 5 11		UnVar11)
(00003825 95 2 241 56 0 0		grep-message)
(0000382B 10)
(0000382C 2		T)
(0000382D 8 3		UnVar3)
(0000382F 3 240 1		*grep-counter*)
(00003832 79		1+)
(00003833 6 240 1		*grep-counter*)
(00003836 5 7		UnVar7)
(00003838 5 6		UnVar6)
(0000383A 5 4		UnVar4)
(0000383C 5 5		UnVar5)
(0000383E 95 4 16 57 0 0		func 00003910)
(00003844 10)
(00003845 5 7		UnVar7)
(00003847 5 4		UnVar4)
(00003849 41		cdr)
(0000384A 81 2 128 2 1 0		TBuf.EOL-pos)
(00003850 8 9		UnVar9)
(00003852 5 0		UnVar0)
(00003854 5 7		UnVar7)
(00003856 5 9		UnVar9)
(00003858 95 3 208 34 0 0		editor-search)
(0000385E 11)
(0000385F 8 4		UnVar4)
(00003861 60 180 255		T->JMP 00003818)
(00003864 15 23 0		JMP 0000387E)
(00003867 9 107 3		"VLMSG.DLL")
(0000386A 51 44 86 0 0		22060)
(0000386F 81 2 106 3 1 0		string-resource)
(00003875 5 11		UnVar11)
(00003877 95 2 241 56 0 0		grep-message)
(0000387D 10)
(0000387E 15 23 0		JMP 00003898)
(00003881 9 107 3		"VLMSG.DLL")
(00003884 51 24 86 0 0		22040)
(00003889 81 2 106 3 1 0		string-resource)
(0000388F 5 11		UnVar11)
(00003891 81 2 109 3 1 0		_msg-err)
(00003897 10)
(00003898 5 10		UnVar10)
(0000389A 60 234 254		T->JMP 00003787)
(0000389D 1		nil)
(0000389E 22		ret)
;;;def grep-filelist 14495
(0000389F 21 3 2 3 0)
(000038A4 9 85 2		'*editor-forward-search*)
(000038A7 2		T)
(000038A8 9 214 2		'_%curr-rep-cntx%)
(000038AB 5 2		UnVar2)
(000038AD 14 3 0		T->JMP 000038B3)
(000038B0 3 214 2		_%curr-rep-cntx%)
(000038B3 9 240 1		'*grep-counter*)
(000038B6 50 0		0)
(000038B8 24 6 0)
(000038BB 15 20 0		JMP 000038D2)
(000038BE 20 0 0 0 0)
(000038C3 4 1 0		UpVar1-0)
(000038C6 4 1 1		UpVar1-1)
(000038C9 4 1 2		UpVar1-2)
(000038CC 96 3 99 55 0 0		grep-filelist-fn)
(000038D2 12 179 3		'(14526 nil))
(000038D5 9 107 3		"VLMSG.DLL")
(000038D8 51 54 86 0 0		22070)
(000038DD 81 2 106 3 1 0		string-resource)
(000038E3 53 2 239 1 1 32		run-fast)
(000038E9 10)
(000038EA 3 240 1		*grep-counter*)
(000038ED 25 3 0)
(000038F0 22		ret)
;;;def grep-message 14577
(000038F1 20 2 1 1 1)
(000038F6 9 97 3		'prinf)
(000038F9 3 238 1		*grep-output*)
(000038FC 9 237 1		'ostm)
(000038FF 81 2 86 3 1 0		slot-value)
(00003905 5 0		UnVar0)
(00003907 5 1		UnVar1)
(00003909 81 3 186 2 1 0		list*)
(0000390F 84		apply+ret)
;;;def nil 14608
(00003910 20 7 4 4 0)
(00003915 100 4		UNVar4)
(00003917 100 5		UNVar5)
(00003919 100 6		UNVar6)
(0000391B 5 0		UnVar0)
(0000391D 5 2		UnVar2)
(0000391F 40		car)
(00003920 81 2 99 2 1 0		TBuf.BOL-pos)
(00003926 8 6		UnVar6)
(00003928 5 0		UnVar0)
(0000392A 5 2		UnVar2)
(0000392C 41		cdr)
(0000392D 81 2 128 2 1 0		TBuf.EOL-pos)
(00003933 8 5		UnVar5)
(00003935 3 238 1		*grep-output*)
(00003938 9 237 1		'ostm)
(0000393B 81 2 86 3 1 0		slot-value)
(00003941 8 4		UnVar4)
(00003943 9 236 1		'*msg-default-prompt*)
(00003946 9 107 3		"VLMSG.DLL")
(00003949 51 64 86 0 0		22080)
(0000394E 81 2 106 3 1 0		string-resource)
(00003954 9 235 1		'*msg-default-title*)
(00003957 9 107 3		"VLMSG.DLL")
(0000395A 51 74 86 0 0		22090)
(0000395F 81 2 106 3 1 0		string-resource)
(00003965 24 4 0)
(00003968 5 4		UnVar4)
(0000396A 81 1 234 1 1 0		fresh-line)
(00003970 10)
(00003971 5 4		UnVar4)
(00003973 5 3		UnVar3)
(00003975 5 2		UnVar2)
(00003977 40		car)
(00003978 5 2		UnVar2)
(0000397A 41		cdr)
(0000397B 53 3 233 1 1 32		instantiate-show-item)
(00003981 9 232 1		"\t~a")
(00003984 5 0		UnVar0)
(00003986 5 6		UnVar6)
(00003988 5 5		UnVar5)
(0000398A 81 3 96 2 1 0		TBuf.subseq)
(00003990 53 4 231 1 1 32		prinf-msg)
(00003996 10)
(00003997 5 4		UnVar4)
(00003999 81 1 125 3 1 0		terpri)
(0000399F 25 2 0)
(000039A2 22		ret)
;;;def _do-grep-flist 14755
(000039A3 21 4 2 2 0)
(000039A8 3 238 1		*grep-output*)
(000039AB 5 0		UnVar0)
(000039AD 53 2 230 1 1 32		outwin.init-log)
(000039B3 10)
(000039B4 9 107 3		"VLMSG.DLL")
(000039B7 51 96 119 0 0		30560)
(000039BC 81 2 106 3 1 0		string-resource)
(000039C2 5 0		UnVar0)
(000039C4 81 1 24 3 1 0		string)
(000039CA 81 2 23 3 1 0		_win-format-message)
(000039D0 81 1 45 3 1 0		ales-prompt-msg)
(000039D6 10)
(000039D7 9 107 3		"VLMSG.DLL")
(000039DA 51 94 86 0 0		22110)
(000039DF 81 2 106 3 1 0		string-resource)
(000039E5 5 1		UnVar1)
(000039E7 81 1 229 1 1 0		length)
(000039ED 5 0		UnVar0)
(000039EF 95 3 241 56 0 0		grep-message)
(000039F5 10)
(000039F6 81 0 49 3 1 0		chdir)
(000039FC 8 3		UnVar3)
(000039FE 5 0		UnVar0)
(00003A00 81 1 49 3 1 0		chdir)
(00003A06 10)
(00003A07 15 15 0		JMP 00003A19)
(00003A0A 20 0 0 0 0)
(00003A0F 4 1 3		UpVar1-3)
(00003A12 81 1 49 3 1 0		chdir)
(00003A18 22		ret)
(00003A19 12 178 3		'(14858 -unwind-cleanup-))
(00003A1C 15 29 0		JMP 00003A3C)
(00003A1F 20 0 0 0 0)
(00003A24 3 78 2		*editor-find-what*)
(00003A27 4 1 1		UpVar1-1)
(00003A2A 3 205 2		*active-mdiwindow*)
(00003A2D 9 229 2		'l-context)
(00003A30 81 2 86 3 1 0		slot-value)
(00003A36 47 3 228 1 32 32		grep-filelist)
(00003A3C 12 177 3		'(14879 -unwind-protect-))
(00003A3F 1		nil)
(00003A40 81 3 117 3 1 0		_unwinded-apply)
(00003A46 8 2		UnVar2)
(00003A48 5 2		UnVar2)
(00003A4A 81 1 40 2 1 0		ZEROP)
(00003A50 13 30 0		nil->JMP 00003A71)
(00003A53 3 156 2		*info-alert*)
(00003A56 9 107 3		"VLMSG.DLL")
(00003A59 51 56 74 0 0		19000)
(00003A5E 81 2 106 3 1 0		string-resource)
(00003A64 3 78 2		*editor-find-what*)
(00003A67 53 3 85 3 1 32		alert)
(00003A6D 10)
(00003A6E 15 23 0		JMP 00003A88)
(00003A71 9 107 3		"VLMSG.DLL")
(00003A74 51 66 74 0 0		19010)
(00003A79 81 2 106 3 1 0		string-resource)
(00003A7F 5 2		UnVar2)
(00003A81 95 2 241 56 0 0		grep-message)
(00003A87 10)
(00003A88 1		nil)
(00003A89 81 1 45 3 1 0		ales-prompt-msg)
(00003A8F 22		ret)
;;;def !grep-choose-source-directory 14992
(00003A90 20 8 1 1 0)
(00003A95 100 1		UNVar1)
(00003A97 100 2		UNVar2)
(00003A99 100 3		UNVar3)
(00003A9B 100 4		UNVar4)
(00003A9D 5 0		UnVar0)
(00003A9F 8 5		UnVar5)
(00003AA1 5 5		UnVar5)
(00003AA3 44 11		IDFun11)
(00003AA5 8 6		UnVar6)
(00003AA7 5 5		UnVar5)
(00003AA9 5 6		UnVar6)
(00003AAB 9 227 1		':CHOOSE-FILES)
(00003AAE 53 3 61 2 1 32		_label-getf)
(00003AB4 8 7		UnVar7)
(00003AB6 5 7		UnVar7)
(00003AB8 53 1 226 1 1 32		drop-down-list-box.text)
(00003ABE 53 1 225 1 1 32		filename-pattern)
(00003AC4 8 4		UnVar4)
(00003AC6 5 4		UnVar4)
(00003AC8 61 8 0		nil->JMP 00003AD3)
(00003ACB 5 4		UnVar4)
(00003ACD 81 1 159 2 1 0		filename-extension)
(00003AD3 8 3		UnVar3)
(00003AD5 5 3		UnVar3)
(00003AD7 13 11 0		nil->JMP 00003AE5)
(00003ADA 5 4		UnVar4)
(00003ADC 81 1 172 2 1 0		filename-directory)
(00003AE2 15 2 0		JMP 00003AE7)
(00003AE5 5 4		UnVar4)
(00003AE7 8 2		UnVar2)
(00003AE9 9 107 3		"VLMSG.DLL")
(00003AEC 51 104 86 0 0		22120)
(00003AF1 81 2 106 3 1 0		string-resource)
(00003AF7 5 2		UnVar2)
(00003AF9 14 3 0		T->JMP 00003AFF)
(00003AFC 3 224 1		_%tmp-directory%)
(00003AFF 1		nil)
(00003B00 5 0		UnVar0)
(00003B02 81 4 223 1 1 0		sh-browse-for-folder)
(00003B08 8 1		UnVar1)
(00003B0A 5 1		UnVar1)
(00003B0C 13 137 0		nil->JMP 00003B98)
(00003B0F 5 3		UnVar3)
(00003B11 13 101 0		nil->JMP 00003B79)
(00003B14 5 1		UnVar1)
(00003B16 95 1 143 33 0 0		_fine-stringp)
(00003B1C 61 29 0		nil->JMP 00003B3C)
(00003B1F 5 1		UnVar1)
(00003B21 5 1		UnVar1)
(00003B23 81 1 93 2 1 0		string-length)
(00003B29 50 1		1)
(00003B2B 71		-)
(00003B2C 81 2 195 2 1 0		char)
(00003B32 9 222 1		'(92 47))
(00003B35 81 2 114 3 1 0		memq)
(00003B3B 35		not)
(00003B3C 13 13 0		nil->JMP 00003B4C)
(00003B3F 5 1		UnVar1)
(00003B41 9 221 1		"/")
(00003B44 81 2 75 3 1 0		concat)
(00003B4A 8 1		UnVar1)
(00003B4C 5 7		UnVar7)
(00003B4E 5 1		UnVar1)
(00003B50 5 4		UnVar4)
(00003B52 81 1 220 1 1 0		filename-non-directory)
(00003B58 81 2 75 3 1 0		concat)
(00003B5E 53 2 219 1 1 32		editable-text.text<-)
(00003B64 10)
(00003B65 5 7		UnVar7)
(00003B67 53 1 102 3 1 32		update-host-spouse)
(00003B6D 10)
(00003B6E 5 0		UnVar0)
(00003B70 5 7		UnVar7)
(00003B72 81 2 218 1 1 0		dialog-item-activate)
(00003B78 22		ret)
(00003B79 5 7		UnVar7)
(00003B7B 5 1		UnVar1)
(00003B7D 53 2 219 1 1 32		editable-text.text<-)
(00003B83 10)
(00003B84 5 7		UnVar7)
(00003B86 53 1 102 3 1 32		update-host-spouse)
(00003B8C 10)
(00003B8D 5 0		UnVar0)
(00003B8F 5 7		UnVar7)
(00003B91 81 2 218 1 1 0		dialog-item-activate)
(00003B97 22		ret)
(00003B98 2		T)
(00003B99 22		ret)
;;;def !editor-init-grep-files 15258
(00003B9A 20 6 1 1 0)
(00003B9F 100 1		UNVar1)
(00003BA1 100 2		UNVar2)
(00003BA3 5 0		UnVar0)
(00003BA5 8 3		UnVar3)
(00003BA7 5 3		UnVar3)
(00003BA9 44 11		IDFun11)
(00003BAB 8 4		UnVar4)
(00003BAD 5 3		UnVar3)
(00003BAF 5 4		UnVar4)
(00003BB1 9 227 1		':CHOOSE-FILES)
(00003BB4 53 3 61 2 1 32		_label-getf)
(00003BBA 8 5		UnVar5)
(00003BBC 3 205 2		*active-mdiwindow*)
(00003BBF 8 2		UnVar2)
(00003BC1 5 2		UnVar2)
(00003BC3 53 1 191 2 1 32		ed-dflt-dir?)
(00003BC9 14 6 0		T->JMP 00003BD2)
(00003BCC 81 0 49 3 1 0		chdir)
(00003BD2 8 1		UnVar1)
(00003BD4 9 217 1		"/\\")
(00003BD7 5 1		UnVar1)
(00003BD9 81 2 40 3 1 0		string-right-trim)
(00003BDF 9 216 1		"\\*.lsp")
(00003BE2 81 2 75 3 1 0		concat)
(00003BE8 6 215 1		*editor-filelist*)
(00003BEB 5 5		UnVar5)
(00003BED 47 1 70 2 32 32		sync-up)
;;;def !editor-grep-files 15347
(00003BF3 20 10 1 1 0)
(00003BF8 100 1		UNVar1)
(00003BFA 5 0		UnVar0)
(00003BFC 53 1 80 2 1 32		verified-sync-down)
(00003C02 10)
(00003C03 5 0		UnVar0)
(00003C05 8 2		UnVar2)
(00003C07 5 2		UnVar2)
(00003C09 44 11		IDFun11)
(00003C0B 8 3		UnVar3)
(00003C0D 5 2		UnVar2)
(00003C0F 5 3		UnVar3)
(00003C11 9 214 1		':FIND-WHAT)
(00003C14 53 3 61 2 1 32		_label-getf)
(00003C1A 8 4		UnVar4)
(00003C1C 5 2		UnVar2)
(00003C1E 5 3		UnVar3)
(00003C20 9 227 1		':CHOOSE-FILES)
(00003C23 53 3 61 2 1 32		_label-getf)
(00003C29 8 5		UnVar5)
(00003C2B 3 78 2		*editor-find-what*)
(00003C2E 95 1 143 33 0 0		_fine-stringp)
(00003C34 13 160 0		nil->JMP 00003CD7)
(00003C37 5 5		UnVar5)
(00003C39 53 1 226 1 1 32		drop-down-list-box.text)
(00003C3F 8 6		UnVar6)
(00003C41 100 7		UNVar7)
(00003C43 100 8		UNVar8)
(00003C45 100 9		UNVar9)
(00003C47 95 0 68 41 0 0		update-find-hist)
(00003C4D 10)
(00003C4E 5 6		UnVar6)
(00003C50 61 8 0		nil->JMP 00003C5B)
(00003C53 5 6		UnVar6)
(00003C55 81 1 159 2 1 0		filename-extension)
(00003C5B 8 8		UnVar8)
(00003C5D 5 6		UnVar6)
(00003C5F 13 21 0		nil->JMP 00003C77)
(00003C62 5 8		UnVar8)
(00003C64 13 11 0		nil->JMP 00003C72)
(00003C67 5 6		UnVar6)
(00003C69 81 1 172 2 1 0		filename-directory)
(00003C6F 15 2 0		JMP 00003C74)
(00003C72 5 6		UnVar6)
(00003C74 15 3 0		JMP 00003C7A)
(00003C77 3 224 1		_%tmp-directory%)
(00003C7A 8 7		UnVar7)
(00003C7C 5 7		UnVar7)
(00003C7E 5 8		UnVar8)
(00003C80 13 11 0		nil->JMP 00003C8E)
(00003C83 5 6		UnVar6)
(00003C85 81 1 220 1 1 0		filename-non-directory)
(00003C8B 15 3 0		JMP 00003C91)
(00003C8E 9 213 1		"*.lsp")
(00003C91 3 212 1		*grep-subdirs*)
(00003C94 53 3 211 1 1 32		directory-browse-files)
(00003C9A 8 9		UnVar9)
(00003C9C 5 9		UnVar9)
(00003C9E 13 19 0		nil->JMP 00003CB4)
(00003CA1 5 0		UnVar0)
(00003CA3 53 1 94 3 1 32		destroy-host-spouse)
(00003CA9 10)
(00003CAA 5 7		UnVar7)
(00003CAC 5 9		UnVar9)
(00003CAE 47 2 210 1 32 32		_do-grep-flist)
(00003CB4 3 156 2		*info-alert*)
(00003CB7 9 107 3		"VLMSG.DLL")
(00003CBA 51 244 76 0 0		19700)
(00003CBF 81 2 106 3 1 0		string-resource)
(00003CC5 53 2 85 3 1 32		alert)
(00003CCB 10)
(00003CCC 5 0		UnVar0)
(00003CCE 5 5		UnVar5)
(00003CD0 81 2 218 1 1 0		dialog-item-activate)
(00003CD6 22		ret)
(00003CD7 81 0 206 2 1 0		message-beep)
(00003CDD 10)
(00003CDE 1		nil)
(00003CDF 22		ret)
;;;def nil 15584
(00003CE0 20 2 2 2 0)
(00003CE5 5 1		UnVar1)
(00003CE7 5 0		UnVar0)
(00003CE9 81 1 209 1 1 0		tmark.seat)
(00003CEF 38		=)
(00003CF0 22		ret)
;;;def nil 15601
(00003CF1 20 2 1 1 0)
(00003CF6 100 1		UNVar1)
(00003CF8 9 209 1		'tmark.seat)
(00003CFB 5 0		UnVar0)
(00003CFD 81 2 6 3 1 0		delete-if-not)
(00003D03 8 0		UnVar0)
(00003D05 5 0		UnVar0)
(00003D07 8 1		UnVar1)
(00003D09 15 26 0		JMP 00003D26)
(00003D0C 5 0		UnVar0)
(00003D0E 5 0		UnVar0)
(00003D10 40		car)
(00003D11 5 0		UnVar0)
(00003D13 41		cdr)
(00003D14 81 2 208 1 1 0		delete)
(00003D1A 81 2 225 2 1 0		setcdr)
(00003D20 10)
(00003D21 5 0		UnVar0)
(00003D23 41		cdr)
(00003D24 8 0		UnVar0)
(00003D26 5 0		UnVar0)
(00003D28 60 225 255		T->JMP 00003D0C)
(00003D2B 5 1		UnVar1)
(00003D2D 22		ret)
;;;def nil 15662
(00003D2E 20 3 2 2 0)
(00003D33 100 2		UNVar2)
(00003D35 5 0		UnVar0)
(00003D37 81 1 167 2 1 0		TWin.cpos)
(00003D3D 8 2		UnVar2)
(00003D3F 5 0		UnVar0)
(00003D41 5 1		UnVar1)
(00003D43 1		nil)
(00003D44 81 3 208 2 1 0		TWin.cpos<-)
(00003D4A 10)
(00003D4B 5 1		UnVar1)
(00003D4D 5 2		UnVar2)
(00003D4F 47 2 221 2 32 32		seat<-)
;;;def !mark-ring-add 15701
(00003D55 21 5 1 2 0)
(00003D5A 100 2		UNVar2)
(00003D5C 100 3		UNVar3)
(00003D5E 100 4		UNVar4)
(00003D60 5 0		UnVar0)
(00003D62 81 1 135 3 1 0		TWinp)
(00003D68 60 5 0		T->JMP 00003D70)
(00003D6B 3 205 2		*active-mdiwindow*)
(00003D6E 8 0		UnVar0)
(00003D70 5 0		UnVar0)
(00003D72 5 1		UnVar1)
(00003D74 81 2 167 2 1 0		TWin.cpos)
(00003D7A 8 1		UnVar1)
(00003D7C 5 0		UnVar0)
(00003D7E 9 166 2		'mark-ring)
(00003D81 81 2 86 3 1 0		slot-value)
(00003D87 95 1 241 60 0 0		func 00003CF1)
(00003D8D 8 4		UnVar4)
(00003D8F 15 16 0		JMP 00003DA2)
(00003D92 20 1 1 1 0)
(00003D97 5 0		UnVar0)
(00003D99 4 1 1		UpVar1-1)
(00003D9C 96 2 224 60 0 0		func 00003CE0)
(00003DA2 12 176 3		'(15762 nil))
(00003DA5 5 4		UnVar4)
(00003DA7 81 2 207 1 1 0		member-if)
(00003DAD 8 3		UnVar3)
(00003DAF 5 3		UnVar3)
(00003DB1 13 31 0		nil->JMP 00003DD3)
(00003DB4 5 3		UnVar3)
(00003DB6 40		car)
(00003DB7 5 4		UnVar4)
(00003DB9 81 2 206 1 1 0		delq)
(00003DBF 8 4		UnVar4)
(00003DC1 5 3		UnVar3)
(00003DC3 5 4		UnVar4)
(00003DC5 81 2 225 2 1 0		setcdr)
(00003DCB 10)
(00003DCC 5 3		UnVar3)
(00003DCE 8 4		UnVar4)
(00003DD0 15 111 0		JMP 00003E42)
(00003DD3 5 4		UnVar4)
(00003DD5 81 1 229 1 1 0		length)
(00003DDB 3 205 1		*mark-ring-length*)
(00003DDE 77		>=)
(00003DDF 13 61 0		nil->JMP 00003E1F)
(00003DE2 5 4		UnVar4)
(00003DE4 50 2		2)
(00003DE6 81 2 204 1 1 0		last)
(00003DEC 8 2		UnVar2)
(00003DEE 5 2		UnVar2)
(00003DF0 41		cdr)
(00003DF1 8 3		UnVar3)
(00003DF3 5 2		UnVar2)
(00003DF5 1		nil)
(00003DF6 81 2 225 2 1 0		setcdr)
(00003DFC 10)
(00003DFD 5 3		UnVar3)
(00003DFF 5 4		UnVar4)
(00003E01 81 2 225 2 1 0		setcdr)
(00003E07 10)
(00003E08 5 3		UnVar3)
(00003E0A 8 4		UnVar4)
(00003E0C 5 3		UnVar3)
(00003E0E 40		car)
(00003E0F 8 3		UnVar3)
(00003E11 5 3		UnVar3)
(00003E13 5 1		UnVar1)
(00003E15 53 2 221 2 1 32		seat<-)
(00003E1B 10)
(00003E1C 15 35 0		JMP 00003E42)
(00003E1F 9 45 2		':OWNER)
(00003E22 5 0		UnVar0)
(00003E24 81 1 203 1 1 0		TWin.TBuf)
(00003E2A 9 44 2		':SEAT)
(00003E2D 5 1		UnVar1)
(00003E2F 9 202 1		':EXCL)
(00003E32 2		T)
(00003E33 53 6 43 2 1 32		tmark)
(00003E39 8 3		UnVar3)
(00003E3B 5 3		UnVar3)
(00003E3D 5 4		UnVar4)
(00003E3F 42		cons)
(00003E40 8 4		UnVar4)
(00003E42 5 0		UnVar0)
(00003E44 5 4		UnVar4)
(00003E46 9 166 2		'mark-ring)
(00003E49 81 3 78 3 1 0		slot-value<-)
(00003E4F 10)
(00003E50 9 107 3		"VLMSG.DLL")
(00003E53 51 244 86 0 0		22260)
(00003E58 81 2 106 3 1 0		string-resource)
(00003E5E 81 1 45 3 1 0		ales-prompt-msg)
(00003E64 22		ret)
;;;def !mark-ring-prev 15973
(00003E65 20 4 1 1 0)
(00003E6A 100 1		UNVar1)
(00003E6C 100 2		UNVar2)
(00003E6E 100 3		UNVar3)
(00003E70 5 0		UnVar0)
(00003E72 81 1 135 3 1 0		TWinp)
(00003E78 60 5 0		T->JMP 00003E80)
(00003E7B 3 205 2		*active-mdiwindow*)
(00003E7E 8 0		UnVar0)
(00003E80 5 0		UnVar0)
(00003E82 9 166 2		'mark-ring)
(00003E85 81 2 86 3 1 0		slot-value)
(00003E8B 95 1 241 60 0 0		func 00003CF1)
(00003E91 11)
(00003E92 8 3		UnVar3)
(00003E94 13 56 0		nil->JMP 00003ECF)
(00003E97 5 0		UnVar0)
(00003E99 81 1 167 2 1 0		TWin.cpos)
(00003E9F 8 2		UnVar2)
(00003EA1 5 3		UnVar3)
(00003EA3 8 1		UnVar1)
(00003EA5 5 1		UnVar1)
(00003EA7 41		cdr)
(00003EA8 8 3		UnVar3)
(00003EAA 5 1		UnVar1)
(00003EAC 1		nil)
(00003EAD 81 2 225 2 1 0		setcdr)
(00003EB3 10)
(00003EB4 5 3		UnVar3)
(00003EB6 5 1		UnVar1)
(00003EB8 81 2 174 2 1 0		nconc)
(00003EBE 8 3		UnVar3)
(00003EC0 5 0		UnVar0)
(00003EC2 5 1		UnVar1)
(00003EC4 40		car)
(00003EC5 95 2 46 61 0 0		func 00003D2E)
(00003ECB 10)
(00003ECC 15 7 0		JMP 00003ED6)
(00003ECF 81 0 206 2 1 0		message-beep)
(00003ED5 10)
(00003ED6 5 0		UnVar0)
(00003ED8 5 3		UnVar3)
(00003EDA 9 166 2		'mark-ring)
(00003EDD 81 3 78 3 1 0		slot-value<-)
(00003EE3 22		ret)
;;;def !mark-ring-next 16100
(00003EE4 20 5 1 1 0)
(00003EE9 100 1		UNVar1)
(00003EEB 100 2		UNVar2)
(00003EED 100 3		UNVar3)
(00003EEF 100 4		UNVar4)
(00003EF1 5 0		UnVar0)
(00003EF3 81 1 135 3 1 0		TWinp)
(00003EF9 60 5 0		T->JMP 00003F01)
(00003EFC 3 205 2		*active-mdiwindow*)
(00003EFF 8 0		UnVar0)
(00003F01 5 0		UnVar0)
(00003F03 9 166 2		'mark-ring)
(00003F06 81 2 86 3 1 0		slot-value)
(00003F0C 95 1 241 60 0 0		func 00003CF1)
(00003F12 11)
(00003F13 8 4		UnVar4)
(00003F15 13 61 0		nil->JMP 00003F55)
(00003F18 5 0		UnVar0)
(00003F1A 81 1 167 2 1 0		TWin.cpos)
(00003F20 8 3		UnVar3)
(00003F22 5 4		UnVar4)
(00003F24 81 1 12 3 1 0		nreverse)
(00003F2A 8 1		UnVar1)
(00003F2C 5 1		UnVar1)
(00003F2E 41		cdr)
(00003F2F 81 1 12 3 1 0		nreverse)
(00003F35 8 4		UnVar4)
(00003F37 5 1		UnVar1)
(00003F39 5 4		UnVar4)
(00003F3B 81 2 225 2 1 0		setcdr)
(00003F41 10)
(00003F42 5 1		UnVar1)
(00003F44 8 4		UnVar4)
(00003F46 5 0		UnVar0)
(00003F48 5 1		UnVar1)
(00003F4A 40		car)
(00003F4B 95 2 46 61 0 0		func 00003D2E)
(00003F51 10)
(00003F52 15 7 0		JMP 00003F5C)
(00003F55 81 0 206 2 1 0		message-beep)
(00003F5B 10)
(00003F5C 5 0		UnVar0)
(00003F5E 5 4		UnVar4)
(00003F60 9 166 2		'mark-ring)
(00003F63 81 3 78 3 1 0		slot-value<-)
(00003F69 22		ret)
;;;def !mark-ring-clear 16234
(00003F6A 20 4 1 1 0)
(00003F6F 100 1		UNVar1)
(00003F71 5 0		UnVar0)
(00003F73 81 1 135 3 1 0		TWinp)
(00003F79 60 5 0		T->JMP 00003F81)
(00003F7C 3 205 2		*active-mdiwindow*)
(00003F7F 8 0		UnVar0)
(00003F81 5 0		UnVar0)
(00003F83 9 166 2		'mark-ring)
(00003F86 81 2 86 3 1 0		slot-value)
(00003F8C 8 1		UnVar1)
(00003F8E 5 0		UnVar0)
(00003F90 1		nil)
(00003F91 9 166 2		'mark-ring)
(00003F94 81 3 78 3 1 0		slot-value<-)
(00003F9A 10)
(00003F9B 5 1		UnVar1)
(00003F9D 8 2		UnVar2)
(00003F9F 100 3		UNVar3)
(00003FA1 15 20 0		JMP 00003FB8)
(00003FA4 5 2		UnVar2)
(00003FA6 40		car)
(00003FA7 8 3		UnVar3)
(00003FA9 5 2		UnVar2)
(00003FAB 41		cdr)
(00003FAC 8 2		UnVar2)
(00003FAE 5 3		UnVar3)
(00003FB0 1		nil)
(00003FB1 81 2 201 1 1 0		tmark.owner<-)
(00003FB7 10)
(00003FB8 5 2		UnVar2)
(00003FBA 60 231 255		T->JMP 00003FA4)
(00003FBD 5 0		UnVar0)
(00003FBF 47 1 102 3 32 32		update-host-spouse)
;;;def !mark-ring-select-to-prev 16325
(00003FC5 20 2 1 1 0)
(00003FCA 100 1		UNVar1)
(00003FCC 5 0		UnVar0)
(00003FCE 81 1 135 3 1 0		TWinp)
(00003FD4 60 5 0		T->JMP 00003FDC)
(00003FD7 3 205 2		*active-mdiwindow*)
(00003FDA 8 0		UnVar0)
(00003FDC 5 0		UnVar0)
(00003FDE 9 166 2		'mark-ring)
(00003FE1 81 2 86 3 1 0		slot-value)
(00003FE7 95 1 241 60 0 0		func 00003CF1)
(00003FED 11)
(00003FEE 8 1		UnVar1)
(00003FF0 13 30 0		nil->JMP 00004011)
(00003FF3 5 0		UnVar0)
(00003FF5 5 1		UnVar1)
(00003FF7 40		car)
(00003FF8 53 1 212 2 1 32		seat)
(00003FFE 5 0		UnVar0)
(00004000 81 1 167 2 1 0		TWin.cpos)
(00004006 42		cons)
(00004007 53 2 133 2 1 32		selection<-)
(0000400D 10)
(0000400E 15 7 0		JMP 00004018)
(00004011 81 0 206 2 1 0		message-beep)
(00004017 10)
(00004018 5 0		UnVar0)
(0000401A 5 1		UnVar1)
(0000401C 9 166 2		'mark-ring)
(0000401F 81 3 78 3 1 0		slot-value<-)
(00004025 22		ret)
;;;def !mark-ring-select-to-next 16422
(00004026 20 2 1 1 0)
(0000402B 100 1		UNVar1)
(0000402D 5 0		UnVar0)
(0000402F 81 1 135 3 1 0		TWinp)
(00004035 60 5 0		T->JMP 0000403D)
(00004038 3 205 2		*active-mdiwindow*)
(0000403B 8 0		UnVar0)
(0000403D 5 0		UnVar0)
(0000403F 9 166 2		'mark-ring)
(00004042 81 2 86 3 1 0		slot-value)
(00004048 95 1 241 60 0 0		func 00003CF1)
(0000404E 11)
(0000404F 8 1		UnVar1)
(00004051 13 36 0		nil->JMP 00004078)
(00004054 5 0		UnVar0)
(00004056 5 1		UnVar1)
(00004058 81 1 204 1 1 0		last)
(0000405E 40		car)
(0000405F 53 1 212 2 1 32		seat)
(00004065 5 0		UnVar0)
(00004067 81 1 167 2 1 0		TWin.cpos)
(0000406D 42		cons)
(0000406E 53 2 133 2 1 32		selection<-)
(00004074 10)
(00004075 15 7 0		JMP 0000407F)
(00004078 81 0 206 2 1 0		message-beep)
(0000407E 10)
(0000407F 5 0		UnVar0)
(00004081 5 1		UnVar1)
(00004083 9 166 2		'mark-ring)
(00004086 81 3 78 3 1 0		slot-value<-)
(0000408C 22		ret)
;;;def !mark-ring-toggle 16525
(0000408D 20 9 1 2 0)
(00004092 100 2		UNVar2)
(00004094 100 3		UNVar3)
(00004096 100 4		UNVar4)
(00004098 100 5		UNVar5)
(0000409A 100 6		UNVar6)
(0000409C 5 0		UnVar0)
(0000409E 81 1 135 3 1 0		TWinp)
(000040A4 60 5 0		T->JMP 000040AC)
(000040A7 3 205 2		*active-mdiwindow*)
(000040AA 8 0		UnVar0)
(000040AC 5 0		UnVar0)
(000040AE 5 1		UnVar1)
(000040B0 81 2 167 2 1 0		TWin.cpos)
(000040B6 8 1		UnVar1)
(000040B8 5 0		UnVar0)
(000040BA 9 166 2		'mark-ring)
(000040BD 81 2 86 3 1 0		slot-value)
(000040C3 95 1 241 60 0 0		func 00003CF1)
(000040C9 8 6		UnVar6)
(000040CB 5 0		UnVar0)
(000040CD 5 1		UnVar1)
(000040CF 81 2 99 2 1 0		TBuf.BOL-pos)
(000040D5 8 5		UnVar5)
(000040D7 5 0		UnVar0)
(000040D9 5 1		UnVar1)
(000040DB 81 2 128 2 1 0		TBuf.EOL-pos)
(000040E1 8 4		UnVar4)
(000040E3 5 6		UnVar6)
(000040E5 8 7		UnVar7)
(000040E7 100 8		UNVar8)
(000040E9 15 49 0		JMP 0000411D)
(000040EC 5 7		UnVar7)
(000040EE 40		car)
(000040EF 8 8		UnVar8)
(000040F1 5 7		UnVar7)
(000040F3 41		cdr)
(000040F4 8 7		UnVar7)
(000040F6 5 8		UnVar8)
(000040F8 81 1 209 1 1 0		tmark.seat)
(000040FE 8 3		UnVar3)
(00004100 5 3		UnVar3)
(00004102 5 5		UnVar5)
(00004104 76		<)
(00004105 60 21 0		T->JMP 0000411D)
(00004108 5 3		UnVar3)
(0000410A 5 4		UnVar4)
(0000410C 75		>)
(0000410D 60 13 0		T->JMP 0000411D)
(00004110 5 8		UnVar8)
(00004112 1		nil)
(00004113 81 2 200 1 1 0		tmark.seat<-)
(00004119 10)
(0000411A 2		T)
(0000411B 8 2		UnVar2)
(0000411D 5 7		UnVar7)
(0000411F 60 202 255		T->JMP 000040EC)
(00004122 5 2		UnVar2)
(00004124 13 30 0		nil->JMP 00004145)
(00004127 5 0		UnVar0)
(00004129 53 1 102 3 1 32		update-host-spouse)
(0000412F 10)
(00004130 9 107 3		"VLMSG.DLL")
(00004133 51 254 86 0 0		22270)
(00004138 81 2 106 3 1 0		string-resource)
(0000413E 81 1 45 3 1 0		ales-prompt-msg)
(00004144 22		ret)
(00004145 5 0		UnVar0)
(00004147 5 1		UnVar1)
(00004149 47 2 48 2 32 32		!mark-ring-add)
;;;def !?debug-step 16719
(0000414F 20 1 0 1 0)
(00004154 3 199 1		_%sys-break-continuable-p%)
(00004157 63		nil->ret)
(00004158 3 198 1		_%sys-top-tag%)
(0000415B 63		nil->ret)
(0000415C 3 197 1		_%sdb-break-level%)
(0000415F 3 196 1		_%sys-break-level%)
(00004162 38		=)
(00004163 22		ret)
;;;def nil 16740
(00004164 20 1 1 1 0)
(00004169 95 0 79 65 0 0		!?debug-step)
(0000416F 13 12 0		nil->JMP 0000417E)
(00004172 3 198 1		_%sys-top-tag%)
(00004175 5 0		UnVar0)
(00004177 81 2 71 3 1 0		throw)
(0000417D 22		ret)
(0000417E 3 207 2		*stop-beep*)
(00004181 81 1 206 2 1 0		message-beep)
(00004187 22		ret)
;;;def sdb-step-in! 16776
(00004188 20 1 1 1 0)
(0000418D 9 195 1		':STEP-IN)
(00004190 97 1 105 65 0 0		offset 00004169)
;;;def sdb-step! 16790
(00004196 20 1 1 1 0)
(0000419B 9 194 1		':STEP)
(0000419E 97 1 105 65 0 0		offset 00004169)
;;;def help-on-help! 16819
(000041B3 20 1 0 1 0)
(000041B8 9 192 1		':HELP-ON-HELP)
(000041BB 47 1 191 1 32 32		mswin-help)
;;;def nil 16833
(000041C1 20 2 0 2 0)
(000041C6 5 0		UnVar0)
(000041C8 13 3 0		nil->JMP 000041CE)
(000041CB 15 26 0		JMP 000041E8)
(000041CE 3 190 1		*vl-help-file*)
(000041D1 8 0		UnVar0)
(000041D3 5 1		UnVar1)
(000041D5 14 14 0		T->JMP 000041E6)
(000041D8 9 107 3		"VLMSG.DLL")
(000041DB 51 114 86 0 0		22130)
(000041E0 81 2 106 3 1 0		string-resource)
(000041E6 8 1		UnVar1)
(000041E8 5 1		UnVar1)
(000041EA 13 3 0		nil->JMP 000041F0)
(000041ED 15 5 0		JMP 000041F5)
(000041F0 9 41 3		"")
(000041F3 8 1		UnVar1)
(000041F5 5 0		UnVar0)
(000041F7 37 4		stringp)
(000041F9 13 43 0		nil->JMP 00004227)
(000041FC 5 0		UnVar0)
(000041FE 81 1 100 3 1 0		file-readable-p)
(00004204 13 2 0		nil->JMP 00004209)
(00004207 2		T)
(00004208 22		ret)
(00004209 3 189 1		*warning-alert*)
(0000420C 9 107 3		"VLMSG.DLL")
(0000420F 51 124 86 0 0		22140)
(00004214 81 2 106 3 1 0		string-resource)
(0000421A 5 1		UnVar1)
(0000421C 5 0		UnVar0)
(0000421E 53 4 85 3 1 32		alert)
(00004224 10)
(00004225 1		nil)
(00004226 22		ret)
(00004227 3 189 1		*warning-alert*)
(0000422A 9 107 3		"VLMSG.DLL")
(0000422D 51 134 86 0 0		22150)
(00004232 81 2 106 3 1 0		string-resource)
(00004238 5 1		UnVar1)
(0000423A 53 3 85 3 1 32		alert)
(00004240 10)
(00004241 1		nil)
(00004242 22		ret)
;;;def help-contents! 16963
(00004243 20 2 0 2 0)
(00004248 81 0 148 2 1 0		in-ads-check)
(0000424E 61 18 0		nil->JMP 00004263)
(00004251 3 190 1		*vl-help-file*)
(00004254 37 4		stringp)
(00004256 61 9 0		nil->JMP 00004262)
(00004259 3 190 1		*vl-help-file*)
(0000425C 81 1 100 3 1 0		file-readable-p)
(00004262 35		not)
(00004263 13 7 0		nil->JMP 0000426D)
(00004266 81 0 188 1 1 0		ads-help)
(0000426C 22		ret)
(0000426D 3 190 1		*vl-help-file*)
(00004270 95 1 193 65 0 0		func 000041C1)
(00004276 63		nil->ret)
(00004277 9 187 1		':PARTIAL-KEY)
(0000427A 3 190 1		*vl-help-file*)
(0000427D 5 1		UnVar1)
(0000427F 14 3 0		T->JMP 00004285)
(00004282 9 186 1		"1VLR")
(00004285 47 3 191 1 32 32		mswin-help)
;;;def !help-tutorial 17035
(0000428B 20 1 0 1 0)
(00004290 81 0 148 2 1 0		in-ads-check)
(00004296 61 18 0		nil->JMP 000042AB)
(00004299 3 190 1		*vl-help-file*)
(0000429C 37 4		stringp)
(0000429E 61 9 0		nil->JMP 000042AA)
(000042A1 3 190 1		*vl-help-file*)
(000042A4 81 1 100 3 1 0		file-readable-p)
(000042AA 35		not)
(000042AB 13 7 0		nil->JMP 000042B5)
(000042AE 81 0 188 1 1 0		ads-help)
(000042B4 22		ret)
(000042B5 95 0 193 65 0 0		func 000041C1)
(000042BB 63		nil->ret)
(000042BC 9 185 1		':KEY)
(000042BF 3 190 1		*vl-help-file*)
(000042C2 9 107 3		"VLMSG.DLL")
(000042C5 51 144 86 0 0		22160)
(000042CA 81 2 106 3 1 0		string-resource)
(000042D0 47 3 191 1 32 32		mswin-help)
;;;def help-search! 17110
(000042D6 20 1 0 1 0)
(000042DB 81 0 148 2 1 0		in-ads-check)
(000042E1 61 18 0		nil->JMP 000042F6)
(000042E4 3 190 1		*vl-help-file*)
(000042E7 37 4		stringp)
(000042E9 61 9 0		nil->JMP 000042F5)
(000042EC 3 190 1		*vl-help-file*)
(000042EF 81 1 100 3 1 0		file-readable-p)
(000042F5 35		not)
(000042F6 13 7 0		nil->JMP 00004300)
(000042F9 81 0 188 1 1 0		ads-help)
(000042FF 22		ret)
(00004300 95 0 193 65 0 0		func 000041C1)
(00004306 63		nil->ret)
(00004307 9 187 1		':PARTIAL-KEY)
(0000430A 3 190 1		*vl-help-file*)
(0000430D 9 41 3		"")
(00004310 47 3 191 1 32 32		mswin-help)
;;;def help-lisp! 17174
(00004316 20 2 1 1 0)
(0000431B 100 1		UNVar1)
(0000431D 5 0		UnVar0)
(0000431F 81 1 135 3 1 0		TWinp)
(00004325 60 5 0		T->JMP 0000432D)
(00004328 3 205 2		*active-mdiwindow*)
(0000432B 8 0		UnVar0)
(0000432D 5 0		UnVar0)
(0000432F 50 64		64)
(00004331 53 2 198 2 1 32		twin-active-selection)
(00004337 14 28 0		T->JMP 00004356)
(0000433A 9 107 3		"VLMSG.DLL")
(0000433D 51 154 86 0 0		22170)
(00004342 81 2 106 3 1 0		string-resource)
(00004348 5 0		UnVar0)
(0000434A 53 1 24 2 1 32		twin-active-word)
(00004350 81 2 184 1 1 0		get-string-dialog)
(00004356 8 1		UnVar1)
(00004358 5 1		UnVar1)
(0000435A 37 4		stringp)
(0000435C 63		nil->ret)
(0000435D 5 1		UnVar1)
(0000435F 5 0		UnVar0)
(00004361 9 229 2		'l-context)
(00004364 81 2 86 3 1 0		slot-value)
(0000436A 96 2 112 67 0 0		lisp-help-on-key)
;;;def lisp-help-on-key 17264
(00004370 20 3 1 2 0)
(00004375 100 2		UNVar2)
(00004377 9 183 1		"\t \n\r")
(0000437A 5 0		UnVar0)
(0000437C 81 2 196 2 1 0		string-trim)
(00004382 8 0		UnVar0)
(00004384 5 1		UnVar1)
(00004386 14 9 0		T->JMP 00004392)
(00004389 3 214 2		_%curr-rep-cntx%)
(0000438C 14 3 0		T->JMP 00004392)
(0000438F 3 182 1		_%sys-rep-cntx%)
(00004392 8 1		UnVar1)
(00004394 5 0		UnVar0)
(00004396 5 1		UnVar1)
(00004398 95 2 91 68 0 0		func 0000445B)
(0000439E 62		T->ret)
(0000439F 5 0		UnVar0)
(000043A1 5 1		UnVar1)
(000043A3 95 2 146 68 0 0		func 00004492)
(000043A9 62		T->ret)
(000043AA 5 0		UnVar0)
(000043AC 5 1		UnVar1)
(000043AE 95 2 138 69 0 0		func 0000458A)
(000043B4 62		T->ret)
(000043B5 5 0		UnVar0)
(000043B7 5 1		UnVar1)
(000043B9 95 2 147 69 0 0		func 00004593)
(000043BF 62		T->ret)
(000043C0 81 0 148 2 1 0		in-ads-check)
(000043C6 61 11 0		nil->JMP 000043D4)
(000043C9 9 41 3		"")
(000043CC 5 0		UnVar0)
(000043CE 81 2 188 1 1 0		ads-help)
(000043D4 62		T->ret)
(000043D5 3 189 1		*warning-alert*)
(000043D8 9 107 3		"VLMSG.DLL")
(000043DB 51 164 86 0 0		22180)
(000043E0 81 2 106 3 1 0		string-resource)
(000043E6 5 0		UnVar0)
(000043E8 47 3 85 3 32 32		alert)
;;;def nil 17390
(000043EE 20 4 2 4 0)
(000043F3 5 0		UnVar0)
(000043F5 37 4		stringp)
(000043F7 63		nil->ret)
(000043F8 5 0		UnVar0)
(000043FA 81 1 100 3 1 0		file-readable-p)
(00004400 13 50 0		nil->JMP 00004435)
(00004403 5 2		UnVar2)
(00004405 81 1 33 2 1 0		fixnump)
(0000440B 13 17 0		nil->JMP 0000441F)
(0000440E 9 181 1		':CONTEXT)
(00004411 5 0		UnVar0)
(00004413 5 2		UnVar2)
(00004415 53 3 191 1 1 32		mswin-help)
(0000441B 10)
(0000441C 15 19 0		JMP 00004432)
(0000441F 9 187 1		':PARTIAL-KEY)
(00004422 5 0		UnVar0)
(00004424 5 2		UnVar2)
(00004426 14 2 0		T->JMP 0000442B)
(00004429 5 1		UnVar1)
(0000442B 53 3 191 1 1 32		mswin-help)
(00004431 10)
(00004432 15 36 0		JMP 00004459)
(00004435 3 189 1		*warning-alert*)
(00004438 9 107 3		"VLMSG.DLL")
(0000443B 51 174 86 0 0		22190)
(00004440 81 2 106 3 1 0		string-resource)
(00004446 5 1		UnVar1)
(00004448 5 3		UnVar3)
(0000444A 14 3 0		T->JMP 00004450)
(0000444D 9 41 3		"")
(00004450 5 0		UnVar0)
(00004452 53 5 85 3 1 32		alert)
(00004458 10)
(00004459 2		T)
(0000445A 22		ret)
;;;def nil 17499
(0000445B 20 3 2 2 0)
(00004460 100 2		UNVar2)
(00004462 5 1		UnVar1)
(00004464 5 0		UnVar0)
(00004466 53 2 180 1 1 32		rep-cntx.find-symbol)
(0000446C 11)
(0000446D 8 2		UnVar2)
(0000446F 63		nil->ret)
(00004470 5 2		UnVar2)
(00004472 9 179 1		':HELP)
(00004475 81 2 178 1 1 0		get)
(0000447B 11)
(0000447C 8 2		UnVar2)
(0000447E 63		nil->ret)
(0000447F 5 2		UnVar2)
(00004481 37 2		consp)
(00004483 63		nil->ret)
(00004484 5 2		UnVar2)
(00004486 40		car)
(00004487 5 0		UnVar0)
(00004489 5 2		UnVar2)
(0000448B 41		cdr)
(0000448C 96 3 238 67 0 0		func 000043EE)
;;;def nil 17554
(00004492 20 5 1 2 0)
(00004497 100 2		UNVar2)
(00004499 100 3		UNVar3)
(0000449B 100 4		UNVar4)
(0000449D 5 0		UnVar0)
(0000449F 9 177 1		"VLA-")
(000044A2 1		nil)
(000044A3 2		T)
(000044A4 53 4 176 1 1 32		string-has-prefix-p)
(000044AA 63		nil->ret)
(000044AB 53 0 175 1 1 32		get-ACAD-itl?)
(000044B1 11)
(000044B2 8 3		UnVar3)
(000044B4 63		nil->ret)
(000044B5 5 3		UnVar3)
(000044B7 50 1		1)
(000044B9 81 2 174 1 1 0		ITypeLib.GetDocumentation)
(000044BF 8 2		UnVar2)
(000044C1 5 3		UnVar3)
(000044C3 53 1 173 1 1 32		Release)
(000044C9 10)
(000044CA 5 2		UnVar2)
(000044CC 37 2		consp)
(000044CE 63		nil->ret)
(000044CF 5 2		UnVar2)
(000044D1 81 1 204 1 1 0		last)
(000044D7 40		car)
(000044D8 53 1 172 1 1 32		filename-base)
(000044DE 5 2		UnVar2)
(000044E0 81 1 204 1 1 0		last)
(000044E6 40		car)
(000044E7 81 1 159 2 1 0		filename-extension)
(000044ED 50 0		0)
(000044EF 50 4		4)
(000044F1 81 3 171 1 1 0		substr)
(000044F7 81 2 75 3 1 0		concat)
(000044FD 9 170 1		"ACADAUTO.CHM")
(00004500 53 2 169 1 1 32		filename-match)
(00004506 61 3 0		nil->JMP 0000450C)
(00004509 3 190 1		*vl-help-file*)
(0000450C 11)
(0000450D 8 2		UnVar2)
(0000450F 63		nil->ret)
(00004510 5 2		UnVar2)
(00004512 5 0		UnVar0)
(00004514 5 0		UnVar0)
(00004516 9 168 1		"GET-")
(00004519 50 4		4)
(0000451B 2		T)
(0000451C 53 4 176 1 1 32		string-has-prefix-p)
(00004522 14 14 0		T->JMP 00004533)
(00004525 5 0		UnVar0)
(00004527 9 167 1		"PUT-")
(0000452A 50 4		4)
(0000452C 2		T)
(0000452D 53 4 176 1 1 32		string-has-prefix-p)
(00004533 13 22 0		nil->JMP 0000454C)
(00004536 9 166 1		"vla_property_")
(00004539 5 0		UnVar0)
(0000453B 50 8		8)
(0000453D 81 2 171 1 1 0		substr)
(00004543 81 2 165 1 1 0		strcat)
(00004549 15 19 0		JMP 0000455F)
(0000454C 9 164 1		"vla_method_")
(0000454F 5 0		UnVar0)
(00004551 50 4		4)
(00004553 81 2 171 1 1 0		substr)
(00004559 81 2 165 1 1 0		strcat)
(0000455F 9 163 1		"PRODUCT")
(00004562 81 1 162 1 1 0		GETVAR)
(00004568 9 107 3		"VLMSG.DLL")
(0000456B 51 204 86 0 0		22220)
(00004570 81 2 106 3 1 0		string-resource)
(00004576 50 7		7)
(00004578 81 2 171 1 1 0		substr)
(0000457E 81 2 165 1 1 0		strcat)
(00004584 97 4 243 67 0 0		offset 000043F3)
;;;def nil 17802
(0000458A 20 3 2 2 0)
(0000458F 100 2		UNVar2)
(00004591 1		nil)
(00004592 22		ret)
;;;def nil 17811
(00004593 20 2 2 2 0)
(00004598 3 161 1		*lpp-help-file*)
(0000459B 13 15 0		nil->JMP 000045AD)
(0000459E 5 1		UnVar1)
(000045A0 53 1 228 2 1 32		object-id)
(000045A6 9 15 3		':AUTOLISP)
(000045A9 38		=)
(000045AA 15 1 0		JMP 000045AE)
(000045AD 2		T)
(000045AE 13 6 0		nil->JMP 000045B7)
(000045B1 3 190 1		*vl-help-file*)
(000045B4 15 3 0		JMP 000045BA)
(000045B7 3 161 1		*lpp-help-file*)
(000045BA 5 0		UnVar0)
(000045BC 5 0		UnVar0)
(000045BE 9 107 3		"VLMSG.DLL")
(000045C1 51 224 86 0 0		22240)
(000045C6 81 2 106 3 1 0		string-resource)
(000045CC 96 4 238 67 0 0		func 000043EE)
;;;def nil 17874
(000045D2 20 2 0 0 0)
(000045D7 100 0		UNVar0)
(000045D9 50 24		24)
(000045DB 50 95		95)
(000045DD 81 2 160 1 1 0		make-string)
(000045E3 8 0		UnVar0)
(000045E5 81 0 159 1 1 0		make-string-output-stream)
(000045EB 8 1		UnVar1)
(000045ED 9 158 1		'*standard-output*)
(000045F0 5 1		UnVar1)
(000045F2 24 2 0)
(000045F5 9 157 1		"ProductName")
(000045F8 81 1 156 1 1 0		test-ver)
(000045FE 81 1 121 3 1 0		write-line)
(00004604 10)
(00004605 3 155 1		?:Pro)
(00004608 13 6 0		nil->JMP 00004611)
(0000460B 9 154 1		"Professional")
(0000460E 15 25 0		JMP 0000462A)
(00004611 3 153 1		?:Std)
(00004614 13 6 0		nil->JMP 0000461D)
(00004617 9 152 1		"Standard")
(0000461A 15 13 0		JMP 0000462A)
(0000461D 3 151 1		?:Lite)
(00004620 13 6 0		nil->JMP 00004629)
(00004623 9 150 1		"Lite")
(00004626 15 1 0		JMP 0000462A)
(00004629 1		nil)
(0000462A 81 1 127 3 1 0		princ)
(00004630 10)
(00004631 9 149 1		" edition")
(00004634 81 1 121 3 1 0		write-line)
(0000463A 10)
(0000463B 81 0 150 2 1 0		_vill-demo-p)
(00004641 13 10 0		nil->JMP 0000464E)
(00004644 9 148 1		"(DEMO mode)")
(00004647 81 1 121 3 1 0		write-line)
(0000464D 10)
(0000464E 5 0		UnVar0)
(00004650 81 1 121 3 1 0		write-line)
(00004656 10)
(00004657 81 0 125 3 1 0		terpri)
(0000465D 10)
(0000465E 9 147 1		"Copyright © 1994-1997")
(00004661 81 1 121 3 1 0		write-line)
(00004667 10)
(00004668 9 146 1		"by")
(0000466B 81 1 121 3 1 0		write-line)
(00004671 10)
(00004672 9 145 1		"CompanyName")
(00004675 81 1 156 1 1 0		test-ver)
(0000467B 81 1 121 3 1 0		write-line)
(00004681 10)
(00004682 9 144 1		"All rights reserved")
(00004685 81 1 121 3 1 0		write-line)
(0000468B 10)
(0000468C 5 0		UnVar0)
(0000468E 81 1 121 3 1 0		write-line)
(00004694 10)
(00004695 81 0 125 3 1 0		terpri)
(0000469B 10)
(0000469C 9 143 1		"Version: ")
(0000469F 81 1 127 3 1 0		princ)
(000046A5 10)
(000046A6 9 142 1		"ProductVersion")
(000046A9 81 1 156 1 1 0		test-ver)
(000046AF 81 1 121 3 1 0		write-line)
(000046B5 10)
(000046B6 9 141 1		"(International)")
(000046B9 81 1 121 3 1 0		write-line)
(000046BF 10)
(000046C0 81 0 140 1 1 0		_vill-beta-p)
(000046C6 13 10 0		nil->JMP 000046D3)
(000046C9 9 139 1		"(Beta test)")
(000046CC 81 1 121 3 1 0		write-line)
(000046D2 10)
(000046D3 3 138 1		*VLISP-VERSION-DATE*)
(000046D6 14 15 0		T->JMP 000046E8)
(000046D9 3 137 1		*LPP-KERNEL-VERSION-DATE*)
(000046DC 14 9 0		T->JMP 000046E8)
(000046DF 3 136 1		*LPPTOP-version-date*)
(000046E2 14 3 0		T->JMP 000046E8)
(000046E5 9 41 3		"")
(000046E8 81 1 121 3 1 0		write-line)
(000046EE 10)
(000046EF 9 135 1		"Build ~a~%")
(000046F2 3 134 1		*vill-build-number*)
(000046F5 81 1 33 2 1 0		fixnump)
(000046FB 13 6 0		nil->JMP 00004704)
(000046FE 3 134 1		*vill-build-number*)
(00004701 15 3 0		JMP 00004707)
(00004704 9 133 1		"###")
(00004707 53 2 132 1 1 32		printf)
(0000470D 10)
(0000470E 81 0 140 1 1 0		_vill-beta-p)
(00004714 13 20 0		nil->JMP 0000472B)
(00004717 9 131 1		"(~a day~:p remain)~%")
(0000471A 3 130 1		*vill-expire-dab*)
(0000471D 53 0 129 1 1 32		_days-after-build)
(00004723 71		-)
(00004724 53 2 132 1 1 32		printf)
(0000472A 10)
(0000472B 81 0 140 1 1 0		_vill-beta-p)
(00004731 13 26 0		nil->JMP 0000474E)
(00004734 5 0		UnVar0)
(00004736 81 1 121 3 1 0		write-line)
(0000473C 10)
(0000473D 81 0 125 3 1 0		terpri)
(00004743 10)
(00004744 9 128 1		"Not for resale!")
(00004747 81 1 121 3 1 0		write-line)
(0000474D 10)
(0000474E 81 0 125 3 1 0		terpri)
(00004754 10)
(00004755 81 0 125 3 1 0		terpri)
(0000475B 10)
(0000475C 9 127 1		".")
(0000475F 81 1 121 3 1 0		write-line)
(00004765 10)
(00004766 25 1 0)
(00004769 5 1		UnVar1)
(0000476B 81 1 126 1 1 0		get-output-stream-string)
(00004771 22		ret)
;;;def nil 18290
(00004772 20 1 0 0 0)
(00004777 81 0 159 1 1 0		make-string-output-stream)
(0000477D 8 0		UnVar0)
(0000477F 9 158 1		'*standard-output*)
(00004782 5 0		UnVar0)
(00004784 24 2 0)
(00004787 9 125 1		". . .")
(0000478A 81 1 121 3 1 0		write-line)
(00004790 10)
(00004791 9 127 1		".")
(00004794 81 1 121 3 1 0		write-line)
(0000479A 10)
(0000479B 9 41 3		"")
(0000479E 81 1 121 3 1 0		write-line)
(000047A4 10)
(000047A5 25 1 0)
(000047A8 5 0		UnVar0)
(000047AA 81 1 126 1 1 0		get-output-stream-string)
(000047B0 22		ret)
;;;def nil 18353
(000047B1 20 7 0 1 0)
(000047B6 100 1		UNVar1)
(000047B8 100 2		UNVar2)
(000047BA 100 3		UNVar3)
(000047BC 100 4		UNVar4)
(000047BE 100 5		UNVar5)
(000047C0 100 6		UNVar6)
(000047C2 95 0 210 69 0 0		func 000045D2)
(000047C8 8 6		UnVar6)
(000047CA 50 10		10)
(000047CC 5 6		UnVar6)
(000047CE 81 2 124 1 1 0		string-count)
(000047D4 8 5		UnVar5)
(000047D6 9 123 1		"MS Sans Serif Bold")
(000047D9 50 8		8)
(000047DB 50 25		25)
(000047DD 50 8		8)
(000047DF 72		*)
(000047E0 5 5		UnVar5)
(000047E2 50 2		2)
(000047E4 71		-)
(000047E5 50 16		16)
(000047E7 72		*)
(000047E8 81 2 249 2 1 0		make-ipoint)
(000047EE 53 3 122 1 1 32		_dialog-x2d)
(000047F4 8 5		UnVar5)
(000047F6 5 6		UnVar6)
(000047F8 95 0 114 71 0 0		func 00004772)
(000047FE 81 2 165 1 1 0		strcat)
(00004804 8 6		UnVar6)
(00004806 5 5		UnVar5)
(00004808 5 6		UnVar6)
(0000480A 53 2 121 1 1 32		editable-text)
(00004810 8 4		UnVar4)
(00004812 5 4		UnVar4)
(00004814 5 4		UnVar4)
(00004816 81 1 120 1 1 0		dialog-item._msw-style)
(0000481C 3 119 1		ES_READONLY)
(0000481F 3 118 1		ES_MULTILINE)
(00004822 3 117 1		ES_AUTOVSCROLL)
(00004825 3 116 1		ES_CENTER)
(00004828 81 5 115 1 1 0		logior)
(0000482E 81 2 114 1 1 0		dialog-item._msw-style<-)
(00004834 10)
(00004835 5 0		UnVar0)
(00004837 81 1 135 3 1 0		TWinp)
(0000483D 13 44 0		nil->JMP 0000486C)
(00004840 5 4		UnVar4)
(00004842 5 0		UnVar0)
(00004844 81 1 240 2 1 0		TWin.fcolor)
(0000484A 81 2 113 1 1 0		dialog-item.fcolor<-)
(00004850 10)
(00004851 5 4		UnVar4)
(00004853 5 0		UnVar0)
(00004855 81 1 238 2 1 0		TWin.bcolor)
(0000485B 81 2 112 1 1 0		dialog-item.bcolor<-)
(00004861 10)
(00004862 5 4		UnVar4)
(00004864 2		T)
(00004865 81 2 111 1 1 0		dialog-item.color-enabled<-)
(0000486B 10)
(0000486C 5 4		UnVar4)
(0000486E 53 1 110 1 1 32		dialog-item._untabstop)
(00004874 10)
(00004875 51 30 0 12 0		786462)
(0000487A 9 107 3		"VLMSG.DLL")
(0000487D 51 84 61 0 0		15700)
(00004882 81 2 106 3 1 0		string-resource)
(00004888 9 94 3		'destroy-host-spouse)
(0000488B 53 3 109 1 1 32		push-button)
(00004891 8 3		UnVar3)
(00004893 2		T)
(00004894 9 108 1		"ALES")
(00004897 81 2 107 1 1 0		icon-resource)
(0000489D 53 1 106 1 1 32		icon)
(000048A3 8 2		UnVar2)
(000048A5 5 2		UnVar2)
(000048A7 2		T)
(000048A8 81 2 105 1 1 0		dialog-item.has-pix-size<-)
(000048AE 10)
(000048AF 5 2		UnVar2)
(000048B1 51 32 0 32 0		2097184)
(000048B6 9 254 2		'size)
(000048B9 81 3 78 3 1 0		slot-value<-)
(000048BF 10)
(000048C0 1		nil)
(000048C1 1		nil)
(000048C2 9 104 1		"About Visual LISP")
(000048C5 9 103 1		':V)
(000048C8 50 5		5)
(000048CA 9 102 1		':HD)
(000048CD 9 101 1		':HU)
(000048D0 50 11		11)
(000048D2 5 2		UnVar2)
(000048D4 50 224		-32)
(000048D6 50 27		27)
(000048D8 5 4		UnVar4)
(000048DA 57 6 0		list)
(000048DD 50 5		5)
(000048DF 5 3		UnVar3)
(000048E1 50 4		4)
(000048E3 57 5 0		list)
(000048E6 50 4		4)
(000048E8 57 4 0		list)
(000048EB 9 100 1		':FONT)
(000048EE 9 123 1		"MS Sans Serif Bold")
(000048F1 9 99 1		':PITCH)
(000048F4 50 8		8)
(000048F6 9 98 1		':DEFAULT-PUSH-BUTTON)
(000048F9 5 3		UnVar3)
(000048FB 53 10 97 1 1 32		di-fmt-dialog)
(00004901 8 1		UnVar1)
(00004903 5 1		UnVar1)
(00004905 22		ret)
;;;def about-lx! 18694
(00004906 20 2 0 1 0)
(0000490B 100 1		UNVar1)
(0000490D 5 0		UnVar0)
(0000490F 81 1 135 3 1 0		TWinp)
(00004915 13 3 0		nil->JMP 0000491B)
(00004918 15 11 0		JMP 00004926)
(0000491B 3 205 2		*active-mdiwindow*)
(0000491E 14 3 0		T->JMP 00004924)
(00004921 3 92 3		*console*)
(00004924 8 0		UnVar0)
(00004926 5 0		UnVar0)
(00004928 95 1 177 71 0 0		func 000047B1)
(0000492E 47 1 64 2 32 32		modal-dialog!!)
;;;def about! 18740
(00004934 20 1 0 1 0)
(00004939 9 96 1		"vlabout.dll")
(0000493C 9 95 1		"AboutDialog")
(0000493F 3 134 1		*vill-build-number*)
(00004942 81 1 94 1 1 0		itoa)
(00004948 81 3 93 1 1 0		_run-dll)
(0000494E 13 2 0		nil->JMP 00004953)
(00004951 1		nil)
(00004952 22		ret)
(00004953 3 92 1		*error-alert*)
(00004956 9 107 3		"VLMSG.DLL")
(00004959 51 234 86 0 0		22250)
(0000495E 81 2 106 3 1 0		string-resource)
(00004964 47 2 85 3 32 32		alert)
;;;def nil 18794
(0000496A 20 1 1 1 0)
(0000496F 5 0		UnVar0)
(00004971 81 1 101 2 1 0		TBuf.editablep)
(00004977 22		ret)
;;;def nil 18808
(00004978 20 1 1 1 0)
(0000497D 5 0		UnVar0)
(0000497F 5 0		UnVar0)
(00004981 81 1 209 2 1 0		TBuf.length)
(00004987 1		nil)
(00004988 81 3 208 2 1 0		TWin.cpos<-)
(0000498E 22		ret)
;;;def nil 18831
(0000498F 20 3 3 3 0)
(00004994 5 1		UnVar1)
(00004996 13 57 0		nil->JMP 000049D2)
(00004999 5 0		UnVar0)
(0000499B 5 1		UnVar1)
(0000499D 40		car)
(0000499E 81 2 88 2 1 0		string-equal)
(000049A4 13 3 0		nil->JMP 000049AA)
(000049A7 5 1		UnVar1)
(000049A9 22		ret)
(000049AA 5 2		UnVar2)
(000049AC 80		1-)
(000049AD 11)
(000049AE 8 2		UnVar2)
(000049B0 50 0		0)
(000049B2 81 2 113 2 1 0		=&)
(000049B8 13 10 0		nil->JMP 000049C5)
(000049BB 5 1		UnVar1)
(000049BD 1		nil)
(000049BE 81 2 225 2 1 0		setcdr)
(000049C4 22		ret)
(000049C5 5 0		UnVar0)
(000049C7 5 1		UnVar1)
(000049C9 41		cdr)
(000049CA 5 2		UnVar2)
(000049CC 97 3 148 73 0 0		offset 00004994)
(000049D2 1		nil)
(000049D3 22		ret)
;;;def history-add 18900
(000049D4 20 2 1 1 0)
(000049D9 100 1		UNVar1)
(000049DB 1		nil)
(000049DC 6 91 1		*console-history-last-tag*)
(000049DF 1		nil)
(000049E0 6 90 1		*console-history-last-shown*)
(000049E3 5 0		UnVar0)
(000049E5 13 14 0		nil->JMP 000049F6)
(000049E8 5 0		UnVar0)
(000049EA 9 41 3		"")
(000049ED 81 2 39 3 1 0		string=)
(000049F3 15 1 0		JMP 000049F7)
(000049F6 2		T)
(000049F7 13 2 0		nil->JMP 000049FC)
(000049FA 1		nil)
(000049FB 22		ret)
(000049FC 5 0		UnVar0)
(000049FE 3 89 1		*console-history*)
(00004A01 3 88 1		*history-maxlen*)
(00004A04 95 3 143 73 0 0		func 0000498F)
(00004A0A 11)
(00004A0B 8 1		UnVar1)
(00004A0D 13 15 0		nil->JMP 00004A1F)
(00004A10 5 1		UnVar1)
(00004A12 40		car)
(00004A13 3 89 1		*console-history*)
(00004A16 81 2 206 1 1 0		delq)
(00004A1C 6 89 1		*console-history*)
(00004A1F 5 0		UnVar0)
(00004A21 3 89 1		*console-history*)
(00004A24 42		cons)
(00004A25 11)
(00004A26 6 89 1		*console-history*)
(00004A29 22		ret)
;;;def nil 18986
(00004A2A 20 3 3 3 0)
(00004A2F 5 2		UnVar2)
(00004A31 13 41 0		nil->JMP 00004A5D)
(00004A34 5 1		UnVar1)
(00004A36 5 0		UnVar0)
(00004A38 5 2		UnVar2)
(00004A3A 40		car)
(00004A3B 1		nil)
(00004A3C 1		nil)
(00004A3D 2		T)
(00004A3E 81 5 87 1 1 0		string-mismatch)
(00004A44 81 2 113 2 1 0		=&)
(00004A4A 13 3 0		nil->JMP 00004A50)
(00004A4D 5 2		UnVar2)
(00004A4F 22		ret)
(00004A50 5 0		UnVar0)
(00004A52 5 1		UnVar1)
(00004A54 5 2		UnVar2)
(00004A56 41		cdr)
(00004A57 97 3 47 74 0 0		offset 00004A2F)
(00004A5D 1		nil)
(00004A5E 22		ret)
;;;def nil 19039
(00004A5F 20 5 1 2 0)
(00004A64 100 2		UNVar2)
(00004A66 100 3		UNVar3)
(00004A68 5 0		UnVar0)
(00004A6A 8 4		UnVar4)
(00004A6C 5 4		UnVar4)
(00004A6E 81 1 101 2 1 0		TBuf.editablep)
(00004A74 13 181 1		nil->JMP 00004C2C)
(00004A77 5 0		UnVar0)
(00004A79 81 1 218 2 1 0		TWin.has-selection-p)
(00004A7F 14 17 0		T->JMP 00004A93)
(00004A82 5 0		UnVar0)
(00004A84 81 1 167 2 1 0		TWin.cpos)
(00004A8A 5 0		UnVar0)
(00004A8C 81 1 209 2 1 0		TBuf.length)
(00004A92 76		<)
(00004A93 13 34 0		nil->JMP 00004AB8)
(00004A96 5 0		UnVar0)
(00004A98 9 86 1		"\t")
(00004A9B 53 2 85 1 1 32		selected-text<-)
(00004AA1 10)
(00004AA2 5 0		UnVar0)
(00004AA4 1		nil)
(00004AA5 1		nil)
(00004AA6 81 3 208 2 1 0		TWin.cpos<-)
(00004AAC 10)
(00004AAD 1		nil)
(00004AAE 6 91 1		*console-history-last-tag*)
(00004AB1 1		nil)
(00004AB2 6 90 1		*console-history-last-shown*)
(00004AB5 15 113 1		JMP 00004C29)
(00004AB8 5 0		UnVar0)
(00004ABA 2		T)
(00004ABB 81 2 84 1 1 0		terminal.input-string)
(00004AC1 14 3 0		T->JMP 00004AC7)
(00004AC4 9 41 3		"")
(00004AC7 8 3		UnVar3)
(00004AC9 3 91 1		*console-history-last-tag*)
(00004ACC 61 12 0		nil->JMP 00004ADB)
(00004ACF 5 3		UnVar3)
(00004AD1 3 90 1		*console-history-last-shown*)
(00004AD4 40		car)
(00004AD5 81 2 88 2 1 0		string-equal)
(00004ADB 13 190 0		nil->JMP 00004B9C)
(00004ADE 5 1		UnVar1)
(00004AE0 13 12 0		nil->JMP 00004AEF)
(00004AE3 3 89 1		*console-history*)
(00004AE6 81 1 12 3 1 0		nreverse)
(00004AEC 6 89 1		*console-history*)
(00004AEF 3 91 1		*console-history-last-tag*)
(00004AF2 3 91 1		*console-history-last-tag*)
(00004AF5 81 1 82 2 1 0		strlen)
(00004AFB 3 90 1		*console-history-last-shown*)
(00004AFE 41		cdr)
(00004AFF 95 3 42 74 0 0		func 00004A2A)
(00004B05 14 21 0		T->JMP 00004B1D)
(00004B08 3 91 1		*console-history-last-tag*)
(00004B0B 3 91 1		*console-history-last-tag*)
(00004B0E 81 1 82 2 1 0		strlen)
(00004B14 3 89 1		*console-history*)
(00004B17 95 3 42 74 0 0		func 00004A2A)
(00004B1D 8 2		UnVar2)
(00004B1F 5 1		UnVar1)
(00004B21 13 12 0		nil->JMP 00004B30)
(00004B24 3 89 1		*console-history*)
(00004B27 81 1 12 3 1 0		nreverse)
(00004B2D 6 89 1		*console-history*)
(00004B30 5 2		UnVar2)
(00004B32 3 90 1		*console-history-last-shown*)
(00004B35 38		=)
(00004B36 13 32 0		nil->JMP 00004B59)
(00004B39 81 0 206 2 1 0		message-beep)
(00004B3F 10)
(00004B40 5 0		UnVar0)
(00004B42 8 4		UnVar4)
(00004B44 5 4		UnVar4)
(00004B46 5 4		UnVar4)
(00004B48 81 1 209 2 1 0		TBuf.length)
(00004B4E 1		nil)
(00004B4F 81 3 208 2 1 0		TWin.cpos<-)
(00004B55 10)
(00004B56 15 64 0		JMP 00004B99)
(00004B59 5 2		UnVar2)
(00004B5B 13 20 0		nil->JMP 00004B72)
(00004B5E 5 0		UnVar0)
(00004B60 5 2		UnVar2)
(00004B62 40		car)
(00004B63 81 2 83 1 1 0		terminal.input-string<-)
(00004B69 10)
(00004B6A 5 2		UnVar2)
(00004B6C 6 90 1		*console-history-last-shown*)
(00004B6F 15 39 0		JMP 00004B99)
(00004B72 81 0 206 2 1 0		message-beep)
(00004B78 10)
(00004B79 81 0 206 2 1 0		message-beep)
(00004B7F 10)
(00004B80 81 0 206 2 1 0		message-beep)
(00004B86 10)
(00004B87 5 0		UnVar0)
(00004B89 5 0		UnVar0)
(00004B8B 81 1 82 1 1 0		terminal.input-zone)
(00004B91 1		nil)
(00004B92 81 3 208 2 1 0		TWin.cpos<-)
(00004B98 10)
(00004B99 15 141 0		JMP 00004C29)
(00004B9C 5 3		UnVar3)
(00004B9E 5 3		UnVar3)
(00004BA0 81 1 82 2 1 0		strlen)
(00004BA6 3 89 1		*console-history*)
(00004BA9 95 3 42 74 0 0		func 00004A2A)
(00004BAF 11)
(00004BB0 8 2		UnVar2)
(00004BB2 13 75 0		nil->JMP 00004C00)
(00004BB5 5 1		UnVar1)
(00004BB7 13 45 0		nil->JMP 00004BE7)
(00004BBA 3 89 1		*console-history*)
(00004BBD 81 1 12 3 1 0		nreverse)
(00004BC3 6 89 1		*console-history*)
(00004BC6 5 3		UnVar3)
(00004BC8 5 3		UnVar3)
(00004BCA 81 1 82 2 1 0		strlen)
(00004BD0 3 89 1		*console-history*)
(00004BD3 95 3 42 74 0 0		func 00004A2A)
(00004BD9 8 2		UnVar2)
(00004BDB 3 89 1		*console-history*)
(00004BDE 81 1 12 3 1 0		nreverse)
(00004BE4 6 89 1		*console-history*)
(00004BE7 5 0		UnVar0)
(00004BE9 5 2		UnVar2)
(00004BEB 40		car)
(00004BEC 81 2 83 1 1 0		terminal.input-string<-)
(00004BF2 10)
(00004BF3 5 3		UnVar3)
(00004BF5 6 91 1		*console-history-last-tag*)
(00004BF8 5 2		UnVar2)
(00004BFA 6 90 1		*console-history-last-shown*)
(00004BFD 15 41 0		JMP 00004C29)
(00004C00 81 0 206 2 1 0		message-beep)
(00004C06 10)
(00004C07 5 0		UnVar0)
(00004C09 5 0		UnVar0)
(00004C0B 81 1 82 1 1 0		terminal.input-zone)
(00004C11 5 0		UnVar0)
(00004C13 81 1 209 2 1 0		TBuf.length)
(00004C19 42		cons)
(00004C1A 53 2 133 2 1 32		selection<-)
(00004C20 10)
(00004C21 1		nil)
(00004C22 6 91 1		*console-history-last-tag*)
(00004C25 1		nil)
(00004C26 6 90 1		*console-history-last-shown*)
(00004C29 15 29 0		JMP 00004C49)
(00004C2C 81 0 206 2 1 0		message-beep)
(00004C32 10)
(00004C33 5 0		UnVar0)
(00004C35 8 4		UnVar4)
(00004C37 5 4		UnVar4)
(00004C39 5 4		UnVar4)
(00004C3B 81 1 209 2 1 0		TBuf.length)
(00004C41 1		nil)
(00004C42 81 3 208 2 1 0		TWin.cpos<-)
(00004C48 10)
(00004C49 5 0		UnVar0)
(00004C4B 1		nil)
(00004C4C 50 254		-2)
(00004C4E 81 3 95 2 1 0		TWin.set-view)
(00004C54 22		ret)
;;;def !history-up 19541
(00004C55 20 1 1 1 0)
(00004C5A 5 0		UnVar0)
(00004C5C 96 1 95 74 0 0		func 00004A5F)
;;;def !history-down 19554
(00004C62 20 1 1 1 0)
(00004C67 5 0		UnVar0)
(00004C69 2		T)
(00004C6A 96 2 95 74 0 0		func 00004A5F)
;;;def !dabbrev-expand 19568
(00004C70 20 3 1 1 0)
(00004C75 100 1		UNVar1)
(00004C77 100 2		UNVar2)
(00004C79 5 0		UnVar0)
(00004C7B 81 1 135 3 1 0		TWinp)
(00004C81 13 3 0		nil->JMP 00004C87)
(00004C84 15 8 0		JMP 00004C8F)
(00004C87 81 0 81 1 1 0		active-mdiwindow)
(00004C8D 8 0		UnVar0)
(00004C8F 5 0		UnVar0)
(00004C91 81 1 135 3 1 0		TWinp)
(00004C97 61 53 0		nil->JMP 00004CCF)
(00004C9A 5 0		UnVar0)
(00004C9C 1		nil)
(00004C9D 1		nil)
(00004C9E 81 3 208 2 1 0		TWin.cpos<-)
(00004CA4 8 2		UnVar2)
(00004CA6 5 0		UnVar0)
(00004CA8 5 2		UnVar2)
(00004CAA 53 2 109 2 1 32		word-at-pos)
(00004CB0 11)
(00004CB1 8 1		UnVar1)
(00004CB3 61 25 0		nil->JMP 00004CCF)
(00004CB6 5 1		UnVar1)
(00004CB8 41		cdr)
(00004CB9 5 2		UnVar2)
(00004CBB 81 2 113 2 1 0		=&)
(00004CC1 61 11 0		nil->JMP 00004CCF)
(00004CC4 5 0		UnVar0)
(00004CC6 5 1		UnVar1)
(00004CC8 40		car)
(00004CC9 81 2 101 2 1 0		TBuf.editablep)
(00004CCF 13 10 0		nil->JMP 00004CDC)
(00004CD2 5 0		UnVar0)
(00004CD4 5 1		UnVar1)
(00004CD6 96 2 227 76 0 0		func 00004CE3)
(00004CDC 81 0 206 2 1 0		message-beep)
(00004CE2 22		ret)
;;;def nil 19683
(00004CE3 20 5 2 2 0)
(00004CE8 100 2		UNVar2)
(00004CEA 100 3		UNVar3)
(00004CEC 100 4		UNVar4)
(00004CEE 5 1		UnVar1)
(00004CF0 41		cdr)
(00004CF1 8 4		UnVar4)
(00004CF3 3 80 1		*dax-xstr*)
(00004CF6 61 101 0		nil->JMP 00004D5E)
(00004CF9 3 79 1		*dax-tick*)
(00004CFC 5 0		UnVar0)
(00004CFE 81 1 78 1 1 0		TBuf.mod-tick)
(00004D04 81 2 113 2 1 0		=&)
(00004D0A 61 81 0		nil->JMP 00004D5E)
(00004D0D 3 77 1		*dax-xend*)
(00004D10 5 4		UnVar4)
(00004D12 38		=)
(00004D13 61 72 0		nil->JMP 00004D5E)
(00004D16 3 76 1		*dax-tbeg*)
(00004D19 5 1		UnVar1)
(00004D1B 40		car)
(00004D1C 38		=)
(00004D1D 61 62 0		nil->JMP 00004D5E)
(00004D20 3 75 1		*dax-end-mark*)
(00004D23 81 1 74 1 1 0		tmarkp)
(00004D29 61 50 0		nil->JMP 00004D5E)
(00004D2C 3 75 1		*dax-end-mark*)
(00004D2F 81 1 73 1 1 0		tmark.owner)
(00004D35 5 0		UnVar0)
(00004D37 81 1 203 1 1 0		TWin.TBuf)
(00004D3D 38		=)
(00004D3E 61 29 0		nil->JMP 00004D5E)
(00004D41 3 80 1		*dax-xstr*)
(00004D44 5 0		UnVar0)
(00004D46 3 76 1		*dax-tbeg*)
(00004D49 3 80 1		*dax-xstr*)
(00004D4C 81 1 82 2 1 0		strlen)
(00004D52 81 3 72 1 1 0		TBuf.substr)
(00004D58 81 2 88 2 1 0		string-equal)
(00004D5E 13 16 0		nil->JMP 00004D71)
(00004D61 2		T)
(00004D62 8 2		UnVar2)
(00004D64 5 0		UnVar0)
(00004D66 95 1 3 79 0 0		func 00004F03)
(00004D6C 8 3		UnVar3)
(00004D6E 15 14 0		JMP 00004D7F)
(00004D71 100 2		UNVar2)
(00004D73 5 0		UnVar0)
(00004D75 5 1		UnVar1)
(00004D77 95 2 58 78 0 0		func 00004E3A)
(00004D7D 8 3		UnVar3)
(00004D7F 1		nil)
(00004D80 81 1 45 3 1 0		ales-prompt-msg)
(00004D86 10)
(00004D87 5 3		UnVar3)
(00004D89 11)
(00004D8A 6 80 1		*dax-xstr*)
(00004D8D 13 53 0		nil->JMP 00004DC5)
(00004D90 5 0		UnVar0)
(00004D92 1		nil)
(00004D93 5 1		UnVar1)
(00004D95 40		car)
(00004D96 5 1		UnVar1)
(00004D98 41		cdr)
(00004D99 71		-)
(00004D9A 81 3 103 2 1 0		TBuf.delete)
(00004DA0 10)
(00004DA1 5 0		UnVar0)
(00004DA3 1		nil)
(00004DA4 5 3		UnVar3)
(00004DA6 81 3 80 3 1 0		TBuf.insert)
(00004DAC 10)
(00004DAD 5 0		UnVar0)
(00004DAF 81 1 167 2 1 0		TWin.cpos)
(00004DB5 6 77 1		*dax-xend*)
(00004DB8 5 0		UnVar0)
(00004DBA 81 1 78 1 1 0		TBuf.mod-tick)
(00004DC0 11)
(00004DC1 6 79 1		*dax-tick*)
(00004DC4 22		ret)
(00004DC5 81 0 206 2 1 0		message-beep)
(00004DCB 10)
(00004DCC 3 75 1		*dax-end-mark*)
(00004DCF 81 1 74 1 1 0		tmarkp)
(00004DD5 13 11 0		nil->JMP 00004DE3)
(00004DD8 3 75 1		*dax-end-mark*)
(00004DDB 1		nil)
(00004DDC 81 2 201 1 1 0		tmark.owner<-)
(00004DE2 10)
(00004DE3 5 2		UnVar2)
(00004DE5 13 39 0		nil->JMP 00004E0F)
(00004DE8 5 0		UnVar0)
(00004DEA 1		nil)
(00004DEB 5 1		UnVar1)
(00004DED 40		car)
(00004DEE 5 1		UnVar1)
(00004DF0 41		cdr)
(00004DF1 71		-)
(00004DF2 81 3 103 2 1 0		TBuf.delete)
(00004DF8 10)
(00004DF9 5 0		UnVar0)
(00004DFB 1		nil)
(00004DFC 3 71 1		*dax-tag*)
(00004DFF 81 3 80 3 1 0		TBuf.insert)
(00004E05 10)
(00004E06 1		nil)
(00004E07 6 71 1		*dax-tag*)
(00004E0A 50 0		0)
(00004E0C 6 79 1		*dax-tick*)
(00004E0F 5 2		UnVar2)
(00004E11 13 17 0		nil->JMP 00004E25)
(00004E14 9 107 3		"VLMSG.DLL")
(00004E17 51 238 82 0 0		21230)
(00004E1C 81 2 106 3 1 0		string-resource)
(00004E22 15 14 0		JMP 00004E33)
(00004E25 9 107 3		"VLMSG.DLL")
(00004E28 51 248 82 0 0		21240)
(00004E2D 81 2 106 3 1 0		string-resource)
(00004E33 81 1 45 3 1 0		ales-prompt-msg)
(00004E39 22		ret)
;;;def nil 20026
(00004E3A 20 4 2 2 0)
(00004E3F 100 2		UNVar2)
(00004E41 100 3		UNVar3)
(00004E43 5 1		UnVar1)
(00004E45 40		car)
(00004E46 6 76 1		*dax-tbeg*)
(00004E49 5 1		UnVar1)
(00004E4B 41		cdr)
(00004E4C 6 77 1		*dax-xend*)
(00004E4F 5 0		UnVar0)
(00004E51 3 76 1		*dax-tbeg*)
(00004E54 3 77 1		*dax-xend*)
(00004E57 81 3 96 2 1 0		TBuf.subseq)
(00004E5D 6 71 1		*dax-tag*)
(00004E60 9 107 3		"VLMSG.DLL")
(00004E63 51 126 119 0 0		30590)
(00004E68 81 2 106 3 1 0		string-resource)
(00004E6E 3 71 1		*dax-tag*)
(00004E71 81 1 24 3 1 0		string)
(00004E77 81 2 23 3 1 0		_win-format-message)
(00004E7D 6 70 1		*dax-prompt*)
(00004E80 3 71 1		*dax-tag*)
(00004E83 57 1 0		list)
(00004E86 6 69 1		*dax-xtbl*)
(00004E89 5 0		UnVar0)
(00004E8B 3 76 1		*dax-tbeg*)
(00004E8E 81 2 126 2 1 0		TBuf.prev-pos)
(00004E94 6 68 1		*dax-beg-pos*)
(00004E97 2		T)
(00004E98 6 67 1		*dax-back*)
(00004E9B 3 75 1		*dax-end-mark*)
(00004E9E 81 1 74 1 1 0		tmarkp)
(00004EA4 13 44 0		nil->JMP 00004ED3)
(00004EA7 3 75 1		*dax-end-mark*)
(00004EAA 5 0		UnVar0)
(00004EAC 81 1 203 1 1 0		TWin.TBuf)
(00004EB2 81 2 201 1 1 0		tmark.owner<-)
(00004EB8 10)
(00004EB9 3 75 1		*dax-end-mark*)
(00004EBC 3 76 1		*dax-tbeg*)
(00004EBF 3 71 1		*dax-tag*)
(00004EC2 81 1 82 2 1 0		strlen)
(00004EC8 70		+)
(00004EC9 53 2 221 2 1 32		seat<-)
(00004ECF 10)
(00004ED0 15 40 0		JMP 00004EFB)
(00004ED3 9 45 2		':OWNER)
(00004ED6 5 0		UnVar0)
(00004ED8 53 1 66 1 1 32		arg->tbuf)
(00004EDE 9 44 2		':SEAT)
(00004EE1 3 76 1		*dax-tbeg*)
(00004EE4 3 71 1		*dax-tag*)
(00004EE7 81 1 82 2 1 0		strlen)
(00004EED 70		+)
(00004EEE 9 202 1		':EXCL)
(00004EF1 2		T)
(00004EF2 53 6 43 2 1 32		tmark)
(00004EF8 6 75 1		*dax-end-mark*)
(00004EFB 5 0		UnVar0)
(00004EFD 96 1 3 79 0 0		func 00004F03)
;;;def nil 20227
(00004F03 20 7 1 1 0)
(00004F08 100 1		UNVar1)
(00004F0A 100 2		UNVar2)
(00004F0C 100 3		UNVar3)
(00004F0E 3 70 1		*dax-prompt*)
(00004F11 81 1 45 3 1 0		ales-prompt-msg)
(00004F17 10)
(00004F18 3 67 1		*dax-back*)
(00004F1B 13 48 0		nil->JMP 00004F4E)
(00004F1E 5 0		UnVar0)
(00004F20 3 71 1		*dax-tag*)
(00004F23 3 65 1		*dax-nocase*)
(00004F26 3 68 1		*dax-beg-pos*)
(00004F29 95 4 135 80 0 0		func 00005087)
(00004F2F 14 25 0		T->JMP 00004F4B)
(00004F32 1		nil)
(00004F33 11)
(00004F34 6 67 1		*dax-back*)
(00004F37 14 17 0		T->JMP 00004F4B)
(00004F3A 5 0		UnVar0)
(00004F3C 3 71 1		*dax-tag*)
(00004F3F 3 65 1		*dax-nocase*)
(00004F42 3 75 1		*dax-end-mark*)
(00004F45 95 4 13 80 0 0		func 0000500D)
(00004F4B 15 17 0		JMP 00004F5F)
(00004F4E 5 0		UnVar0)
(00004F50 3 71 1		*dax-tag*)
(00004F53 3 65 1		*dax-nocase*)
(00004F56 3 75 1		*dax-end-mark*)
(00004F59 95 4 13 80 0 0		func 0000500D)
(00004F5F 8 3		UnVar3)
(00004F61 5 3		UnVar3)
(00004F63 63		nil->ret)
(00004F64 5 0		UnVar0)
(00004F66 5 3		UnVar3)
(00004F68 53 2 109 2 1 32		word-at-pos)
(00004F6E 8 2		UnVar2)
(00004F70 5 0		UnVar0)
(00004F72 5 3		UnVar3)
(00004F74 5 2		UnVar2)
(00004F76 41		cdr)
(00004F77 5 2		UnVar2)
(00004F79 40		car)
(00004F7A 71		-)
(00004F7B 81 3 72 1 1 0		TBuf.substr)
(00004F81 8 1		UnVar1)
(00004F83 3 67 1		*dax-back*)
(00004F86 13 27 0		nil->JMP 00004FA4)
(00004F89 5 0		UnVar0)
(00004F8B 5 2		UnVar2)
(00004F8D 40		car)
(00004F8E 3 71 1		*dax-tag*)
(00004F91 81 1 82 2 1 0		strlen)
(00004F97 70		+)
(00004F98 81 2 126 2 1 0		TBuf.prev-pos)
(00004F9E 6 68 1		*dax-beg-pos*)
(00004FA1 15 21 0		JMP 00004FB9)
(00004FA4 3 75 1		*dax-end-mark*)
(00004FA7 5 0		UnVar0)
(00004FA9 5 2		UnVar2)
(00004FAB 40		car)
(00004FAC 81 2 121 2 1 0		TBuf.next-pos)
(00004FB2 53 2 221 2 1 32		seat<-)
(00004FB8 10)
(00004FB9 5 1		UnVar1)
(00004FBB 53 1 64 1 1 32		circle-list)
(00004FC1 8 4		UnVar4)
(00004FC3 3 69 1		*dax-xtbl*)
(00004FC6 8 5		UnVar5)
(00004FC8 100 6		UNVar6)
(00004FCA 15 10 0		JMP 00004FD7)
(00004FCD 5 4		UnVar4)
(00004FCF 41		cdr)
(00004FD0 8 4		UnVar4)
(00004FD2 5 5		UnVar5)
(00004FD4 41		cdr)
(00004FD5 8 5		UnVar5)
(00004FD7 5 4		UnVar4)
(00004FD9 61 21 0		nil->JMP 00004FF1)
(00004FDC 5 5		UnVar5)
(00004FDE 61 16 0		nil->JMP 00004FF1)
(00004FE1 5 4		UnVar4)
(00004FE3 40		car)
(00004FE4 5 5		UnVar5)
(00004FE6 40		car)
(00004FE7 81 2 88 2 1 0		string-equal)
(00004FED 11)
(00004FEE 8 6		UnVar6)
(00004FF0 35		not)
(00004FF1 60 217 255		T->JMP 00004FCD)
(00004FF4 5 6		UnVar6)
(00004FF6 13 8 0		nil->JMP 00005001)
(00004FF9 5 0		UnVar0)
(00004FFB 97 1 8 79 0 0		offset 00004F08)
(00005001 5 1		UnVar1)
(00005003 3 69 1		*dax-xtbl*)
(00005006 42		cons)
(00005007 6 69 1		*dax-xtbl*)
(0000500A 5 1		UnVar1)
(0000500C 22		ret)
;;;def nil 20493
(0000500D 20 8 2 5 0)
(00005012 100 5		UNVar5)
(00005014 100 6		UNVar6)
(00005016 100 7		UNVar7)
(00005018 5 0		UnVar0)
(0000501A 9 229 2		'l-context)
(0000501D 81 2 86 3 1 0		slot-value)
(00005023 53 1 105 2 1 32		cntx-wsep)
(00005029 8 7		UnVar7)
(0000502B 5 0		UnVar0)
(0000502D 5 1		UnVar1)
(0000502F 5 2		UnVar2)
(00005031 5 3		UnVar3)
(00005033 5 4		UnVar4)
(00005035 81 5 84 2 1 0		TBuf.search-forward)
(0000503B 11)
(0000503C 8 6		UnVar6)
(0000503E 63		nil->ret)
(0000503F 5 0		UnVar0)
(00005041 5 7		UnVar7)
(00005043 2		T)
(00005044 5 6		UnVar6)
(00005046 81 4 117 2 1 0		TBuf.scan-chars-backward)
(0000504C 8 5		UnVar5)
(0000504E 5 5		UnVar5)
(00005050 13 13 0		nil->JMP 00005060)
(00005053 5 0		UnVar0)
(00005055 5 5		UnVar5)
(00005057 81 2 121 2 1 0		TBuf.next-pos)
(0000505D 15 2 0		JMP 00005062)
(00005060 50 0		0)
(00005062 8 5		UnVar5)
(00005064 5 5		UnVar5)
(00005066 5 6		UnVar6)
(00005068 38		=)
(00005069 13 3 0		nil->JMP 0000506F)
(0000506C 5 6		UnVar6)
(0000506E 22		ret)
(0000506F 5 0		UnVar0)
(00005071 5 1		UnVar1)
(00005073 5 2		UnVar2)
(00005075 5 0		UnVar0)
(00005077 5 6		UnVar6)
(00005079 81 2 121 2 1 0		TBuf.next-pos)
(0000507F 5 4		UnVar4)
(00005081 97 5 18 80 0 0		offset 00005012)
;;;def nil 20615
(00005087 20 8 2 5 0)
(0000508C 100 5		UNVar5)
(0000508E 100 6		UNVar6)
(00005090 100 7		UNVar7)
(00005092 5 0		UnVar0)
(00005094 9 229 2		'l-context)
(00005097 81 2 86 3 1 0		slot-value)
(0000509D 53 1 105 2 1 32		cntx-wsep)
(000050A3 8 7		UnVar7)
(000050A5 5 0		UnVar0)
(000050A7 5 1		UnVar1)
(000050A9 5 2		UnVar2)
(000050AB 5 3		UnVar3)
(000050AD 5 4		UnVar4)
(000050AF 81 5 83 2 1 0		TBuf.search-backward)
(000050B5 11)
(000050B6 8 6		UnVar6)
(000050B8 63		nil->ret)
(000050B9 5 0		UnVar0)
(000050BB 5 7		UnVar7)
(000050BD 2		T)
(000050BE 5 6		UnVar6)
(000050C0 81 4 117 2 1 0		TBuf.scan-chars-backward)
(000050C6 8 5		UnVar5)
(000050C8 5 5		UnVar5)
(000050CA 13 13 0		nil->JMP 000050DA)
(000050CD 5 0		UnVar0)
(000050CF 5 5		UnVar5)
(000050D1 81 2 121 2 1 0		TBuf.next-pos)
(000050D7 15 2 0		JMP 000050DC)
(000050DA 50 0		0)
(000050DC 8 5		UnVar5)
(000050DE 5 5		UnVar5)
(000050E0 5 6		UnVar6)
(000050E2 38		=)
(000050E3 13 3 0		nil->JMP 000050E9)
(000050E6 5 6		UnVar6)
(000050E8 22		ret)
(000050E9 5 0		UnVar0)
(000050EB 5 1		UnVar1)
(000050ED 5 2		UnVar2)
(000050EF 5 0		UnVar0)
(000050F1 5 6		UnVar6)
(000050F3 5 1		UnVar1)
(000050F5 81 1 82 2 1 0		strlen)
(000050FB 70		+)
(000050FC 81 2 126 2 1 0		TBuf.prev-pos)
(00005102 5 4		UnVar4)
(00005104 97 5 140 80 0 0		offset 0000508C)
;;;def !?al-check 20746
(0000510A 20 2 1 2 0)
(0000510F 5 0		UnVar0)
(00005111 53 1 91 3 1 32		editorp)
(00005117 63		nil->ret)
(00005118 9 15 3		':AUTOLISP)
(0000511B 5 0		UnVar0)
(0000511D 44 10		IDFun10)
(0000511F 14 3 0		T->JMP 00005125)
(00005122 3 214 2		_%curr-rep-cntx%)
(00005125 53 1 228 2 1 32		object-id)
(0000512B 38		=)
(0000512C 63		nil->ret)
(0000512D 5 1		UnVar1)
(0000512F 13 9 0		nil->JMP 0000513B)
(00005132 5 0		UnVar0)
(00005134 81 1 218 2 1 0		TWin.has-selection-p)
(0000513A 22		ret)
(0000513B 2		T)
(0000513C 22		ret)
;;;def nil 20797
(0000513D 20 1 1 1 0)
(00005142 5 0		UnVar0)
(00005144 95 1 10 81 0 0		!?al-check)
(0000514A 13 2 0		nil->JMP 0000514F)
(0000514D 1		nil)
(0000514E 22		ret)
(0000514F 3 22 3		*stop-alert*)
(00005152 9 63 1		"checker supported only\nin AutoLISP editor")
(00005155 47 2 85 3 32 32		alert)
;;;def al-check-ed 20827
(0000515B 21 2 1 2 0)
(00005160 5 0		UnVar0)
(00005162 95 1 61 81 0 0		func 0000513D)
(00005168 10)
(00005169 3 62 1		*build-window*)
(0000516C 5 0		UnVar0)
(0000516E 53 1 191 2 1 32		ed-dflt-dir?)
(00005174 53 2 230 1 1 32		outwin.init-log)
(0000517A 10)
(0000517B 5 0		UnVar0)
(0000517D 15 97 0		JMP 000051E1)
(00005180 20 2 2 2 0)
(00005185 9 61 1		'*analyse-output*)
(00005188 3 62 1		*build-window*)
(0000518B 9 237 1		'ostm)
(0000518E 81 2 86 3 1 0		slot-value)
(00005194 24 2 0)
(00005197 3 61 1		*analyse-output*)
(0000519A 9 107 3		"VLMSG.DLL")
(0000519D 51 88 82 0 0		21080)
(000051A2 81 2 106 3 1 0		string-resource)
(000051A8 4 1 0		UpVar1-0)
(000051AB 9 87 3		'caption)
(000051AE 81 2 86 3 1 0		slot-value)
(000051B4 4 1 1		UpVar1-1)
(000051B7 13 17 0		nil->JMP 000051CB)
(000051BA 9 107 3		"VLMSG.DLL")
(000051BD 51 98 82 0 0		21090)
(000051C2 81 2 106 3 1 0		string-resource)
(000051C8 15 3 0		JMP 000051CE)
(000051CB 9 41 3		"")
(000051CE 53 4 97 3 1 32		prinf)
(000051D4 10)
(000051D5 5 0		UnVar0)
(000051D7 53 1 60 1 1 32		check-pdb-stream)
(000051DD 25 1 0)
(000051E0 22		ret)
(000051E1 12 175 3		'(20864 nil))
(000051E4 3 5 2		_%al-rep-cntx%)
(000051E7 5 1		UnVar1)
(000051E9 13 4 0		nil->JMP 000051F0)
(000051EC 1		nil)
(000051ED 15 11 0		JMP 000051FB)
(000051F0 50 0		0)
(000051F2 5 0		UnVar0)
(000051F4 81 1 209 2 1 0		TBuf.length)
(000051FA 42		cons)
(000051FB 1		nil)
(000051FC 47 5 201 2 32 32		process-selection-istream)
;;;def !al-check-selection 20994
(00005202 20 1 1 1 0)
(00005207 5 0		UnVar0)
(00005209 53 1 91 3 1 32		editorp)
(0000520F 60 5 0		T->JMP 00005217)
(00005212 3 205 2		*active-mdiwindow*)
(00005215 8 0		UnVar0)
(00005217 5 0		UnVar0)
(00005219 2		T)
(0000521A 47 2 59 1 32 32		al-check-ed)
;;;def !al-check-buffer 21024
(00005220 20 1 1 1 0)
(00005225 5 0		UnVar0)
(00005227 53 1 91 3 1 32		editorp)
(0000522D 60 5 0		T->JMP 00005235)
(00005230 3 205 2		*active-mdiwindow*)
(00005233 8 0		UnVar0)
(00005235 5 0		UnVar0)
(00005237 47 1 59 1 32 32		al-check-ed)
;;;def !al-check-file 21053
(0000523D 21 5 1 1 0)
(00005242 100 1		UNVar1)
(00005244 100 2		UNVar2)
(00005246 5 0		UnVar0)
(00005248 81 1 135 3 1 0		TWinp)
(0000524E 60 5 0		T->JMP 00005256)
(00005251 3 205 2		*active-mdiwindow*)
(00005254 8 0		UnVar0)
(00005256 5 0		UnVar0)
(00005258 9 107 3		"VLMSG.DLL")
(0000525B 51 108 82 0 0		21100)
(00005260 81 2 106 3 1 0		string-resource)
(00005266 2		T)
(00005267 95 3 50 18 0 0		get-filename-to-load)
(0000526D 11)
(0000526E 8 2		UnVar2)
(00005270 63		nil->ret)
(00005271 3 62 1		*build-window*)
(00005274 5 2		UnVar2)
(00005276 81 1 172 2 1 0		filename-directory)
(0000527C 53 2 230 1 1 32		outwin.init-log)
(00005282 10)
(00005283 5 2		UnVar2)
(00005285 9 44 3		':INPUT)
(00005288 81 2 64 3 1 0		open)
(0000528E 8 3		UnVar3)
(00005290 5 3		UnVar3)
(00005292 8 4		UnVar4)
(00005294 15 35 0		JMP 000052BA)
(00005297 20 0 0 0 0)
(0000529C 4 1 3		UpVar1-3)
(0000529F 81 1 63 3 1 0		streamp)
(000052A5 63		nil->ret)
(000052A6 4 1 3		UpVar1-3)
(000052A9 81 1 62 3 1 0		open-streamp)
(000052AF 63		nil->ret)
(000052B0 4 1 3		UpVar1-3)
(000052B3 81 1 61 3 1 0		close)
(000052B9 22		ret)
(000052BA 12 174 3		'(21143 -unwind-cleanup-))
(000052BD 15 63 0		JMP 000052FF)
(000052C0 20 0 0 0 0)
(000052C5 9 61 1		'*analyse-output*)
(000052C8 3 62 1		*build-window*)
(000052CB 9 237 1		'ostm)
(000052CE 81 2 86 3 1 0		slot-value)
(000052D4 24 2 0)
(000052D7 3 61 1		*analyse-output*)
(000052DA 9 107 3		"VLMSG.DLL")
(000052DD 51 28 82 0 0		21020)
(000052E2 81 2 106 3 1 0		string-resource)
(000052E8 4 1 2		UpVar1-2)
(000052EB 53 3 97 3 1 32		prinf)
(000052F1 10)
(000052F2 4 1 4		UpVar1-4)
(000052F5 53 1 60 1 1 32		check-pdb-stream)
(000052FB 25 1 0)
(000052FE 22		ret)
(000052FF 12 173 3		'(21184 -unwind-protect-))
(00005302 1		nil)
(00005303 81 3 117 3 1 0		_unwinded-apply)
(00005309 22		ret)
;;;def mdiwins->list 21258
(0000530A 20 9 0 0 0)
(0000530F 100 0		UNVar0)
(00005311 100 1		UNVar1)
(00005313 100 2		UNVar2)
(00005315 100 3		UNVar3)
(00005317 100 4		UNVar4)
(00005319 100 5		UNVar5)
(0000531B 81 0 93 3 1 0		list-mdiwindows-with-host-spouse)
(00005321 8 6		UnVar6)
(00005323 100 7		UNVar7)
(00005325 15 100 0		JMP 0000538C)
(00005328 5 6		UnVar6)
(0000532A 40		car)
(0000532B 8 7		UnVar7)
(0000532D 5 6		UnVar6)
(0000532F 41		cdr)
(00005330 8 6		UnVar6)
(00005332 5 7		UnVar7)
(00005334 81 1 126 3 1 0		type-of)
(0000533A 8 8		UnVar8)
(0000533C 5 8		UnVar8)
(0000533E 9 58 1		'console)
(00005341 53 2 57 1 1 32		subtypep)
(00005347 13 10 0		nil->JMP 00005354)
(0000534A 5 7		UnVar7)
(0000534C 5 4		UnVar4)
(0000534E 42		cons)
(0000534F 8 4		UnVar4)
(00005351 15 56 0		JMP 0000538C)
(00005354 5 8		UnVar8)
(00005356 9 116 3		'editor)
(00005359 53 2 57 1 1 32		subtypep)
(0000535F 13 35 0		nil->JMP 00005385)
(00005362 5 7		UnVar7)
(00005364 81 1 126 3 1 0		type-of)
(0000536A 9 116 3		'editor)
(0000536D 38		=)
(0000536E 13 10 0		nil->JMP 0000537B)
(00005371 5 7		UnVar7)
(00005373 5 2		UnVar2)
(00005375 42		cons)
(00005376 8 2		UnVar2)
(00005378 15 7 0		JMP 00005382)
(0000537B 5 7		UnVar7)
(0000537D 5 1		UnVar1)
(0000537F 42		cons)
(00005380 8 1		UnVar1)
(00005382 15 7 0		JMP 0000538C)
(00005385 5 7		UnVar7)
(00005387 5 3		UnVar3)
(00005389 42		cons)
(0000538A 8 3		UnVar3)
(0000538C 5 6		UnVar6)
(0000538E 60 151 255		T->JMP 00005328)
(00005391 3 92 3		*console*)
(00005394 3 92 3		*console*)
(00005397 5 4		UnVar4)
(00005399 81 2 206 1 1 0		delq)
(0000539F 9 56 1		'_addr<)
(000053A2 81 2 248 1 1 0		sort)
(000053A8 42		cons)
(000053A9 8 4		UnVar4)
(000053AB 5 3		UnVar3)
(000053AD 9 56 1		'_addr<)
(000053B0 81 2 248 1 1 0		sort)
(000053B6 8 3		UnVar3)
(000053B8 5 2		UnVar2)
(000053BA 15 65 0		JMP 000053FE)
(000053BD 20 3 2 2 0)
(000053C2 100 2		UNVar2)
(000053C4 5 0		UnVar0)
(000053C6 44 15		IDFun15)
(000053C8 11)
(000053C9 8 2		UnVar2)
(000053CB 13 24 0		nil->JMP 000053E6)
(000053CE 5 1		UnVar1)
(000053D0 44 15		IDFun15)
(000053D2 8 1		UnVar1)
(000053D4 5 1		UnVar1)
(000053D6 13 11 0		nil->JMP 000053E4)
(000053D9 5 2		UnVar2)
(000053DB 5 1		UnVar1)
(000053DD 81 2 249 1 1 0		string<)
(000053E3 22		ret)
(000053E4 2		T)
(000053E5 22		ret)
(000053E6 5 1		UnVar1)
(000053E8 44 15		IDFun15)
(000053EA 13 2 0		nil->JMP 000053EF)
(000053ED 1		nil)
(000053EE 22		ret)
(000053EF 5 0		UnVar0)
(000053F1 44 0		IDFun0)
(000053F3 5 1		UnVar1)
(000053F5 44 0		IDFun0)
(000053F7 81 2 249 1 1 0		string<)
(000053FD 22		ret)
(000053FE 9 172 3		'(21437 nil))
(00005401 81 2 248 1 1 0		sort)
(00005407 8 2		UnVar2)
(00005409 5 1		UnVar1)
(0000540B 15 34 0		JMP 00005430)
(0000540E 20 2 2 2 0)
(00005413 5 0		UnVar0)
(00005415 9 87 3		'caption)
(00005418 81 2 86 3 1 0		slot-value)
(0000541E 5 1		UnVar1)
(00005420 9 87 3		'caption)
(00005423 81 2 86 3 1 0		slot-value)
(00005429 81 2 249 1 1 0		string<)
(0000542F 22		ret)
(00005430 9 171 3		'(21518 nil))
(00005433 81 2 248 1 1 0		sort)
(00005439 8 1		UnVar1)
(0000543B 5 4		UnVar4)
(0000543D 3 55 1		*trace-terminal*)
(00005440 57 1 0		list)
(00005443 5 2		UnVar2)
(00005445 5 1		UnVar1)
(00005447 3 55 1		*trace-terminal*)
(0000544A 5 3		UnVar3)
(0000544C 81 2 206 1 1 0		delq)
(00005452 81 5 174 2 1 0		nconc)
(00005458 22		ret)
;;;def nil 21593
(00005459 20 3 2 2 0)
(0000545E 100 2		UNVar2)
(00005460 5 1		UnVar1)
(00005462 80		1-)
(00005463 95 0 10 83 0 0		mdiwins->list)
(00005469 81 2 179 2 1 0		nth)
(0000546F 8 2		UnVar2)
(00005471 5 2		UnVar2)
(00005473 9 54 1		'mdiwindow)
(00005476 53 2 53 1 1 32		typep)
(0000547C 63		nil->ret)
(0000547D 5 2		UnVar2)
(0000547F 47 1 89 3 32 32		mdiwindow-show-up)
;;;def window-1! 21637
(00005485 20 1 1 1 0)
(0000548A 5 0		UnVar0)
(0000548C 50 1		1)
(0000548E 96 2 89 84 0 0		func 00005459)
;;;def window-2! 21652
(00005494 20 1 1 1 0)
(00005499 5 0		UnVar0)
(0000549B 50 2		2)
(0000549D 96 2 89 84 0 0		func 00005459)
;;;def window-3! 21667
(000054A3 20 1 1 1 0)
(000054A8 5 0		UnVar0)
(000054AA 50 3		3)
(000054AC 96 2 89 84 0 0		func 00005459)
;;;def window-4! 21682
(000054B2 20 1 1 1 0)
(000054B7 5 0		UnVar0)
(000054B9 50 4		4)
(000054BB 96 2 89 84 0 0		func 00005459)
;;;def window-5! 21697
(000054C1 20 1 1 1 0)
(000054C6 5 0		UnVar0)
(000054C8 50 5		5)
(000054CA 96 2 89 84 0 0		func 00005459)
;;;def window-6! 21712
(000054D0 20 1 1 1 0)
(000054D5 5 0		UnVar0)
(000054D7 50 6		6)
(000054D9 96 2 89 84 0 0		func 00005459)
;;;def window-7! 21727
(000054DF 20 1 1 1 0)
(000054E4 5 0		UnVar0)
(000054E6 50 7		7)
(000054E8 96 2 89 84 0 0		func 00005459)
;;;def window-8! 21742
(000054EE 20 1 1 1 0)
(000054F3 5 0		UnVar0)
(000054F5 50 8		8)
(000054F7 96 2 89 84 0 0		func 00005459)
;;;def window-9! 21757
(000054FD 20 1 1 1 0)
(00005502 5 0		UnVar0)
(00005504 50 9		9)
(00005506 96 2 89 84 0 0		func 00005459)
;;;def make-mm-cmd 21772
(0000550C 21 1 1 1 0)
(00005511 15 14 0		JMP 00005522)
(00005514 20 1 1 1 0)
(00005519 4 1 0		UpVar1-0)
(0000551C 47 1 89 3 32 32		mdiwindow-show-up)
(00005522 12 170 3		'(21780 nil))
(00005525 22		ret)
;;;def nil 21798
(00005526 20 6 0 0 0)
(0000552B 100 0		UNVar0)
(0000552D 50 1		1)
(0000552F 8 1		UnVar1)
(00005531 3 205 2		*active-mdiwindow*)
(00005534 8 2		UnVar2)
(00005536 95 0 10 83 0 0		mdiwins->list)
(0000553C 8 3		UnVar3)
(0000553E 100 4		UNVar4)
(00005540 15 133 0		JMP 000055C8)
(00005543 5 3		UnVar3)
(00005545 40		car)
(00005546 8 4		UnVar4)
(00005548 5 3		UnVar3)
(0000554A 41		cdr)
(0000554B 8 3		UnVar3)
(0000554D 1		nil)
(0000554E 9 52 1		"~a~a ~a~a")
(00005551 5 1		UnVar1)
(00005553 50 10		10)
(00005555 76		<)
(00005556 13 6 0		nil->JMP 0000555F)
(00005559 9 51 1		"&")
(0000555C 15 3 0		JMP 00005562)
(0000555F 9 41 3		"")
(00005562 5 1		UnVar1)
(00005564 5 4		UnVar4)
(00005566 9 87 3		'caption)
(00005569 81 2 86 3 1 0		slot-value)
(0000556F 5 4		UnVar4)
(00005571 53 1 90 3 1 32		needs-save-p)
(00005577 13 6 0		nil->JMP 00005580)
(0000557A 9 50 1		" *")
(0000557D 15 3 0		JMP 00005583)
(00005580 9 41 3		"")
(00005583 53 6 1 3 1 32		format)
(00005589 5 4		UnVar4)
(0000558B 53 1 49 1 1 32		make-mm-cmd)
(00005591 9 107 3		"VLMSG.DLL")
(00005594 51 69 92 0 0		23621)
(00005599 81 2 106 3 1 0		string-resource)
(0000559F 53 3 48 1 1 32		menu-item)
(000055A5 8 5		UnVar5)
(000055A7 5 4		UnVar4)
(000055A9 5 2		UnVar2)
(000055AB 38		=)
(000055AC 13 13 0		nil->JMP 000055BC)
(000055AF 5 5		UnVar5)
(000055B1 2		T)
(000055B2 9 47 1		'checked)
(000055B5 81 3 78 3 1 0		slot-value<-)
(000055BB 10)
(000055BC 5 5		UnVar5)
(000055BE 5 0		UnVar0)
(000055C0 42		cons)
(000055C1 8 0		UnVar0)
(000055C3 5 1		UnVar1)
(000055C5 79		1+)
(000055C6 8 1		UnVar1)
(000055C8 5 3		UnVar3)
(000055CA 60 118 255		T->JMP 00005543)
(000055CD 9 46 1		'menu)
(000055D0 9 45 1		"Alt-0")
(000055D3 9 107 3		"VLMSG.DLL")
(000055D6 51 68 92 0 0		23620)
(000055DB 81 2 106 3 1 0		string-resource)
(000055E1 5 0		UnVar0)
(000055E3 81 1 12 3 1 0		nreverse)
(000055E9 81 3 186 2 1 0		list*)
(000055EF 84		apply+ret)
;;;def window-list! 22000
(000055F0 20 2 1 1 0)
(000055F5 100 1		UNVar1)
(000055F7 1		nil)
(000055F8 1		nil)
(000055F9 42		cons)
(000055FA 8 1		UnVar1)
(000055FC 15 31 0		JMP 0000561E)
(000055FF 1		nil)
(00005600 81 1 44 1 1 0		yield)
(00005606 10)
(00005607 5 1		UnVar1)
(00005609 81 1 43 1 1 0		peek-command)
(0000560F 11)
(00005610 8 1		UnVar1)
(00005612 13 9 0		nil->JMP 0000561E)
(00005615 5 1		UnVar1)
(00005617 41		cdr)
(00005618 5 1		UnVar1)
(0000561A 40		car)
(0000561B 52 1 0		)
(0000561E 5 1		UnVar1)
(00005620 60 220 255		T->JMP 000055FF)
(00005623 95 0 38 85 0 0		func 00005526)
(00005629 5 0		UnVar0)
(0000562B 47 2 42 1 32 32		mdiwin-track-popup-menu)
;;;def window-iconize-all! 22065
(00005631 20 4 1 1 0)
(00005636 100 1		UNVar1)
(00005638 3 205 2		*active-mdiwindow*)
(0000563B 8 1		UnVar1)
(0000563D 81 0 93 3 1 0		list-mdiwindows-with-host-spouse)
(00005643 8 2		UnVar2)
(00005645 100 3		UNVar3)
(00005647 15 34 0		JMP 0000566C)
(0000564A 5 2		UnVar2)
(0000564C 40		car)
(0000564D 8 3		UnVar3)
(0000564F 5 2		UnVar2)
(00005651 41		cdr)
(00005652 8 2		UnVar2)
(00005654 5 3		UnVar3)
(00005656 9 248 2		':MINIMIZED)
(00005659 9 31 3		'state)
(0000565C 81 3 78 3 1 0		slot-value<-)
(00005662 10)
(00005663 5 3		UnVar3)
(00005665 53 1 102 3 1 32		update-host-spouse)
(0000566B 10)
(0000566C 5 2		UnVar2)
(0000566E 60 217 255		T->JMP 0000564A)
(00005671 81 0 34 3 1 0		mdiwindows-arrange-icons)
(00005677 10)
(00005678 5 1		UnVar1)
(0000567A 81 1 37 2 1 0		mdiwindow-activate)
(00005680 22		ret)
;;;def show-vlisp-windows 22145
(00005681 20 2 0 0 0)
(00005686 2		T)
(00005687 2		T)
(00005688 81 2 41 1 1 0		window-state-visible)
(0000568E 13 2 0		nil->JMP 00005693)
(00005691 1		nil)
(00005692 22		ret)
(00005693 53 0 95 3 1 32		list-true-dialogs-with-host-spouse)
(00005699 8 0		UnVar0)
(0000569B 100 1		UNVar1)
(0000569D 15 20 0		JMP 000056B4)
(000056A0 5 0		UnVar0)
(000056A2 40		car)
(000056A3 8 1		UnVar1)
(000056A5 5 0		UnVar0)
(000056A7 41		cdr)
(000056A8 8 0		UnVar0)
(000056AA 5 1		UnVar1)
(000056AC 2		T)
(000056AD 81 2 41 1 1 0		window-state-visible)
(000056B3 10)
(000056B4 5 0		UnVar0)
(000056B6 60 231 255		T->JMP 000056A0)
(000056B9 3 205 2		*active-mdiwindow*)
(000056BC 14 3 0		T->JMP 000056C2)
(000056BF 3 92 3		*console*)
(000056C2 81 1 37 2 1 0		mdiwindow-activate)
(000056C8 22		ret)
;;;def hide-vlisp-windows 22217
(000056C9 20 2 0 0 0)
(000056CE 2		T)
(000056CF 1		nil)
(000056D0 81 2 41 1 1 0		window-state-visible)
(000056D6 63		nil->ret)
(000056D7 1		nil)
(000056D8 6 40 1		*SDB-STOP-ONCE*)
(000056DB 1		nil)
(000056DC 6 39 1		*SDB-ANIMATE*)
(000056DF 53 0 95 3 1 32		list-true-dialogs-with-host-spouse)
(000056E5 8 0		UnVar0)
(000056E7 100 1		UNVar1)
(000056E9 15 20 0		JMP 00005700)
(000056EC 5 0		UnVar0)
(000056EE 40		car)
(000056EF 8 1		UnVar1)
(000056F1 5 0		UnVar0)
(000056F3 41		cdr)
(000056F4 8 0		UnVar0)
(000056F6 5 1		UnVar1)
(000056F8 1		nil)
(000056F9 81 2 41 1 1 0		window-state-visible)
(000056FF 10)
(00005700 5 0		UnVar0)
(00005702 60 231 255		T->JMP 000056EC)
(00005705 2		T)
(00005706 22		ret)
;;;def is-pref-:LEX 22279
(00005707 20 1 1 1 0)
(0000570C 50 4		4)
(0000570E 9 38 1		":LEX")
(00005711 5 0		UnVar0)
(00005713 81 2 87 1 1 0		string-mismatch)
(00005719 38		=)
(0000571A 22		ret)
;;;def twin.color-id-list 22299
(0000571B 20 4 1 1 0)
(00005720 100 1		UNVar1)
(00005722 100 2		UNVar2)
(00005724 9 37 1		':LEX-FASTA)
(00005727 3 36 1		_%twin-color-names%)
(0000572A 81 2 35 1 1 0		remove)
(00005730 8 2		UnVar2)
(00005732 5 0		UnVar0)
(00005734 81 1 132 2 1 0		TBuf.lex-scanner-id)
(0000573A 11)
(0000573B 8 1		UnVar1)
(0000573D 13 37 0		nil->JMP 00005765)
(00005740 5 1		UnVar1)
(00005742 9 34 1		':CPP)
(00005745 38		=)
(00005746 60 13 0		T->JMP 00005756)
(00005749 9 33 1		':LEX-SPEC2)
(0000574C 5 2		UnVar2)
(0000574E 81 2 206 1 1 0		delq)
(00005754 8 2		UnVar2)
(00005756 5 1		UnVar1)
(00005758 9 32 1		'(:AL :LPP))
(0000575B 81 2 114 3 1 0		memq)
(00005761 10)
(00005762 15 13 0		JMP 00005772)
(00005765 9 169 3		'(22279 is-pref-:LEX))
(00005768 5 2		UnVar2)
(0000576A 81 2 31 1 1 0		delete-if)
(00005770 8 2		UnVar2)
(00005772 5 0		UnVar0)
(00005774 81 1 126 3 1 0		type-of)
(0000577A 9 116 3		'editor)
(0000577D 38		=)
(0000577E 13 29 0		nil->JMP 0000579E)
(00005781 9 30 1		':INPUT-ZONE)
(00005784 5 2		UnVar2)
(00005786 81 2 206 1 1 0		delq)
(0000578C 8 2		UnVar2)
(0000578E 9 29 1		':CONSOLE-MESSAGE)
(00005791 5 2		UnVar2)
(00005793 81 2 206 1 1 0		delq)
(00005799 8 2		UnVar2)
(0000579B 15 160 0		JMP 0000583E)
(0000579E 5 0		UnVar0)
(000057A0 81 1 131 3 1 0		terminalp)
(000057A6 13 90 0		nil->JMP 00005803)
(000057A9 9 29 1		':CONSOLE-MESSAGE)
(000057AC 5 2		UnVar2)
(000057AE 81 2 114 3 1 0		memq)
(000057B4 1		nil)
(000057B5 81 2 225 2 1 0		setcdr)
(000057BB 10)
(000057BC 9 28 1		':BPT-ACTIVE)
(000057BF 5 2		UnVar2)
(000057C1 81 2 206 1 1 0		delq)
(000057C7 8 2		UnVar2)
(000057C9 9 27 1		':BPT-DISABLE)
(000057CC 5 2		UnVar2)
(000057CE 81 2 206 1 1 0		delq)
(000057D4 8 2		UnVar2)
(000057D6 5 0		UnVar0)
(000057D8 81 1 215 2 1 0		tbuf.ro-tmark)
(000057DE 8 3		UnVar3)
(000057E0 5 3		UnVar3)
(000057E2 61 8 0		nil->JMP 000057ED)
(000057E5 5 3		UnVar3)
(000057E7 81 1 209 1 1 0		tmark.seat)
(000057ED 13 3 0		nil->JMP 000057F3)
(000057F0 15 13 0		JMP 00005800)
(000057F3 9 30 1		':INPUT-ZONE)
(000057F6 5 2		UnVar2)
(000057F8 81 2 206 1 1 0		delq)
(000057FE 8 2		UnVar2)
(00005800 15 59 0		JMP 0000583E)
(00005803 5 0		UnVar0)
(00005805 53 1 26 1 1 32		outwinp)
(0000580B 13 48 0		nil->JMP 0000583E)
(0000580E 9 28 1		':BPT-ACTIVE)
(00005811 5 2		UnVar2)
(00005813 81 2 206 1 1 0		delq)
(00005819 8 2		UnVar2)
(0000581B 9 27 1		':BPT-DISABLE)
(0000581E 5 2		UnVar2)
(00005820 81 2 206 1 1 0		delq)
(00005826 8 2		UnVar2)
(00005828 9 25 1		':ERROR-HIGHLIGHT)
(0000582B 5 2		UnVar2)
(0000582D 81 2 114 3 1 0		memq)
(00005833 1		nil)
(00005834 81 2 225 2 1 0		setcdr)
(0000583A 10)
(0000583B 15 0 0		JMP 0000583E)
(0000583E 5 2		UnVar2)
(00005840 22		ret)
;;;def _small-positive 22593
(00005841 20 1 1 1 0)
(00005846 5 0		UnVar0)
(00005848 81 1 33 2 1 0		fixnump)
(0000584E 63		nil->ret)
(0000584F 50 0		0)
(00005851 5 0		UnVar0)
(00005853 78		<=)
(00005854 63		nil->ret)
(00005855 5 0		UnVar0)
(00005857 50 20		20)
(00005859 78		<=)
(0000585A 22		ret)
;;;def _update-winattr-dlg 22619
(0000585B 20 9 1 1 0)
(00005860 100 1		UNVar1)
(00005862 100 2		UNVar2)
(00005864 100 3		UNVar3)
(00005866 5 0		UnVar0)
(00005868 9 68 2		'items)
(0000586B 81 2 86 3 1 0		slot-value)
(00005871 8 1		UnVar1)
(00005873 51 19 5 0 0		1299)
(00005878 51 252 255 0 0		65532)
(0000587D 51 251 255 0 0		65531)
(00005882 51 250 255 0 0		65530)
(00005887 51 249 255 0 0		65529)
(0000588C 51 248 255 0 0		65528)
(00005891 51 61 4 0 0		1085)
(00005896 51 62 4 0 0		1086)
(0000589B 51 241 3 0 0		1009)
(000058A0 51 67 4 0 0		1091)
(000058A5 51 234 3 0 0		1002)
(000058AA 51 21 5 0 0		1301)
(000058AF 51 47 4 0 0		1071)
(000058B4 51 22 5 0 0		1302)
(000058B9 50 1		1)
(000058BB 50 2		2)
(000058BD 51 23 5 0 0		1303)
(000058C2 57 17 0		list)
(000058C5 8 3		UnVar3)
(000058C7 5 1		UnVar1)
(000058C9 8 4		UnVar4)
(000058CB 5 3		UnVar3)
(000058CD 8 5		UnVar5)
(000058CF 100 6		UNVar6)
(000058D1 15 31 0		JMP 000058F3)
(000058D4 5 4		UnVar4)
(000058D6 40		car)
(000058D7 8 7		UnVar7)
(000058D9 5 5		UnVar5)
(000058DB 40		car)
(000058DC 8 8		UnVar8)
(000058DE 5 7		UnVar7)
(000058E0 40		car)
(000058E1 5 8		UnVar8)
(000058E3 42		cons)
(000058E4 5 6		UnVar6)
(000058E6 42		cons)
(000058E7 8 6		UnVar6)
(000058E9 5 4		UnVar4)
(000058EB 41		cdr)
(000058EC 8 4		UnVar4)
(000058EE 5 5		UnVar5)
(000058F0 41		cdr)
(000058F1 8 5		UnVar5)
(000058F3 5 4		UnVar4)
(000058F5 61 2 0		nil->JMP 000058FA)
(000058F8 5 5		UnVar5)
(000058FA 60 215 255		T->JMP 000058D4)
(000058FD 5 6		UnVar6)
(000058FF 81 1 12 3 1 0		nreverse)
(00005905 8 2		UnVar2)
(00005907 5 0		UnVar0)
(00005909 9 66 2		"vldlg.dll")
(0000590C 51 144 0 0 0		144)
(00005911 5 2		UnVar2)
(00005913 47 4 65 2 32 32		dialog-update-from-res)
;;;def !window-attr 22809
(00005919 21 31 1 1 0)
(0000591E 100 1		UNVar1)
(00005920 100 2		UNVar2)
(00005922 100 3		UNVar3)
(00005924 100 4		UNVar4)
(00005926 100 5		UNVar5)
(00005928 100 6		UNVar6)
(0000592A 100 7		UNVar7)
(0000592C 100 8		UNVar8)
(0000592E 100 9		UNVar9)
(00005930 100 10		UNVar10)
(00005932 100 11		UNVar11)
(00005934 100 12		UNVar12)
(00005936 100 13		UNVar13)
(00005938 100 14		UNVar14)
(0000593A 100 15		UNVar15)
(0000593C 100 16		UNVar16)
(0000593E 100 17		UNVar17)
(00005940 100 18		UNVar18)
(00005942 100 19		UNVar19)
(00005944 100 20		UNVar20)
(00005946 100 21		UNVar21)
(00005948 100 22		UNVar22)
(0000594A 100 23		UNVar23)
(0000594C 100 24		UNVar24)
(0000594E 100 25		UNVar25)
(00005950 100 26		UNVar26)
(00005952 100 27		UNVar27)
(00005954 5 0		UnVar0)
(00005956 81 1 135 3 1 0		TWinp)
(0000595C 60 14 0		T->JMP 0000596D)
(0000595F 81 0 81 1 1 0		active-mdiwindow)
(00005965 14 3 0		T->JMP 0000596B)
(00005968 3 92 3		*console*)
(0000596B 8 0		UnVar0)
(0000596D 5 0		UnVar0)
(0000596F 95 1 27 87 0 0		twin.color-id-list)
(00005975 8 9		UnVar9)
(00005977 5 0		UnVar0)
(00005979 9 234 2		'color-vector)
(0000597C 81 2 86 3 1 0		slot-value)
(00005982 11)
(00005983 8 8		UnVar8)
(00005985 13 13 0		nil->JMP 00005995)
(00005988 5 8		UnVar8)
(0000598A 53 1 24 1 1 32		copy-vector)
(00005990 8 7		UnVar7)
(00005992 15 33 0		JMP 000059B6)
(00005995 50 2		2)
(00005997 5 9		UnVar9)
(00005999 81 1 204 1 1 0		last)
(0000599F 40		car)
(000059A0 53 1 23 1 1 32		twin-color-name->id)
(000059A6 79		1+)
(000059A7 72		*)
(000059A8 81 1 22 1 1 0		make-vector)
(000059AE 81 1 21 1 1 0		_twin.kern-colors-vec)
(000059B4 8 7		UnVar7)
(000059B6 5 0		UnVar0)
(000059B8 5 7		UnVar7)
(000059BA 9 234 2		'color-vector)
(000059BD 81 3 78 3 1 0		slot-value<-)
(000059C3 10)
(000059C4 5 9		UnVar9)
(000059C6 8 28		UnVar28)
(000059C8 100 29		UNVar29)
(000059CA 15 26 0		JMP 000059E7)
(000059CD 5 28		UnVar28)
(000059CF 40		car)
(000059D0 8 30		UnVar30)
(000059D2 5 30		UnVar30)
(000059D4 81 1 24 3 1 0		string)
(000059DA 57 1 0		list)
(000059DD 5 29		UnVar29)
(000059DF 42		cons)
(000059E0 8 29		UnVar29)
(000059E2 5 28		UnVar28)
(000059E4 41		cdr)
(000059E5 8 28		UnVar28)
(000059E7 5 28		UnVar28)
(000059E9 60 225 255		T->JMP 000059CD)
(000059EC 5 29		UnVar29)
(000059EE 81 1 12 3 1 0		nreverse)
(000059F4 8 9		UnVar9)
(000059F6 5 0		UnVar0)
(000059F8 81 1 240 2 1 0		TWin.fcolor)
(000059FE 8 18		UnVar18)
(00005A00 5 0		UnVar0)
(00005A02 81 1 238 2 1 0		TWin.bcolor)
(00005A08 8 17		UnVar17)
(00005A0A 5 7		UnVar7)
(00005A0C 5 18		UnVar18)
(00005A0E 3 20 1		*WT-ci*)
(00005A11 53 3 19 1 1 32		color-tab-fg<-)
(00005A17 10)
(00005A18 5 7		UnVar7)
(00005A1A 5 17		UnVar17)
(00005A1C 3 20 1		*WT-ci*)
(00005A1F 53 3 18 1 1 32		color-tab-bg<-)
(00005A25 10)
(00005A26 9 17 1		':WINDOW-TEXT)
(00005A29 81 1 16 1 1 0		symbol-name)
(00005A2F 5 9		UnVar9)
(00005A31 81 2 15 1 1 0		assoc)
(00005A37 2		T)
(00005A38 81 2 225 2 1 0		setcdr)
(00005A3E 10)
(00005A3F 51 40 0 12 0		786472)
(00005A44 9 107 3		"VLMSG.DLL")
(00005A47 51 250 90 0 0		23290)
(00005A4C 81 2 106 3 1 0		string-resource)
(00005A52 9 14 1		':LEFT)
(00005A55 53 3 13 1 1 32		static-text)
(00005A5B 8 6		UnVar6)
(00005A5D 51 12 0 12 0		786444)
(00005A62 15 15 0		JMP 00005A74)
(00005A65 20 0 0 0 0)
(00005A6A 4 1 0		UpVar1-0)
(00005A6D 81 1 232 2 1 0		TWin.tab-width)
(00005A73 22		ret)
(00005A74 12 168 3		'(23141 nil))
(00005A77 15 17 0		JMP 00005A8B)
(00005A7A 20 1 1 1 0)
(00005A7F 4 1 0		UpVar1-0)
(00005A82 5 0		UnVar0)
(00005A84 81 2 12 1 1 0		TWin.tab-width<-)
(00005A8A 22		ret)
(00005A8B 12 167 3		'(23162 nil))
(00005A8E 57 2 0		list)
(00005A91 15 26 0		JMP 00005AAE)
(00005A94 20 1 1 1 0)
(00005A99 5 0		UnVar0)
(00005A9B 81 1 33 2 1 0		fixnump)
(00005AA1 63		nil->ret)
(00005AA2 50 1		1)
(00005AA4 5 0		UnVar0)
(00005AA6 76		<)
(00005AA7 63		nil->ret)
(00005AA8 5 0		UnVar0)
(00005AAA 50 20		20)
(00005AAC 78		<=)
(00005AAD 22		ret)
(00005AAE 9 166 3		'(23188 nil))
(00005AB1 9 107 3		"VLMSG.DLL")
(00005AB4 51 4 91 0 0		23300)
(00005AB9 81 2 106 3 1 0		string-resource)
(00005ABF 9 107 3		"VLMSG.DLL")
(00005AC2 51 14 91 0 0		23310)
(00005AC7 81 2 106 3 1 0		string-resource)
(00005ACD 9 107 3		"VLMSG.DLL")
(00005AD0 51 24 91 0 0		23320)
(00005AD5 81 2 106 3 1 0		string-resource)
(00005ADB 53 6 11 1 1 32		accessed-checked-editable-text)
(00005AE1 8 5		UnVar5)
(00005AE3 51 40 0 12 0		786472)
(00005AE8 9 107 3		"VLMSG.DLL")
(00005AEB 51 34 91 0 0		23330)
(00005AF0 81 2 106 3 1 0		string-resource)
(00005AF6 9 14 1		':LEFT)
(00005AF9 53 3 13 1 1 32		static-text)
(00005AFF 8 3		UnVar3)
(00005B01 51 12 0 12 0		786444)
(00005B06 15 15 0		JMP 00005B18)
(00005B09 20 0 0 0 0)
(00005B0E 4 1 0		UpVar1-0)
(00005B11 81 1 230 2 1 0		TWin.left-margin)
(00005B17 22		ret)
(00005B18 12 165 3		'(23305 nil))
(00005B1B 15 17 0		JMP 00005B2F)
(00005B1E 20 1 1 1 0)
(00005B23 4 1 0		UpVar1-0)
(00005B26 5 0		UnVar0)
(00005B28 81 2 10 1 1 0		TWin.left-margin<-)
(00005B2E 22		ret)
(00005B2F 12 164 3		'(23326 nil))
(00005B32 57 2 0		list)
(00005B35 9 163 3		'(22593 _small-positive))
(00005B38 9 107 3		"VLMSG.DLL")
(00005B3B 51 44 91 0 0		23340)
(00005B40 81 2 106 3 1 0		string-resource)
(00005B46 9 107 3		"VLMSG.DLL")
(00005B49 51 54 91 0 0		23350)
(00005B4E 81 2 106 3 1 0		string-resource)
(00005B54 9 107 3		"VLMSG.DLL")
(00005B57 51 64 91 0 0		23360)
(00005B5C 81 2 106 3 1 0		string-resource)
(00005B62 53 6 11 1 1 32		accessed-checked-editable-text)
(00005B68 8 2		UnVar2)
(00005B6A 51 61 0 11 0		720957)
(00005B6F 9 107 3		"VLMSG.DLL")
(00005B72 51 74 91 0 0		23370)
(00005B77 81 2 106 3 1 0		string-resource)
(00005B7D 9 9 1		':RIGHT)
(00005B80 53 3 13 1 1 32		static-text)
(00005B86 8 15		UnVar15)
(00005B88 5 15		UnVar15)
(00005B8A 2		T)
(00005B8B 81 2 111 1 1 0		dialog-item.color-enabled<-)
(00005B91 10)
(00005B92 51 61 0 11 0		720957)
(00005B97 9 107 3		"VLMSG.DLL")
(00005B9A 51 84 91 0 0		23380)
(00005B9F 81 2 106 3 1 0		string-resource)
(00005BA5 9 8 1		':CENTER)
(00005BA8 53 3 13 1 1 32		static-text)
(00005BAE 8 16		UnVar16)
(00005BB0 5 16		UnVar16)
(00005BB2 2		T)
(00005BB3 81 2 111 1 1 0		dialog-item.color-enabled<-)
(00005BB9 10)
(00005BBA 51 61 0 11 0		720957)
(00005BBF 9 107 3		"VLMSG.DLL")
(00005BC2 51 74 91 0 0		23370)
(00005BC7 81 2 106 3 1 0		string-resource)
(00005BCD 9 14 1		':LEFT)
(00005BD0 53 3 13 1 1 32		static-text)
(00005BD6 8 14		UnVar14)
(00005BD8 5 14		UnVar14)
(00005BDA 2		T)
(00005BDB 81 2 111 1 1 0		dialog-item.color-enabled<-)
(00005BE1 10)
(00005BE2 5 15		UnVar15)
(00005BE4 5 18		UnVar18)
(00005BE6 5 17		UnVar17)
(00005BE8 95 3 9 100 0 0		func 00006409)
(00005BEE 10)
(00005BEF 5 14		UnVar14)
(00005BF1 5 18		UnVar18)
(00005BF3 5 17		UnVar17)
(00005BF5 95 3 9 100 0 0		func 00006409)
(00005BFB 10)
(00005BFC 5 16		UnVar16)
(00005BFE 5 18		UnVar18)
(00005C00 5 17		UnVar17)
(00005C02 95 3 9 100 0 0		func 00006409)
(00005C08 10)
(00005C09 5 0		UnVar0)
(00005C0B 81 1 132 2 1 0		TBuf.lex-scanner-id)
(00005C11 13 101 0		nil->JMP 00005C79)
(00005C14 51 60 0 12 0		786492)
(00005C19 9 107 3		"VLMSG.DLL")
(00005C1C 51 94 91 0 0		23390)
(00005C21 81 2 106 3 1 0		string-resource)
(00005C27 15 26 0		JMP 00005C44)
(00005C2A 20 1 1 1 0)
(00005C2F 4 1 0		UpVar1-0)
(00005C32 4 1 11		UpVar1-11)
(00005C35 9 47 1		'checked)
(00005C38 81 2 86 3 1 0		slot-value)
(00005C3E 96 2 90 100 0 0		func 0000645A)
(00005C44 12 162 3		'(23594 nil))
(00005C47 1		nil)
(00005C48 9 107 3		"VLMSG.DLL")
(00005C4B 51 104 91 0 0		23400)
(00005C50 81 2 106 3 1 0		string-resource)
(00005C56 53 5 7 1 1 32		check-box)
(00005C5C 8 11		UnVar11)
(00005C5E 5 0		UnVar0)
(00005C60 9 236 2		'lex-color-p)
(00005C63 81 2 86 3 1 0		slot-value)
(00005C69 8 10		UnVar10)
(00005C6B 5 11		UnVar11)
(00005C6D 5 10		UnVar10)
(00005C6F 9 47 1		'checked)
(00005C72 81 3 78 3 1 0		slot-value<-)
(00005C78 10)
(00005C79 51 80 0 12 0		786512)
(00005C7E 9 107 3		"VLMSG.DLL")
(00005C81 51 114 91 0 0		23410)
(00005C86 81 2 106 3 1 0		string-resource)
(00005C8C 15 189 0		JMP 00005D4C)
(00005C8F 20 2 1 1 0)
(00005C94 100 1		UNVar1)
(00005C96 4 1 21		UpVar1-21)
(00005C99 95 1 36 100 0 0		func 00006424)
(00005C9F 8 1		UnVar1)
(00005CA1 5 1		UnVar1)
(00005CA3 63		nil->ret)
(00005CA4 5 1		UnVar1)
(00005CA6 9 17 1		':WINDOW-TEXT)
(00005CA9 38		=)
(00005CAA 13 34 0		nil->JMP 00005CCF)
(00005CAD 4 1 19		UpVar1-19)
(00005CB0 1		nil)
(00005CB1 9 47 1		'checked)
(00005CB4 81 3 78 3 1 0		slot-value<-)
(00005CBA 10)
(00005CBB 4 1 19		UpVar1-19)
(00005CBE 53 1 102 3 1 32		update-host-spouse)
(00005CC4 10)
(00005CC5 3 207 2		*stop-beep*)
(00005CC8 81 1 206 2 1 0		message-beep)
(00005CCE 22		ret)
(00005CCF 4 1 19		UpVar1-19)
(00005CD2 9 47 1		'checked)
(00005CD5 81 2 86 3 1 0		slot-value)
(00005CDB 13 16 0		nil->JMP 00005CEE)
(00005CDE 4 1 13		UpVar1-13)
(00005CE1 4 1 18		UpVar1-18)
(00005CE4 9 6 1		'rgb)
(00005CE7 81 3 78 3 1 0		slot-value<-)
(00005CED 10)
(00005CEE 4 1 16		UpVar1-16)
(00005CF1 4 1 18		UpVar1-18)
(00005CF4 81 2 113 1 1 0		dialog-item.fcolor<-)
(00005CFA 10)
(00005CFB 4 1 13		UpVar1-13)
(00005CFE 53 1 102 3 1 32		update-host-spouse)
(00005D04 10)
(00005D05 4 1 16		UpVar1-16)
(00005D08 53 1 102 3 1 32		update-host-spouse)
(00005D0E 10)
(00005D0F 4 1 7		UpVar1-7)
(00005D12 4 1 19		UpVar1-19)
(00005D15 9 47 1		'checked)
(00005D18 81 2 86 3 1 0		slot-value)
(00005D1E 13 4 0		nil->JMP 00005D25)
(00005D21 1		nil)
(00005D22 15 3 0		JMP 00005D28)
(00005D25 4 1 18		UpVar1-18)
(00005D28 5 1		UnVar1)
(00005D2A 53 3 19 1 1 32		color-tab-fg<-)
(00005D30 10)
(00005D31 4 1 0		UpVar1-0)
(00005D34 4 1 11		UpVar1-11)
(00005D37 61 12 0		nil->JMP 00005D46)
(00005D3A 4 1 11		UpVar1-11)
(00005D3D 9 47 1		'checked)
(00005D40 81 2 86 3 1 0		slot-value)
(00005D46 96 2 90 100 0 0		func 0000645A)
(00005D4C 12 161 3		'(23695 nil))
(00005D4F 1		nil)
(00005D50 9 107 3		"VLMSG.DLL")
(00005D53 51 124 91 0 0		23420)
(00005D58 81 2 106 3 1 0		string-resource)
(00005D5E 53 5 7 1 1 32		check-box)
(00005D64 8 19		UnVar19)
(00005D66 51 80 0 12 0		786512)
(00005D6B 9 107 3		"VLMSG.DLL")
(00005D6E 51 134 91 0 0		23430)
(00005D73 81 2 106 3 1 0		string-resource)
(00005D79 15 188 0		JMP 00005E38)
(00005D7C 20 2 1 1 0)
(00005D81 100 1		UNVar1)
(00005D83 4 1 21		UpVar1-21)
(00005D86 95 1 36 100 0 0		func 00006424)
(00005D8C 11)
(00005D8D 8 1		UnVar1)
(00005D8F 63		nil->ret)
(00005D90 5 1		UnVar1)
(00005D92 9 17 1		':WINDOW-TEXT)
(00005D95 38		=)
(00005D96 13 34 0		nil->JMP 00005DBB)
(00005D99 4 1 20		UpVar1-20)
(00005D9C 1		nil)
(00005D9D 9 47 1		'checked)
(00005DA0 81 3 78 3 1 0		slot-value<-)
(00005DA6 10)
(00005DA7 4 1 20		UpVar1-20)
(00005DAA 53 1 102 3 1 32		update-host-spouse)
(00005DB0 10)
(00005DB1 3 207 2		*stop-beep*)
(00005DB4 81 1 206 2 1 0		message-beep)
(00005DBA 22		ret)
(00005DBB 4 1 20		UpVar1-20)
(00005DBE 9 47 1		'checked)
(00005DC1 81 2 86 3 1 0		slot-value)
(00005DC7 13 16 0		nil->JMP 00005DDA)
(00005DCA 4 1 12		UpVar1-12)
(00005DCD 4 1 17		UpVar1-17)
(00005DD0 9 6 1		'rgb)
(00005DD3 81 3 78 3 1 0		slot-value<-)
(00005DD9 10)
(00005DDA 4 1 16		UpVar1-16)
(00005DDD 4 1 17		UpVar1-17)
(00005DE0 81 2 112 1 1 0		dialog-item.bcolor<-)
(00005DE6 10)
(00005DE7 4 1 12		UpVar1-12)
(00005DEA 53 1 102 3 1 32		update-host-spouse)
(00005DF0 10)
(00005DF1 4 1 16		UpVar1-16)
(00005DF4 53 1 102 3 1 32		update-host-spouse)
(00005DFA 10)
(00005DFB 4 1 7		UpVar1-7)
(00005DFE 4 1 20		UpVar1-20)
(00005E01 9 47 1		'checked)
(00005E04 81 2 86 3 1 0		slot-value)
(00005E0A 13 4 0		nil->JMP 00005E11)
(00005E0D 1		nil)
(00005E0E 15 3 0		JMP 00005E14)
(00005E11 4 1 17		UpVar1-17)
(00005E14 5 1		UnVar1)
(00005E16 53 3 18 1 1 32		color-tab-bg<-)
(00005E1C 10)
(00005E1D 4 1 0		UpVar1-0)
(00005E20 4 1 11		UpVar1-11)
(00005E23 61 12 0		nil->JMP 00005E32)
(00005E26 4 1 11		UpVar1-11)
(00005E29 9 47 1		'checked)
(00005E2C 81 2 86 3 1 0		slot-value)
(00005E32 96 2 90 100 0 0		func 0000645A)
(00005E38 12 160 3		'(23932 nil))
(00005E3B 1		nil)
(00005E3C 9 107 3		"VLMSG.DLL")
(00005E3F 51 144 91 0 0		23440)
(00005E44 81 2 106 3 1 0		string-resource)
(00005E4A 53 5 7 1 1 32		check-box)
(00005E50 8 20		UnVar20)
(00005E52 15 45 0		JMP 00005E82)
(00005E55 20 3 1 1 0)
(00005E5A 100 1		UNVar1)
(00005E5C 100 2		UNVar2)
(00005E5E 1		nil)
(00005E5F 81 1 7 2 1 0		box)
(00005E65 8 1		UnVar1)
(00005E67 5 0		UnVar0)
(00005E69 5 1		UnVar1)
(00005E6B 53 2 80 2 1 32		verified-sync-down)
(00005E71 13 2 0		nil->JMP 00005E76)
(00005E74 1		nil)
(00005E75 22		ret)
(00005E76 2		T)
(00005E77 7 1 26		UpVar1-26)
(00005E7A 5 0		UnVar0)
(00005E7C 47 1 94 3 32 32		destroy-host-spouse)
(00005E82 12 159 3		'(24149 nil))
(00005E85 8 23		UnVar23)
(00005E87 51 42 0 14 0		917546)
(00005E8C 9 107 3		"VLMSG.DLL")
(00005E8F 51 84 61 0 0		15700)
(00005E94 81 2 106 3 1 0		string-resource)
(00005E9A 5 23		UnVar23)
(00005E9C 9 107 3		"VLMSG.DLL")
(00005E9F 51 154 91 0 0		23450)
(00005EA4 81 2 106 3 1 0		string-resource)
(00005EAA 53 4 109 1 1 32		push-button)
(00005EB0 8 25		UnVar25)
(00005EB2 15 42 0		JMP 00005EDF)
(00005EB5 20 1 1 1 0)
(00005EBA 4 1 0		UpVar1-0)
(00005EBD 4 1 8		UpVar1-8)
(00005EC0 9 234 2		'color-vector)
(00005EC3 81 3 78 3 1 0		slot-value<-)
(00005EC9 10)
(00005ECA 5 0		UnVar0)
(00005ECC 53 1 94 3 1 32		destroy-host-spouse)
(00005ED2 10)
(00005ED3 4 1 0		UpVar1-0)
(00005ED6 4 1 10		UpVar1-10)
(00005ED9 96 2 90 100 0 0		func 0000645A)
(00005EDF 12 158 3		'(24245 nil))
(00005EE2 8 22		UnVar22)
(00005EE4 51 42 0 14 0		917546)
(00005EE9 9 107 3		"VLMSG.DLL")
(00005EEC 51 228 82 0 0		21220)
(00005EF1 81 2 106 3 1 0		string-resource)
(00005EF7 5 22		UnVar22)
(00005EF9 9 107 3		"VLMSG.DLL")
(00005EFC 51 164 91 0 0		23460)
(00005F01 81 2 106 3 1 0		string-resource)
(00005F07 53 4 109 1 1 32		push-button)
(00005F0D 8 24		UnVar24)
(00005F0F 51 90 0 12 0		786522)
(00005F14 5 9		UnVar9)
(00005F16 15 14 1		JMP 00006027)
(00005F19 20 4 1 1 0)
(00005F1E 100 1		UNVar1)
(00005F20 100 2		UNVar2)
(00005F22 100 3		UNVar3)
(00005F24 4 1 21		UpVar1-21)
(00005F27 95 1 36 100 0 0		func 00006424)
(00005F2D 11)
(00005F2E 8 3		UnVar3)
(00005F30 63		nil->ret)
(00005F31 9 107 3		"VLMSG.DLL")
(00005F34 51 86 119 0 0		30550)
(00005F39 81 2 106 3 1 0		string-resource)
(00005F3F 5 3		UnVar3)
(00005F41 81 1 24 3 1 0		string)
(00005F47 81 2 23 3 1 0		_win-format-message)
(00005F4D 81 1 45 3 1 0		ales-prompt-msg)
(00005F53 10)
(00005F54 4 1 7		UpVar1-7)
(00005F57 5 3		UnVar3)
(00005F59 53 2 5 1 1 32		color-tab-fg)
(00005F5F 8 2		UnVar2)
(00005F61 4 1 7		UpVar1-7)
(00005F64 5 3		UnVar3)
(00005F66 53 2 4 1 1 32		color-tab-bg)
(00005F6C 8 1		UnVar1)
(00005F6E 5 2		UnVar2)
(00005F70 13 17 0		nil->JMP 00005F84)
(00005F73 4 1 19		UpVar1-19)
(00005F76 1		nil)
(00005F77 9 47 1		'checked)
(00005F7A 81 3 78 3 1 0		slot-value<-)
(00005F80 10)
(00005F81 15 19 0		JMP 00005F97)
(00005F84 4 1 19		UpVar1-19)
(00005F87 2		T)
(00005F88 9 47 1		'checked)
(00005F8B 81 3 78 3 1 0		slot-value<-)
(00005F91 10)
(00005F92 4 1 18		UpVar1-18)
(00005F95 8 2		UnVar2)
(00005F97 4 1 19		UpVar1-19)
(00005F9A 53 1 102 3 1 32		update-host-spouse)
(00005FA0 10)
(00005FA1 5 1		UnVar1)
(00005FA3 13 17 0		nil->JMP 00005FB7)
(00005FA6 4 1 20		UpVar1-20)
(00005FA9 1		nil)
(00005FAA 9 47 1		'checked)
(00005FAD 81 3 78 3 1 0		slot-value<-)
(00005FB3 10)
(00005FB4 15 19 0		JMP 00005FCA)
(00005FB7 4 1 20		UpVar1-20)
(00005FBA 2		T)
(00005FBB 9 47 1		'checked)
(00005FBE 81 3 78 3 1 0		slot-value<-)
(00005FC4 10)
(00005FC5 4 1 17		UpVar1-17)
(00005FC8 8 1		UnVar1)
(00005FCA 4 1 20		UpVar1-20)
(00005FCD 53 1 102 3 1 32		update-host-spouse)
(00005FD3 10)
(00005FD4 4 1 13		UpVar1-13)
(00005FD7 5 2		UnVar2)
(00005FD9 9 6 1		'rgb)
(00005FDC 81 3 78 3 1 0		slot-value<-)
(00005FE2 10)
(00005FE3 4 1 12		UpVar1-12)
(00005FE6 5 1		UnVar1)
(00005FE8 9 6 1		'rgb)
(00005FEB 81 3 78 3 1 0		slot-value<-)
(00005FF1 10)
(00005FF2 4 1 13		UpVar1-13)
(00005FF5 53 1 102 3 1 32		update-host-spouse)
(00005FFB 10)
(00005FFC 4 1 12		UpVar1-12)
(00005FFF 53 1 102 3 1 32		update-host-spouse)
(00006005 10)
(00006006 4 1 16		UpVar1-16)
(00006009 5 2		UnVar2)
(0000600B 81 2 113 1 1 0		dialog-item.fcolor<-)
(00006011 10)
(00006012 4 1 16		UpVar1-16)
(00006015 5 1		UnVar1)
(00006017 81 2 112 1 1 0		dialog-item.bcolor<-)
(0000601D 10)
(0000601E 4 1 16		UpVar1-16)
(00006021 47 1 102 3 32 32		update-host-spouse)
(00006027 12 157 3		'(24345 nil))
(0000602A 1		nil)
(0000602B 9 107 3		"VLMSG.DLL")
(0000602E 51 184 91 0 0		23480)
(00006033 81 2 106 3 1 0		string-resource)
(00006039 53 5 3 1 1 32		drop-down-list-box)
(0000603F 8 21		UnVar21)
(00006041 5 21		UnVar21)
(00006043 3 2 1		WS_TABSTOP)
(00006046 3 1 1		WS_GROUP)
(00006049 3 0 1		WS_VSCROLL)
(0000604C 3 255 0		WS_VISIBLE)
(0000604F 3 254 0		WS_CHILD)
(00006052 3 253 0		LBS_SORT)
(00006055 3 252 0		LBS_NOTIFY)
(00006058 81 7 115 1 1 0		logior)
(0000605E 81 2 114 1 1 0		dialog-item._msw-style<-)
(00006064 10)
(00006065 51 181 0 12 0		786613)
(0000606A 15 231 0		JMP 00006154)
(0000606D 20 2 1 1 0)
(00006072 100 1		UNVar1)
(00006074 4 1 21		UpVar1-21)
(00006077 95 1 36 100 0 0		func 00006424)
(0000607D 8 1		UnVar1)
(0000607F 4 1 19		UpVar1-19)
(00006082 9 47 1		'checked)
(00006085 81 2 86 3 1 0		slot-value)
(0000608B 13 24 0		nil->JMP 000060A6)
(0000608E 4 1 19		UpVar1-19)
(00006091 1		nil)
(00006092 9 47 1		'checked)
(00006095 81 3 78 3 1 0		slot-value<-)
(0000609B 10)
(0000609C 4 1 19		UpVar1-19)
(0000609F 53 1 102 3 1 32		update-host-spouse)
(000060A5 10)
(000060A6 5 1		UnVar1)
(000060A8 9 17 1		':WINDOW-TEXT)
(000060AB 38		=)
(000060AC 13 79 0		nil->JMP 000060FE)
(000060AF 4 1 13		UpVar1-13)
(000060B2 9 6 1		'rgb)
(000060B5 81 2 86 3 1 0		slot-value)
(000060BB 7 1 18		UpVar1-18)
(000060BE 4 1 15		UpVar1-15)
(000060C1 4 1 13		UpVar1-13)
(000060C4 9 6 1		'rgb)
(000060C7 81 2 86 3 1 0		slot-value)
(000060CD 81 2 113 1 1 0		dialog-item.fcolor<-)
(000060D3 10)
(000060D4 4 1 14		UpVar1-14)
(000060D7 4 1 13		UpVar1-13)
(000060DA 9 6 1		'rgb)
(000060DD 81 2 86 3 1 0		slot-value)
(000060E3 81 2 113 1 1 0		dialog-item.fcolor<-)
(000060E9 10)
(000060EA 4 1 15		UpVar1-15)
(000060ED 53 1 102 3 1 32		update-host-spouse)
(000060F3 10)
(000060F4 4 1 14		UpVar1-14)
(000060F7 53 1 102 3 1 32		update-host-spouse)
(000060FD 10)
(000060FE 4 1 16		UpVar1-16)
(00006101 4 1 13		UpVar1-13)
(00006104 9 6 1		'rgb)
(00006107 81 2 86 3 1 0		slot-value)
(0000610D 81 2 113 1 1 0		dialog-item.fcolor<-)
(00006113 10)
(00006114 4 1 16		UpVar1-16)
(00006117 53 1 102 3 1 32		update-host-spouse)
(0000611D 10)
(0000611E 5 1		UnVar1)
(00006120 63		nil->ret)
(00006121 4 1 7		UpVar1-7)
(00006124 4 1 13		UpVar1-13)
(00006127 9 6 1		'rgb)
(0000612A 81 2 86 3 1 0		slot-value)
(00006130 5 1		UnVar1)
(00006132 53 3 19 1 1 32		color-tab-fg<-)
(00006138 10)
(00006139 4 1 0		UpVar1-0)
(0000613C 4 1 11		UpVar1-11)
(0000613F 61 12 0		nil->JMP 0000614E)
(00006142 4 1 11		UpVar1-11)
(00006145 9 47 1		'checked)
(00006148 81 2 86 3 1 0		slot-value)
(0000614E 96 2 90 100 0 0		func 0000645A)
(00006154 12 156 3		'(24685 nil))
(00006157 9 107 3		"VLMSG.DLL")
(0000615A 51 194 91 0 0		23490)
(0000615F 81 2 106 3 1 0		string-resource)
(00006165 53 3 251 0 1 32		color-selector)
(0000616B 8 13		UnVar13)
(0000616D 5 13		UnVar13)
(0000616F 5 18		UnVar18)
(00006171 9 6 1		'rgb)
(00006174 81 3 78 3 1 0		slot-value<-)
(0000617A 10)
(0000617B 51 181 0 12 0		786613)
(00006180 15 231 0		JMP 0000626A)
(00006183 20 2 1 1 0)
(00006188 100 1		UNVar1)
(0000618A 4 1 21		UpVar1-21)
(0000618D 95 1 36 100 0 0		func 00006424)
(00006193 8 1		UnVar1)
(00006195 4 1 20		UpVar1-20)
(00006198 9 47 1		'checked)
(0000619B 81 2 86 3 1 0		slot-value)
(000061A1 13 24 0		nil->JMP 000061BC)
(000061A4 4 1 20		UpVar1-20)
(000061A7 1		nil)
(000061A8 9 47 1		'checked)
(000061AB 81 3 78 3 1 0		slot-value<-)
(000061B1 10)
(000061B2 4 1 20		UpVar1-20)
(000061B5 53 1 102 3 1 32		update-host-spouse)
(000061BB 10)
(000061BC 5 1		UnVar1)
(000061BE 9 17 1		':WINDOW-TEXT)
(000061C1 38		=)
(000061C2 13 79 0		nil->JMP 00006214)
(000061C5 4 1 12		UpVar1-12)
(000061C8 9 6 1		'rgb)
(000061CB 81 2 86 3 1 0		slot-value)
(000061D1 7 1 17		UpVar1-17)
(000061D4 4 1 15		UpVar1-15)
(000061D7 4 1 12		UpVar1-12)
(000061DA 9 6 1		'rgb)
(000061DD 81 2 86 3 1 0		slot-value)
(000061E3 81 2 112 1 1 0		dialog-item.bcolor<-)
(000061E9 10)
(000061EA 4 1 14		UpVar1-14)
(000061ED 4 1 12		UpVar1-12)
(000061F0 9 6 1		'rgb)
(000061F3 81 2 86 3 1 0		slot-value)
(000061F9 81 2 112 1 1 0		dialog-item.bcolor<-)
(000061FF 10)
(00006200 4 1 15		UpVar1-15)
(00006203 53 1 102 3 1 32		update-host-spouse)
(00006209 10)
(0000620A 4 1 14		UpVar1-14)
(0000620D 53 1 102 3 1 32		update-host-spouse)
(00006213 10)
(00006214 4 1 16		UpVar1-16)
(00006217 4 1 12		UpVar1-12)
(0000621A 9 6 1		'rgb)
(0000621D 81 2 86 3 1 0		slot-value)
(00006223 81 2 112 1 1 0		dialog-item.bcolor<-)
(00006229 10)
(0000622A 4 1 16		UpVar1-16)
(0000622D 53 1 102 3 1 32		update-host-spouse)
(00006233 10)
(00006234 5 1		UnVar1)
(00006236 63		nil->ret)
(00006237 4 1 7		UpVar1-7)
(0000623A 4 1 12		UpVar1-12)
(0000623D 9 6 1		'rgb)
(00006240 81 2 86 3 1 0		slot-value)
(00006246 5 1		UnVar1)
(00006248 53 3 18 1 1 32		color-tab-bg<-)
(0000624E 10)
(0000624F 4 1 0		UpVar1-0)
(00006252 4 1 11		UpVar1-11)
(00006255 61 12 0		nil->JMP 00006264)
(00006258 4 1 11		UpVar1-11)
(0000625B 9 47 1		'checked)
(0000625E 81 2 86 3 1 0		slot-value)
(00006264 96 2 90 100 0 0		func 0000645A)
(0000626A 12 155 3		'(24963 nil))
(0000626D 9 107 3		"VLMSG.DLL")
(00006270 51 204 91 0 0		23500)
(00006275 81 2 106 3 1 0		string-resource)
(0000627B 53 3 251 0 1 32		color-selector)
(00006281 8 12		UnVar12)
(00006283 5 12		UnVar12)
(00006285 5 17		UnVar17)
(00006287 9 6 1		'rgb)
(0000628A 81 3 78 3 1 0		slot-value<-)
(00006290 10)
(00006291 1		nil)
(00006292 1		nil)
(00006293 9 107 3		"VLMSG.DLL")
(00006296 51 214 91 0 0		23510)
(0000629B 81 2 106 3 1 0		string-resource)
(000062A1 9 103 1		':V)
(000062A4 50 2		2)
(000062A6 9 250 0		':H)
(000062A9 50 4		4)
(000062AB 51 188 0 79 0		5177532)
(000062B0 9 107 3		"VLMSG.DLL")
(000062B3 51 224 91 0 0		23520)
(000062B8 81 2 106 3 1 0		string-resource)
(000062BE 53 2 249 0 1 32		group-box)
(000062C4 9 250 0		':H)
(000062C7 51 70 255 255 255		-186)
(000062CC 9 103 1		':V)
(000062CF 50 12		12)
(000062D1 9 250 0		':H)
(000062D4 5 15		UnVar15)
(000062D6 5 16		UnVar16)
(000062D8 5 14		UnVar14)
(000062DA 57 4 0		list)
(000062DD 50 1		1)
(000062DF 5 13		UnVar13)
(000062E1 50 1		1)
(000062E3 5 12		UnVar12)
(000062E5 50 2		2)
(000062E7 9 250 0		':H)
(000062EA 50 1		1)
(000062EC 9 103 1		':V)
(000062EF 50 1		1)
(000062F1 5 19		UnVar19)
(000062F3 5 20		UnVar20)
(000062F5 57 4 0		list)
(000062F8 50 10		10)
(000062FA 9 103 1		':V)
(000062FD 50 1		1)
(000062FF 5 21		UnVar21)
(00006301 50 1		1)
(00006303 5 11		UnVar11)
(00006305 61 5 0		nil->JMP 0000630D)
(00006308 5 11		UnVar11)
(0000630A 57 1 0		list)
(0000630D 81 5 186 2 1 0		list*)
(00006313 57 5 0		list)
(00006316 57 9 0		list)
(00006319 57 3 0		list)
(0000631C 50 4		4)
(0000631E 57 5 0		list)
(00006321 50 2		2)
(00006323 9 250 0		':H)
(00006326 50 4		4)
(00006328 50 4		4)
(0000632A 9 103 1		':V)
(0000632D 50 4		4)
(0000632F 9 250 0		':H)
(00006332 5 5		UnVar5)
(00006334 50 4		4)
(00006336 9 103 1		':V)
(00006339 50 2		2)
(0000633B 5 6		UnVar6)
(0000633D 57 3 0		list)
(00006340 57 4 0		list)
(00006343 50 4		4)
(00006345 9 250 0		':H)
(00006348 5 2		UnVar2)
(0000634A 50 4		4)
(0000634C 9 103 1		':V)
(0000634F 50 2		2)
(00006351 5 3		UnVar3)
(00006353 57 3 0		list)
(00006356 57 4 0		list)
(00006359 57 5 0		list)
(0000635C 50 22		22)
(0000635E 50 60		60)
(00006360 9 103 1		':V)
(00006363 50 4		4)
(00006365 5 25		UnVar25)
(00006367 50 3		3)
(00006369 5 24		UnVar24)
(0000636B 57 5 0		list)
(0000636E 57 7 0		list)
(00006371 50 3		3)
(00006373 57 6 0		list)
(00006376 9 100 1		':FONT)
(00006379 3 248 0		*inspector-font*)
(0000637C 9 99 1		':PITCH)
(0000637F 3 247 0		*inspector-pitch*)
(00006382 9 98 1		':DEFAULT-PUSH-BUTTON)
(00006385 5 24		UnVar24)
(00006387 9 246 0		':CLOSE-BOX-COMMAND)
(0000638A 5 22		UnVar22)
(0000638C 9 245 0		':STATUS)
(0000638F 50 1		1)
(00006391 53 14 244 0 1 32		dialog-fmt)
(00006397 8 27		UnVar27)
(00006399 5 21		UnVar21)
(0000639B 51 90 0 70 0		4587610)
(000063A0 9 254 2		'size)
(000063A3 81 3 78 3 1 0		slot-value<-)
(000063A9 10)
(000063AA 5 27		UnVar27)
(000063AC 95 1 91 88 0 0		_update-winattr-dlg)
(000063B2 10)
(000063B3 5 27		UnVar27)
(000063B5 53 1 64 2 1 32		modal-dialog!!)
(000063BB 10)
(000063BC 5 26		UnVar26)
(000063BE 13 69 0		nil->JMP 00006406)
(000063C1 5 11		UnVar11)
(000063C3 13 23 0		nil->JMP 000063DD)
(000063C6 5 0		UnVar0)
(000063C8 5 11		UnVar11)
(000063CA 9 47 1		'checked)
(000063CD 81 2 86 3 1 0		slot-value)
(000063D3 9 236 2		'lex-color-p)
(000063D6 81 3 78 3 1 0		slot-value<-)
(000063DC 10)
(000063DD 5 0		UnVar0)
(000063DF 5 17		UnVar17)
(000063E1 81 2 243 0 1 0		TWin.bcolor<-)
(000063E7 10)
(000063E8 5 0		UnVar0)
(000063EA 5 18		UnVar18)
(000063EC 81 2 242 0 1 0		TWin.fcolor<-)
(000063F2 10)
(000063F3 5 0		UnVar0)
(000063F5 2		T)
(000063F6 53 2 102 3 1 32		update-host-spouse)
(000063FC 10)
(000063FD 5 0		UnVar0)
(000063FF 95 1 150 13 0 0		!wa-set-prototype)
(00006405 10)
(00006406 5 27		UnVar27)
(00006408 22		ret)
;;;def nil 25609
(00006409 20 3 3 3 0)
(0000640E 5 0		UnVar0)
(00006410 5 1		UnVar1)
(00006412 81 2 113 1 1 0		dialog-item.fcolor<-)
(00006418 10)
(00006419 5 0		UnVar0)
(0000641B 5 2		UnVar2)
(0000641D 81 2 112 1 1 0		dialog-item.bcolor<-)
(00006423 22		ret)
;;;def nil 25636
(00006424 20 1 1 1 0)
(00006429 5 0		UnVar0)
(0000642B 9 241 0		'text)
(0000642E 81 2 86 3 1 0		slot-value)
(00006434 14 19 0		T->JMP 0000644A)
(00006437 2		T)
(00006438 5 0		UnVar0)
(0000643A 9 68 2		'items)
(0000643D 81 2 86 3 1 0		slot-value)
(00006443 81 2 240 0 1 0		rassoc)
(00006449 40		car)
(0000644A 11)
(0000644B 8 0		UnVar0)
(0000644D 63		nil->ret)
(0000644E 5 0		UnVar0)
(00006450 9 120 3		':LPP)
(00006453 81 2 239 0 1 0		intern)
(00006459 22		ret)
;;;def nil 25690
(0000645A 20 3 2 2 0)
(0000645F 100 2		UNVar2)
(00006461 5 0		UnVar0)
(00006463 9 31 3		'state)
(00006466 81 2 86 3 1 0		slot-value)
(0000646C 9 248 2		':MINIMIZED)
(0000646F 38		=)
(00006470 13 15 0		nil->JMP 00006482)
(00006473 5 0		UnVar0)
(00006475 9 32 3		':NORMAL)
(00006478 9 31 3		'state)
(0000647B 81 3 78 3 1 0		slot-value<-)
(00006481 10)
(00006482 5 0		UnVar0)
(00006484 9 234 2		'color-vector)
(00006487 81 2 86 3 1 0		slot-value)
(0000648D 11)
(0000648E 8 2		UnVar2)
(00006490 13 43 0		nil->JMP 000064BE)
(00006493 5 0		UnVar0)
(00006495 5 2		UnVar2)
(00006497 3 20 1		*WT-ci*)
(0000649A 53 2 5 1 1 32		color-tab-fg)
(000064A0 81 2 242 0 1 0		TWin.fcolor<-)
(000064A6 10)
(000064A7 5 0		UnVar0)
(000064A9 5 2		UnVar2)
(000064AB 3 20 1		*WT-ci*)
(000064AE 53 2 4 1 1 32		color-tab-bg)
(000064B4 81 2 243 0 1 0		TWin.bcolor<-)
(000064BA 10)
(000064BB 15 35 0		JMP 000064E1)
(000064BE 3 20 1		*WT-ci*)
(000064C1 81 1 238 0 1 0		_twin.kern-colors)
(000064C7 8 2		UnVar2)
(000064C9 5 0		UnVar0)
(000064CB 5 2		UnVar2)
(000064CD 40		car)
(000064CE 81 2 242 0 1 0		TWin.fcolor<-)
(000064D4 10)
(000064D5 5 0		UnVar0)
(000064D7 5 2		UnVar2)
(000064D9 41		cdr)
(000064DA 81 2 243 0 1 0		TWin.bcolor<-)
(000064E0 10)
(000064E1 5 0		UnVar0)
(000064E3 81 1 132 2 1 0		TBuf.lex-scanner-id)
(000064E9 13 14 0		nil->JMP 000064FA)
(000064EC 5 0		UnVar0)
(000064EE 5 1		UnVar1)
(000064F0 9 236 2		'lex-color-p)
(000064F3 81 3 78 3 1 0		slot-value<-)
(000064F9 10)
(000064FA 5 0		UnVar0)
(000064FC 2		T)
(000064FD 47 2 102 3 32 32		update-host-spouse)
;;;def nil 25859
(00006503 20 3 1 1 0)
(00006508 100 1		UNVar1)
(0000650A 100 2		UNVar2)
(0000650C 5 0		UnVar0)
(0000650E 53 1 91 3 1 32		editorp)
(00006514 63		nil->ret)
(00006515 5 0		UnVar0)
(00006517 9 79 3		'filename)
(0000651A 81 2 86 3 1 0		slot-value)
(00006520 11)
(00006521 8 2		UnVar2)
(00006523 13 25 0		nil->JMP 0000653F)
(00006526 5 2		UnVar2)
(00006528 81 1 159 2 1 0		filename-extension)
(0000652E 14 3 0		T->JMP 00006534)
(00006531 9 41 3		"")
(00006534 9 189 2		".LSP")
(00006537 81 2 88 2 1 0		string-equal)
(0000653D 35		not)
(0000653E 22		ret)
(0000653F 2		T)
(00006540 22		ret)
;;;def !editor-coloring 25921
(00006541 20 3 0 1 0)
(00006546 100 1		UNVar1)
(00006548 100 2		UNVar2)
(0000654A 5 0		UnVar0)
(0000654C 81 1 135 3 1 0		TWinp)
(00006552 13 12 0		nil->JMP 00006561)
(00006555 5 0		UnVar0)
(00006557 81 1 37 2 1 0		mdiwindow-activate)
(0000655D 10)
(0000655E 15 8 0		JMP 00006569)
(00006561 81 0 81 1 1 0		active-mdiwindow)
(00006567 8 0		UnVar0)
(00006569 5 0		UnVar0)
(0000656B 95 1 226 101 0 0		set-color-dialog)
(00006571 11)
(00006572 8 1		UnVar1)
(00006574 63		nil->ret)
(00006575 5 1		UnVar1)
(00006577 40		car)
(00006578 8 1		UnVar1)
(0000657A 5 0		UnVar0)
(0000657C 53 1 91 3 1 32		editorp)
(00006582 61 14 0		nil->JMP 00006593)
(00006585 5 0		UnVar0)
(00006587 9 79 3		'filename)
(0000658A 81 2 86 3 1 0		slot-value)
(00006590 11)
(00006591 8 2		UnVar2)
(00006593 13 23 0		nil->JMP 000065AD)
(00006596 5 2		UnVar2)
(00006598 81 1 159 2 1 0		filename-extension)
(0000659E 14 3 0		T->JMP 000065A4)
(000065A1 9 127 1		".")
(000065A4 5 1		UnVar1)
(000065A6 53 2 237 0 1 32		set-extension-color)
(000065AC 10)
(000065AD 5 0		UnVar0)
(000065AF 9 229 2		'l-context)
(000065B2 81 2 86 3 1 0		slot-value)
(000065B8 5 1		UnVar1)
(000065BA 53 2 236 0 1 32		true-color)
(000065C0 5 0		UnVar0)
(000065C2 81 1 132 2 1 0		TBuf.lex-scanner-id)
(000065C8 38		=)
(000065C9 13 2 0		nil->JMP 000065CE)
(000065CC 1		nil)
(000065CD 22		ret)
(000065CE 5 0		UnVar0)
(000065D0 5 1		UnVar1)
(000065D2 53 2 235 0 1 32		set-window-color)
(000065D8 10)
(000065D9 5 0		UnVar0)
(000065DB 2		T)
(000065DC 47 2 102 3 32 32		update-host-spouse)
;;;def set-color-dialog 26082
(000065E2 20 16 1 1 0)
(000065E7 100 1		UNVar1)
(000065E9 100 2		UNVar2)
(000065EB 100 3		UNVar3)
(000065ED 100 4		UNVar4)
(000065EF 100 5		UNVar5)
(000065F1 100 6		UNVar6)
(000065F3 100 7		UNVar7)
(000065F5 100 8		UNVar8)
(000065F7 5 0		UnVar0)
(000065F9 53 1 91 3 1 32		editorp)
(000065FF 9 234 0		"Coloring editors only")
(00006602 53 2 17 3 1 32		assert)
(00006608 10)
(00006609 9 233 0		'_%lex-style%)
(0000660C 5 0		UnVar0)
(0000660E 81 1 132 2 1 0		TBuf.lex-scanner-id)
(00006614 24 2 0)
(00006617 5 0		UnVar0)
(00006619 9 229 2		'l-context)
(0000661C 81 2 86 3 1 0		slot-value)
(00006622 53 1 228 2 1 32		object-id)
(00006628 9 15 3		':AUTOLISP)
(0000662B 38		=)
(0000662C 8 6		UnVar6)
(0000662E 5 0		UnVar0)
(00006630 9 79 3		'filename)
(00006633 81 2 86 3 1 0		slot-value)
(00006639 11)
(0000663A 8 8		UnVar8)
(0000663C 61 8 0		nil->JMP 00006647)
(0000663F 5 8		UnVar8)
(00006641 81 1 159 2 1 0		filename-extension)
(00006647 8 7		UnVar7)
(00006649 5 6		UnVar6)
(0000664B 13 6 0		nil->JMP 00006654)
(0000664E 9 232 0		'(nil :AL :CPP :DCL :SQL))
(00006651 15 3 0		JMP 00006657)
(00006654 9 231 0		'(nil :AL :CPP :DCL :SQL :LPP T))
(00006657 8 5		UnVar5)
(00006659 9 107 3		"VLMSG.DLL")
(0000665C 51 124 71 0 0		18300)
(00006661 81 2 106 3 1 0		string-resource)
(00006667 9 107 3		"VLMSG.DLL")
(0000666A 51 123 53 0 0		13691)
(0000666F 81 2 106 3 1 0		string-resource)
(00006675 9 107 3		"VLMSG.DLL")
(00006678 51 244 91 0 0		23540)
(0000667D 81 2 106 3 1 0		string-resource)
(00006683 9 107 3		"VLMSG.DLL")
(00006686 51 254 91 0 0		23550)
(0000668B 81 2 106 3 1 0		string-resource)
(00006691 9 107 3		"VLMSG.DLL")
(00006694 51 8 92 0 0		23560)
(00006699 81 2 106 3 1 0		string-resource)
(0000669F 5 6		UnVar6)
(000066A1 13 4 0		nil->JMP 000066A8)
(000066A4 1		nil)
(000066A5 15 3 0		JMP 000066AB)
(000066A8 9 230 0		'("LISP++" "Contexted"))
(000066AB 81 6 186 2 1 0		list*)
(000066B1 8 4		UnVar4)
(000066B3 5 5		UnVar5)
(000066B5 8 9		UnVar9)
(000066B7 100 10		UNVar10)
(000066B9 15 19 0		JMP 000066CF)
(000066BC 5 9		UnVar9)
(000066BE 40		car)
(000066BF 53 1 229 0 1 32		lex-coloring-name)
(000066C5 5 10		UnVar10)
(000066C7 42		cons)
(000066C8 8 10		UnVar10)
(000066CA 5 9		UnVar9)
(000066CC 41		cdr)
(000066CD 8 9		UnVar9)
(000066CF 5 9		UnVar9)
(000066D1 60 232 255		T->JMP 000066BC)
(000066D4 5 10		UnVar10)
(000066D6 81 1 12 3 1 0		nreverse)
(000066DC 8 3		UnVar3)
(000066DE 9 107 3		"VLMSG.DLL")
(000066E1 51 18 92 0 0		23570)
(000066E6 81 2 106 3 1 0		string-resource)
(000066EC 9 233 0		'_%lex-style%)
(000066EF 9 107 3		"VLMSG.DLL")
(000066F2 51 28 92 0 0		23580)
(000066F7 81 2 106 3 1 0		string-resource)
(000066FD 5 7		UnVar7)
(000066FF 13 56 0		nil->JMP 0000673A)
(00006702 5 7		UnVar7)
(00006704 9 41 3		"")
(00006707 81 2 3 3 1 0		equal)
(0000670D 13 17 0		nil->JMP 00006721)
(00006710 9 107 3		"VLMSG.DLL")
(00006713 51 48 92 0 0		23600)
(00006718 81 2 106 3 1 0		string-resource)
(0000671E 15 22 0		JMP 00006737)
(00006721 5 7		UnVar7)
(00006723 9 107 3		"VLMSG.DLL")
(00006726 51 58 92 0 0		23610)
(0000672B 81 2 106 3 1 0		string-resource)
(00006731 81 2 75 3 1 0		concat)
(00006737 15 14 0		JMP 00006748)
(0000673A 9 107 3		"VLMSG.DLL")
(0000673D 51 38 92 0 0		23590)
(00006742 81 2 106 3 1 0		string-resource)
(00006748 81 2 75 3 1 0		concat)
(0000674E 1		nil)
(0000674F 9 228 0		':ONE-OF)
(00006752 5 5		UnVar5)
(00006754 5 4		UnVar4)
(00006756 51 80 0 12 0		786512)
(0000675B 5 3		UnVar3)
(0000675D 57 8 0		list)
(00006760 57 1 0		list)
(00006763 53 2 227 0 1 32		varslist->dialog)
(00006769 8 1		UnVar1)
(0000676B 5 6		UnVar6)
(0000676D 13 135 0		nil->JMP 000067F7)
(00006770 100 9		UNVar9)
(00006772 100 10		UNVar10)
(00006774 51 153 4 0 0		1177)
(00006779 51 154 4 0 0		1178)
(0000677E 51 155 4 0 0		1179)
(00006783 51 156 4 0 0		1180)
(00006788 51 151 4 0 0		1175)
(0000678D 51 152 4 0 0		1176)
(00006792 50 1		1)
(00006794 50 2		2)
(00006796 57 8 0		list)
(00006799 8 9		UnVar9)
(0000679B 5 1		UnVar1)
(0000679D 9 68 2		'items)
(000067A0 81 2 86 3 1 0		slot-value)
(000067A6 8 11		UnVar11)
(000067A8 5 9		UnVar9)
(000067AA 8 12		UnVar12)
(000067AC 100 13		UNVar13)
(000067AE 15 31 0		JMP 000067D0)
(000067B1 5 11		UnVar11)
(000067B3 40		car)
(000067B4 8 14		UnVar14)
(000067B6 5 12		UnVar12)
(000067B8 40		car)
(000067B9 8 15		UnVar15)
(000067BB 5 14		UnVar14)
(000067BD 40		car)
(000067BE 5 15		UnVar15)
(000067C0 42		cons)
(000067C1 5 13		UnVar13)
(000067C3 42		cons)
(000067C4 8 13		UnVar13)
(000067C6 5 11		UnVar11)
(000067C8 41		cdr)
(000067C9 8 11		UnVar11)
(000067CB 5 12		UnVar12)
(000067CD 41		cdr)
(000067CE 8 12		UnVar12)
(000067D0 5 11		UnVar11)
(000067D2 61 2 0		nil->JMP 000067D7)
(000067D5 5 12		UnVar12)
(000067D7 60 215 255		T->JMP 000067B1)
(000067DA 5 13		UnVar13)
(000067DC 81 1 12 3 1 0		nreverse)
(000067E2 8 10		UnVar10)
(000067E4 5 1		UnVar1)
(000067E6 9 66 2		"vldlg.dll")
(000067E9 51 146 0 0 0		146)
(000067EE 5 10		UnVar10)
(000067F0 53 4 65 2 1 32		dialog-update-from-res)
(000067F6 10)
(000067F7 5 1		UnVar1)
(000067F9 53 1 64 2 1 32		modal-dialog!!)
(000067FF 8 2		UnVar2)
(00006801 5 2		UnVar2)
(00006803 9 47 2		':OK)
(00006806 38		=)
(00006807 61 6 0		nil->JMP 00006810)
(0000680A 3 233 0		_%lex-style%)
(0000680D 57 1 0		list)
(00006810 25 1 0)
(00006813 22		ret)
;;;def >@editor-coloring 26644
(00006814 20 2 1 1 0)
(00006819 100 1		UNVar1)
(0000681B 81 0 81 1 1 0		active-mdiwindow)
(00006821 8 1		UnVar1)
(00006823 5 0		UnVar0)
(00006825 5 1		UnVar1)
(00006827 95 1 3 101 0 0		func 00006503)
(0000682D 35		not)
(0000682E 9 226 0		'disabled)
(00006831 81 3 78 3 1 0		slot-value<-)
(00006837 22		ret)
;;;def !edit-font 26680
(00006838 20 2 0 1 0)
(0000683D 100 1		UNVar1)
(0000683F 81 0 225 0 1 0		get-logfont)
(00006845 81 1 224 0 1 0		choose-log-font)
(0000684B 11)
(0000684C 8 1		UnVar1)
(0000684E 63		nil->ret)
(0000684F 5 1		UnVar1)
(00006851 81 1 223 0 1 0		set-logfont)
(00006857 22		ret)
;;;def nil 26712
(00006858 20 0 0 0 0)
(0000685D 1		nil)
(0000685E 1		nil)
(0000685F 9 107 3		"VLMSG.DLL")
(00006862 51 206 84 0 0		21710)
(00006867 81 2 106 3 1 0		string-resource)
(0000686D 9 250 0		':H)
(00006870 50 20		20)
(00006872 9 103 1		':V)
(00006875 50 4		4)
(00006877 9 222 0		':GROUP)
(0000687A 9 107 3		"VLMSG.DLL")
(0000687D 51 216 84 0 0		21720)
(00006882 81 2 106 3 1 0		string-resource)
(00006888 9 250 0		':H)
(0000688B 50 3		3)
(0000688D 9 103 1		':V)
(00006890 9 221 0		'*editor-make-backup*)
(00006893 9 107 3		"VLMSG.DLL")
(00006896 51 226 84 0 0		21730)
(0000689B 81 2 106 3 1 0		string-resource)
(000068A1 95 2 218 105 0 0		dio-acb)
(000068A7 50 2		2)
(000068A9 9 67 3		'*editor-backup-by-copy*)
(000068AC 9 107 3		"VLMSG.DLL")
(000068AF 51 236 84 0 0		21740)
(000068B4 81 2 106 3 1 0		string-resource)
(000068BA 95 2 218 105 0 0		dio-acb)
(000068C0 50 2		2)
(000068C2 9 220 0		'_undo-join)
(000068C5 57 1 0		list)
(000068C8 9 107 3		"VLMSG.DLL")
(000068CB 51 246 84 0 0		21750)
(000068D0 81 2 106 3 1 0		string-resource)
(000068D6 95 2 218 105 0 0		dio-acb)
(000068DC 50 2		2)
(000068DE 57 7 0		list)
(000068E1 57 3 0		list)
(000068E4 57 3 0		list)
(000068E7 50 4		4)
(000068E9 9 222 0		':GROUP)
(000068EC 9 107 3		"VLMSG.DLL")
(000068EF 51 0 85 0 0		21760)
(000068F4 81 2 106 3 1 0		string-resource)
(000068FA 9 250 0		':H)
(000068FD 50 3		3)
(000068FF 9 103 1		':V)
(00006902 9 57 3		'*desktop-save-windows*)
(00006905 9 107 3		"VLMSG.DLL")
(00006908 51 10 85 0 0		21770)
(0000690D 81 2 106 3 1 0		string-resource)
(00006913 95 2 218 105 0 0		dio-acb)
(00006919 50 2		2)
(0000691B 9 33 3		'*desktop-autosave*)
(0000691E 9 107 3		"VLMSG.DLL")
(00006921 51 20 85 0 0		21780)
(00006926 81 2 106 3 1 0		string-resource)
(0000692C 95 2 218 105 0 0		dio-acb)
(00006932 50 2		2)
(00006934 57 5 0		list)
(00006937 57 3 0		list)
(0000693A 57 3 0		list)
(0000693D 50 4		4)
(0000693F 9 107 3		"VLMSG.DLL")
(00006942 51 30 85 0 0		21790)
(00006947 81 2 106 3 1 0		string-resource)
(0000694D 9 219 0		'*protect-assign*)
(00006950 9 218 0		'(0 1 2 3))
(00006953 9 107 3		"VLMSG.DLL")
(00006956 51 40 85 0 0		21800)
(0000695B 81 2 106 3 1 0		string-resource)
(00006961 9 107 3		"VLMSG.DLL")
(00006964 51 50 85 0 0		21810)
(00006969 81 2 106 3 1 0		string-resource)
(0000696F 9 107 3		"VLMSG.DLL")
(00006972 51 60 85 0 0		21820)
(00006977 81 2 106 3 1 0		string-resource)
(0000697D 9 107 3		"VLMSG.DLL")
(00006980 51 70 85 0 0		21830)
(00006985 81 2 106 3 1 0		string-resource)
(0000698B 57 4 0		list)
(0000698E 3 217 0		*dio-acb-sz*)
(00006991 53 5 216 0 1 32		option-init-item-one-of)
(00006997 50 4		4)
(00006999 9 215 0		'*auto-switch-to-ACAD*)
(0000699C 9 107 3		"VLMSG.DLL")
(0000699F 51 80 85 0 0		21840)
(000069A4 81 2 106 3 1 0		string-resource)
(000069AA 9 107 3		"VLMSG.DLL")
(000069AD 51 90 85 0 0		21850)
(000069B2 81 2 106 3 1 0		string-resource)
(000069B8 95 3 218 105 0 0		dio-acb)
(000069BE 50 2		2)
(000069C0 57 10 0		list)
(000069C3 50 10		10)
(000069C5 57 4 0		list)
(000069C8 9 100 1		':FONT)
(000069CB 3 248 0		*inspector-font*)
(000069CE 9 99 1		':PITCH)
(000069D1 3 247 0		*inspector-pitch*)
(000069D4 47 8 244 0 32 32		dialog-fmt)
;;;def dio-acb 27098
(000069DA 20 3 1 3 0)
(000069DF 5 1		UnVar1)
(000069E1 13 3 0		nil->JMP 000069E7)
(000069E4 15 10 0		JMP 000069F1)
(000069E7 5 0		UnVar0)
(000069E9 81 1 16 1 1 0		symbol-name)
(000069EF 8 1		UnVar1)
(000069F1 5 2		UnVar2)
(000069F3 13 3 0		nil->JMP 000069F9)
(000069F6 15 4 0		JMP 000069FD)
(000069F9 5 1		UnVar1)
(000069FB 8 2		UnVar2)
(000069FD 3 217 0		*dio-acb-sz*)
(00006A00 5 0		UnVar0)
(00006A02 1		nil)
(00006A03 5 1		UnVar1)
(00006A05 5 2		UnVar2)
(00006A07 47 5 214 0 32 32		accessed-check-box)
;;;def nil 27149
(00006A0D 20 0 0 0 0)
(00006A12 1		nil)
(00006A13 1		nil)
(00006A14 9 107 3		"VLMSG.DLL")
(00006A17 51 100 85 0 0		21860)
(00006A1C 81 2 106 3 1 0		string-resource)
(00006A22 9 250 0		':H)
(00006A25 50 30		30)
(00006A27 9 213 0		':VC)
(00006A2A 50 2		2)
(00006A2C 9 103 1		':V)
(00006A2F 50 25		25)
(00006A31 9 212 0		'*al-check-warning*)
(00006A34 9 107 3		"VLMSG.DLL")
(00006A37 51 110 85 0 0		21870)
(00006A3C 81 2 106 3 1 0		string-resource)
(00006A42 9 107 3		"VLMSG.DLL")
(00006A45 51 120 85 0 0		21880)
(00006A4A 81 2 106 3 1 0		string-resource)
(00006A50 95 3 218 105 0 0		dio-acb)
(00006A56 50 3		3)
(00006A58 9 204 2		'*load-print*)
(00006A5B 9 107 3		"VLMSG.DLL")
(00006A5E 51 130 85 0 0		21890)
(00006A63 81 2 106 3 1 0		string-resource)
(00006A69 9 107 3		"VLMSG.DLL")
(00006A6C 51 140 85 0 0		21900)
(00006A71 81 2 106 3 1 0		string-resource)
(00006A77 95 3 218 105 0 0		dio-acb)
(00006A7D 50 3		3)
(00006A7F 9 200 2		'*load-verbose*)
(00006A82 9 107 3		"VLMSG.DLL")
(00006A85 51 150 85 0 0		21910)
(00006A8A 81 2 106 3 1 0		string-resource)
(00006A90 1		nil)
(00006A91 95 3 218 105 0 0		dio-acb)
(00006A97 50 3		3)
(00006A99 9 211 0		'*prin-echo-ACAD*)
(00006A9C 9 107 3		"VLMSG.DLL")
(00006A9F 51 160 85 0 0		21920)
(00006AA4 81 2 106 3 1 0		string-resource)
(00006AAA 9 107 3		"VLMSG.DLL")
(00006AAD 51 170 85 0 0		21930)
(00006AB2 81 2 106 3 1 0		string-resource)
(00006AB8 95 3 218 105 0 0		dio-acb)
(00006ABE 50 3		3)
(00006AC0 9 210 0		'*ACAD-INSPECT-VERBOSE*)
(00006AC3 9 107 3		"VLMSG.DLL")
(00006AC6 51 180 85 0 0		21940)
(00006ACB 81 2 106 3 1 0		string-resource)
(00006AD1 9 107 3		"VLMSG.DLL")
(00006AD4 51 190 85 0 0		21950)
(00006AD9 81 2 106 3 1 0		string-resource)
(00006ADF 95 3 218 105 0 0		dio-acb)
(00006AE5 50 3		3)
(00006AE7 9 209 0		'*SDB-SKIP-TOP-LEVEL*)
(00006AEA 9 107 3		"VLMSG.DLL")
(00006AED 51 200 85 0 0		21960)
(00006AF2 81 2 106 3 1 0		string-resource)
(00006AF8 9 107 3		"VLMSG.DLL")
(00006AFB 51 210 85 0 0		21970)
(00006B00 81 2 106 3 1 0		string-resource)
(00006B06 95 3 218 105 0 0		dio-acb)
(00006B0C 50 3		3)
(00006B0E 9 250 0		':H)
(00006B11 50 12		12)
(00006B13 51 80 0 12 0		786512)
(00006B18 9 107 3		"VLMSG.DLL")
(00006B1B 51 220 85 0 0		21980)
(00006B20 81 2 106 3 1 0		string-resource)
(00006B26 53 2 13 1 1 32		static-text)
(00006B2C 50 5		5)
(00006B2E 9 208 0		'*SDB-ANIMATE-DELAY*)
(00006B31 9 33 2		'fixnump)
(00006B34 9 107 3		"VLMSG.DLL")
(00006B37 51 230 85 0 0		21990)
(00006B3C 81 2 106 3 1 0		string-resource)
(00006B42 9 107 3		"VLMSG.DLL")
(00006B45 51 240 85 0 0		22000)
(00006B4A 81 2 106 3 1 0		string-resource)
(00006B50 51 35 0 12 0		786467)
(00006B55 9 107 3		"VLMSG.DLL")
(00006B58 51 250 85 0 0		22010)
(00006B5D 81 2 106 3 1 0		string-resource)
(00006B63 53 6 207 0 1 32		accessed-checked-value-item)
(00006B69 57 5 0		list)
(00006B6C 57 15 0		list)
(00006B6F 50 30		30)
(00006B71 57 4 0		list)
(00006B74 50 30		30)
(00006B76 57 4 0		list)
(00006B79 9 100 1		':FONT)
(00006B7C 3 248 0		*inspector-font*)
(00006B7F 9 99 1		':PITCH)
(00006B82 3 247 0		*inspector-pitch*)
(00006B85 9 245 0		':STATUS)
(00006B88 50 1		1)
(00006B8A 47 10 244 0 32 32		dialog-fmt)
;;;def general-options! 27536
(00006B90 20 8 0 1 0)
(00006B95 3 206 0		*general-options-dialog*)
(00006B98 13 35 0		nil->JMP 00006BBE)
(00006B9B 3 206 0		*general-options-dialog*)
(00006B9E 40		car)
(00006B9F 4 1 0		UpVar1-0)
(00006BA2 9 254 2		'size)
(00006BA5 81 3 78 3 1 0		slot-value<-)
(00006BAB 10)
(00006BAC 3 206 0		*general-options-dialog*)
(00006BAF 41		cdr)
(00006BB0 40		car)
(00006BB1 4 1 1		UpVar1-1)
(00006BB4 9 254 2		'size)
(00006BB7 81 3 78 3 1 0		slot-value<-)
(00006BBD 10)
(00006BBE 95 0 88 104 0 0		func 00006858)
(00006BC4 95 0 13 106 0 0		func 00006A0D)
(00006BCA 57 2 0		list)
(00006BCD 6 206 0		*general-options-dialog*)
(00006BD0 3 206 0		*general-options-dialog*)
(00006BD3 40		car)
(00006BD4 9 254 2		'size)
(00006BD7 81 2 86 3 1 0		slot-value)
(00006BDD 7 1 0		UpVar1-0)
(00006BE0 3 206 0		*general-options-dialog*)
(00006BE3 41		cdr)
(00006BE4 40		car)
(00006BE5 9 254 2		'size)
(00006BE8 81 2 86 3 1 0		slot-value)
(00006BEE 7 1 1		UpVar1-1)
(00006BF1 100 1		UNVar1)
(00006BF3 100 2		UNVar2)
(00006BF5 51 22 4 0 0		1046)
(00006BFA 51 23 4 0 0		1047)
(00006BFF 51 24 4 0 0		1048)
(00006C04 51 21 4 0 0		1045)
(00006C09 51 25 4 0 0		1049)
(00006C0E 51 26 4 0 0		1050)
(00006C13 51 188 4 0 0		1212)
(00006C18 51 28 4 0 0		1052)
(00006C1D 51 29 4 0 0		1053)
(00006C22 51 30 4 0 0		1054)
(00006C27 51 31 4 0 0		1055)
(00006C2C 51 189 4 0 0		1213)
(00006C31 51 27 4 0 0		1051)
(00006C36 57 13 0		list)
(00006C39 8 1		UnVar1)
(00006C3B 3 206 0		*general-options-dialog*)
(00006C3E 40		car)
(00006C3F 9 68 2		'items)
(00006C42 81 2 86 3 1 0		slot-value)
(00006C48 8 3		UnVar3)
(00006C4A 5 1		UnVar1)
(00006C4C 8 4		UnVar4)
(00006C4E 100 5		UNVar5)
(00006C50 15 31 0		JMP 00006C72)
(00006C53 5 3		UnVar3)
(00006C55 40		car)
(00006C56 8 6		UnVar6)
(00006C58 5 4		UnVar4)
(00006C5A 40		car)
(00006C5B 8 7		UnVar7)
(00006C5D 5 6		UnVar6)
(00006C5F 40		car)
(00006C60 5 7		UnVar7)
(00006C62 42		cons)
(00006C63 5 5		UnVar5)
(00006C65 42		cons)
(00006C66 8 5		UnVar5)
(00006C68 5 3		UnVar3)
(00006C6A 41		cdr)
(00006C6B 8 3		UnVar3)
(00006C6D 5 4		UnVar4)
(00006C6F 41		cdr)
(00006C70 8 4		UnVar4)
(00006C72 5 3		UnVar3)
(00006C74 61 2 0		nil->JMP 00006C79)
(00006C77 5 4		UnVar4)
(00006C79 60 215 255		T->JMP 00006C53)
(00006C7C 5 5		UnVar5)
(00006C7E 81 1 12 3 1 0		nreverse)
(00006C84 8 2		UnVar2)
(00006C86 3 206 0		*general-options-dialog*)
(00006C89 40		car)
(00006C8A 9 66 2		"vldlg.dll")
(00006C8D 50 114		114)
(00006C8F 5 2		UnVar2)
(00006C91 53 4 65 2 1 32		dialog-update-from-res)
(00006C97 10)
(00006C98 51 32 4 0 0		1056)
(00006C9D 51 33 4 0 0		1057)
(00006CA2 51 34 4 0 0		1058)
(00006CA7 51 35 4 0 0		1059)
(00006CAC 51 36 4 0 0		1060)
(00006CB1 51 37 4 0 0		1061)
(00006CB6 51 191 4 0 0		1215)
(00006CBB 51 192 4 0 0		1216)
(00006CC0 51 193 4 0 0		1217)
(00006CC5 57 9 0		list)
(00006CC8 8 1		UnVar1)
(00006CCA 3 206 0		*general-options-dialog*)
(00006CCD 41		cdr)
(00006CCE 40		car)
(00006CCF 9 68 2		'items)
(00006CD2 81 2 86 3 1 0		slot-value)
(00006CD8 8 3		UnVar3)
(00006CDA 5 1		UnVar1)
(00006CDC 8 4		UnVar4)
(00006CDE 100 5		UNVar5)
(00006CE0 15 31 0		JMP 00006D02)
(00006CE3 5 3		UnVar3)
(00006CE5 40		car)
(00006CE6 8 6		UnVar6)
(00006CE8 5 4		UnVar4)
(00006CEA 40		car)
(00006CEB 8 7		UnVar7)
(00006CED 5 6		UnVar6)
(00006CEF 40		car)
(00006CF0 5 7		UnVar7)
(00006CF2 42		cons)
(00006CF3 5 5		UnVar5)
(00006CF5 42		cons)
(00006CF6 8 5		UnVar5)
(00006CF8 5 3		UnVar3)
(00006CFA 41		cdr)
(00006CFB 8 3		UnVar3)
(00006CFD 5 4		UnVar4)
(00006CFF 41		cdr)
(00006D00 8 4		UnVar4)
(00006D02 5 3		UnVar3)
(00006D04 61 2 0		nil->JMP 00006D09)
(00006D07 5 4		UnVar4)
(00006D09 60 215 255		T->JMP 00006CE3)
(00006D0C 5 5		UnVar5)
(00006D0E 81 1 12 3 1 0		nreverse)
(00006D14 8 2		UnVar2)
(00006D16 3 206 0		*general-options-dialog*)
(00006D19 41		cdr)
(00006D1A 40		car)
(00006D1B 9 66 2		"vldlg.dll")
(00006D1E 50 115		115)
(00006D20 5 2		UnVar2)
(00006D22 53 4 65 2 1 32		dialog-update-from-res)
(00006D28 10)
(00006D29 3 206 0		*general-options-dialog*)
(00006D2C 9 163 2		':CAPTION)
(00006D2F 9 107 3		"VLMSG.DLL")
(00006D32 51 4 86 0 0		22020)
(00006D37 81 2 106 3 1 0		string-resource)
(00006D3D 47 3 205 0 32 32		modal-dialog-sheet!!)
;;;def clip-bmp-pos 27971
(00006D43 20 4 2 4 0)
(00006D48 5 2		UnVar2)
(00006D4A 14 3 0		T->JMP 00006D50)
(00006D4D 3 204 0		*btn-wid*)
(00006D50 8 2		UnVar2)
(00006D52 5 3		UnVar3)
(00006D54 14 3 0		T->JMP 00006D5A)
(00006D57 3 203 0		*btn-ht*)
(00006D5A 8 3		UnVar3)
(00006D5C 5 2		UnVar2)
(00006D5E 5 1		UnVar1)
(00006D60 72		*)
(00006D61 5 3		UnVar3)
(00006D63 5 0		UnVar0)
(00006D65 72		*)
(00006D66 81 2 249 2 1 0		make-ipoint)
(00006D6C 22		ret)
;;;def clip-bmp-pos16 28013
(00006D6D 20 4 2 4 0)
(00006D72 5 2		UnVar2)
(00006D74 14 3 0		T->JMP 00006D7A)
(00006D77 3 202 0		*btn-wid16*)
(00006D7A 8 2		UnVar2)
(00006D7C 5 3		UnVar3)
(00006D7E 14 3 0		T->JMP 00006D84)
(00006D81 3 201 0		*btn-ht16*)
(00006D84 8 3		UnVar3)
(00006D86 5 2		UnVar2)
(00006D88 5 1		UnVar1)
(00006D8A 72		*)
(00006D8B 5 3		UnVar3)
(00006D8D 5 0		UnVar0)
(00006D8F 72		*)
(00006D90 81 2 249 2 1 0		make-ipoint)
(00006D96 22		ret)
;;;def source-pos-status 28055
(00006D97 20 2 1 1 0)
(00006D9C 5 0		UnVar0)
(00006D9E 81 1 33 2 1 0		fixnump)
(00006DA4 13 3 0		nil->JMP 00006DAA)
(00006DA7 15 50 0		JMP 00006DDC)
(00006DAA 5 0		UnVar0)
(00006DAC 8 1		UnVar1)
(00006DAE 5 1		UnVar1)
(00006DB0 9 200 0		':BEFORE)
(00006DB3 38		=)
(00006DB4 13 5 0		nil->JMP 00006DBC)
(00006DB7 50 1		1)
(00006DB9 15 30 0		JMP 00006DDA)
(00006DBC 5 1		UnVar1)
(00006DBE 9 199 0		':INSIDE)
(00006DC1 38		=)
(00006DC2 13 5 0		nil->JMP 00006DCA)
(00006DC5 50 2		2)
(00006DC7 15 16 0		JMP 00006DDA)
(00006DCA 5 1		UnVar1)
(00006DCC 9 198 0		':AFTER)
(00006DCF 38		=)
(00006DD0 13 5 0		nil->JMP 00006DD8)
(00006DD3 50 3		3)
(00006DD5 15 2 0		JMP 00006DDA)
(00006DD8 50 0		0)
(00006DDA 8 0		UnVar0)
(00006DDC 3 197 0		*bpt-status*)
(00006DDF 5 0		UnVar0)
(00006DE1 81 2 196 0 1 0		bitmap-push-button.state<-)
(00006DE7 10)
(00006DE8 3 195 0		*sdb-toolbar-dlg*)
(00006DEB 53 1 194 0 1 32		dialogp)
(00006DF1 63		nil->ret)
(00006DF2 3 197 0		*bpt-status*)
(00006DF5 3 195 0		*sdb-toolbar-dlg*)
(00006DF8 81 2 193 0 1 0		bitmap-push-button._redraw)
(00006DFE 22		ret)
;;;def nil 28159
(00006DFF 20 1 0 1 0)
(00006E04 3 205 2		*active-mdiwindow*)
(00006E07 81 1 192 0 1 0		TBuf.can-undo-p)
(00006E0D 13 10 0		nil->JMP 00006E1A)
(00006E10 3 205 2		*active-mdiwindow*)
(00006E13 81 1 191 0 1 0		TBuf.undo)
(00006E19 22		ret)
(00006E1A 81 0 206 2 1 0		message-beep)
(00006E20 22		ret)
;;;def nil 28193
(00006E21 20 1 0 1 0)
(00006E26 3 205 2		*active-mdiwindow*)
(00006E29 81 1 190 0 1 0		TBuf.can-redo-p)
(00006E2F 13 10 0		nil->JMP 00006E3C)
(00006E32 3 205 2		*active-mdiwindow*)
(00006E35 81 1 189 0 1 0		TBuf.redo)
(00006E3B 22		ret)
(00006E3C 81 0 206 2 1 0		message-beep)
(00006E42 22		ret)
;;;def nil 28227
(00006E43 20 1 1 1 0)
(00006E48 3 205 2		*active-mdiwindow*)
(00006E4B 47 1 188 0 32 32		apropos!)
;;;def nil 28241
(00006E51 20 1 1 1 0)
(00006E56 3 205 2		*active-mdiwindow*)
(00006E59 47 1 187 0 32 32		inspect-trace-stack!)
;;;def nil 28255
(00006E5F 20 1 1 1 0)
(00006E64 3 205 2		*active-mdiwindow*)
(00006E67 96 1 22 67 0 0		help-lisp!)
;;;def nil 28269
(00006E6D 20 1 1 1 0)
(00006E72 3 205 2		*active-mdiwindow*)
(00006E75 8 0		UnVar0)
(00006E77 9 83 3		'save!)
(00006E7A 5 0		UnVar0)
(00006E7C 81 2 186 0 1 0		compute-applicable-methods)
(00006E82 13 8 0		nil->JMP 00006E8D)
(00006E85 5 0		UnVar0)
(00006E87 47 1 83 3 32 32		save!)
(00006E8D 3 207 2		*stop-beep*)
(00006E90 81 1 206 2 1 0		message-beep)
(00006E96 22		ret)
;;;def nil 28311
(00006E97 20 1 1 1 0)
(00006E9C 5 0		UnVar0)
(00006E9E 81 1 185 0 1 0		edit-cut!)
(00006EA4 62		T->ret)
(00006EA5 3 207 2		*stop-beep*)
(00006EA8 81 1 206 2 1 0		message-beep)
(00006EAE 22		ret)
;;;def nil 28335
(00006EAF 20 1 1 1 0)
(00006EB4 5 0		UnVar0)
(00006EB6 81 1 184 0 1 0		edit-copy!)
(00006EBC 62		T->ret)
(00006EBD 3 207 2		*stop-beep*)
(00006EC0 81 1 206 2 1 0		message-beep)
(00006EC6 22		ret)
;;;def nil 28359
(00006EC7 20 1 1 1 0)
(00006ECC 5 0		UnVar0)
(00006ECE 81 1 183 0 1 0		edit-paste!)
(00006ED4 62		T->ret)
(00006ED5 3 207 2		*stop-beep*)
(00006ED8 81 1 206 2 1 0		message-beep)
(00006EDE 22		ret)
;;;def nil 28383
(00006EDF 20 1 1 1 0)
(00006EE4 81 0 148 2 1 0		in-ads-check)
(00006EEA 13 8 0		nil->JMP 00006EF5)
(00006EED 5 0		UnVar0)
(00006EEF 47 1 182 0 32 32		ACAD!)
(00006EF5 3 207 2		*stop-beep*)
(00006EF8 81 1 206 2 1 0		message-beep)
(00006EFE 22		ret)
;;;def sep-bmp-pb 28415
(00006EFF 20 3 2 2 0)
(00006F04 100 2		UNVar2)
(00006F06 3 181 0		*carp-res0*)
(00006F09 5 0		UnVar0)
(00006F0B 5 1		UnVar1)
(00006F0D 9 180 0		'identity)
(00006F10 9 41 3		"")
(00006F13 53 5 179 0 1 32		bmp-push-button)
(00006F19 8 2		UnVar2)
(00006F1B 5 2		UnVar2)
(00006F1D 3 178 0		WS_DISABLED)
(00006F20 53 2 177 0 1 32		dialog-item.disable<-)
(00006F26 10)
(00006F27 5 2		UnVar2)
(00006F29 22		ret)
;;;def !editor-insert-file 28458
(00006F2A 20 4 1 1 0)
(00006F2F 100 1		UNVar1)
(00006F31 100 2		UNVar2)
(00006F33 100 3		UNVar3)
(00006F35 5 0		UnVar0)
(00006F37 81 1 167 2 1 0		TWin.cpos)
(00006F3D 8 3		UnVar3)
(00006F3F 5 0		UnVar0)
(00006F41 5 3		UnVar3)
(00006F43 81 2 101 2 1 0		TBuf.editablep)
(00006F49 13 168 0		nil->JMP 00006FF4)
(00006F4C 5 0		UnVar0)
(00006F4E 53 1 191 2 1 32		ed-dflt-dir?)
(00006F54 14 6 0		T->JMP 00006F5D)
(00006F57 81 0 49 3 1 0		chdir)
(00006F5D 9 107 3		"VLMSG.DLL")
(00006F60 51 118 82 0 0		21110)
(00006F65 81 2 106 3 1 0		string-resource)
(00006F6B 5 0		UnVar0)
(00006F6D 53 1 91 3 1 32		editorp)
(00006F73 61 14 0		nil->JMP 00006F84)
(00006F76 5 0		UnVar0)
(00006F78 9 79 3		'filename)
(00006F7B 81 2 86 3 1 0		slot-value)
(00006F81 11)
(00006F82 8 1		UnVar1)
(00006F84 61 8 0		nil->JMP 00006F8F)
(00006F87 5 1		UnVar1)
(00006F89 81 1 159 2 1 0		filename-extension)
(00006F8F 2		T)
(00006F90 3 176 0		*OFN-INSERT-FILE*)
(00006F93 53 5 158 2 1 32		choose-editor-file-dialog)
(00006F99 11)
(00006F9A 8 2		UnVar2)
(00006F9C 13 83 0		nil->JMP 00006FF2)
(00006F9F 5 2		UnVar2)
(00006FA1 37 2		consp)
(00006FA3 13 5 0		nil->JMP 00006FAB)
(00006FA6 5 2		UnVar2)
(00006FA8 40		car)
(00006FA9 8 2		UnVar2)
(00006FAB 5 0		UnVar0)
(00006FAD 5 3		UnVar3)
(00006FAF 1		nil)
(00006FB0 81 3 208 2 1 0		TWin.cpos<-)
(00006FB6 10)
(00006FB7 5 0		UnVar0)
(00006FB9 5 2		UnVar2)
(00006FBB 5 3		UnVar3)
(00006FBD 81 3 246 1 1 0		TBuf.insert-file)
(00006FC3 13 19 0		nil->JMP 00006FD9)
(00006FC6 5 0		UnVar0)
(00006FC8 5 3		UnVar3)
(00006FCA 5 0		UnVar0)
(00006FCC 81 1 167 2 1 0		TWin.cpos)
(00006FD2 42		cons)
(00006FD3 47 2 133 2 32 32		selection<-)
(00006FD9 3 92 1		*error-alert*)
(00006FDC 9 107 3		"VLMSG.DLL")
(00006FDF 51 128 82 0 0		21120)
(00006FE4 81 2 106 3 1 0		string-resource)
(00006FEA 5 2		UnVar2)
(00006FEC 47 3 85 3 32 32		alert)
(00006FF2 1		nil)
(00006FF3 22		ret)
(00006FF4 3 207 2		*stop-beep*)
(00006FF7 81 1 206 2 1 0		message-beep)
(00006FFD 22		ret)
;;;def !editor-write-block 28670
(00006FFE 20 1 1 1 0)
(00007003 81 0 150 2 1 0		_vill-demo-p)
(00007009 13 20 0		nil->JMP 00007020)
(0000700C 9 107 3		"VLMSG.DLL")
(0000700F 51 138 82 0 0		21130)
(00007014 81 2 106 3 1 0		string-resource)
(0000701A 47 1 149 2 32 32		_demov-nocmd)
(00007020 5 0		UnVar0)
(00007022 5 0		UnVar0)
(00007024 53 1 217 2 1 32		selection)
(0000702A 96 2 48 112 0 0		func 00007030)
;;;def nil 28720
(00007030 20 6 2 2 0)
(00007035 100 2		UNVar2)
(00007037 100 3		UNVar3)
(00007039 100 4		UNVar4)
(0000703B 5 1		UnVar1)
(0000703D 40		car)
(0000703E 5 1		UnVar1)
(00007040 41		cdr)
(00007041 38		=)
(00007042 13 10 0		nil->JMP 0000704F)
(00007045 3 207 2		*stop-beep*)
(00007048 81 1 206 2 1 0		message-beep)
(0000704E 22		ret)
(0000704F 5 0		UnVar0)
(00007051 53 1 191 2 1 32		ed-dflt-dir?)
(00007057 14 6 0		T->JMP 00007060)
(0000705A 81 0 49 3 1 0		chdir)
(00007060 9 107 3		"VLMSG.DLL")
(00007063 51 148 82 0 0		21140)
(00007068 81 2 106 3 1 0		string-resource)
(0000706E 5 0		UnVar0)
(00007070 53 1 91 3 1 32		editorp)
(00007076 61 14 0		nil->JMP 00007087)
(00007079 5 0		UnVar0)
(0000707B 9 79 3		'filename)
(0000707E 81 2 86 3 1 0		slot-value)
(00007084 11)
(00007085 8 2		UnVar2)
(00007087 61 8 0		nil->JMP 00007092)
(0000708A 5 2		UnVar2)
(0000708C 81 1 159 2 1 0		filename-extension)
(00007092 1		nil)
(00007093 3 175 0		OFN_PATHMUSTEXIST)
(00007096 3 174 0		OFN_HIDEREADONLY)
(00007099 3 173 0		OFN_NOCHANGEDIR)
(0000709C 81 3 115 1 1 0		logior)
(000070A2 53 5 158 2 1 32		choose-editor-file-dialog)
(000070A8 8 4		UnVar4)
(000070AA 5 4		UnVar4)
(000070AC 13 77 0		nil->JMP 000070FC)
(000070AF 5 4		UnVar4)
(000070B1 53 1 172 0 1 32		_filename4save)
(000070B7 8 4		UnVar4)
(000070B9 5 4		UnVar4)
(000070BB 81 1 100 3 1 0		file-readable-p)
(000070C1 13 56 0		nil->JMP 000070FC)
(000070C4 3 88 3		*yes-no-cancel-alert*)
(000070C7 9 107 3		"VLMSG.DLL")
(000070CA 51 158 82 0 0		21150)
(000070CF 81 2 106 3 1 0		string-resource)
(000070D5 5 4		UnVar4)
(000070D7 53 3 85 3 1 32		alert)
(000070DD 8 5		UnVar5)
(000070DF 5 5		UnVar5)
(000070E1 9 84 3		':YES)
(000070E4 38		=)
(000070E5 13 6 0		nil->JMP 000070EE)
(000070E8 2		T)
(000070E9 8 3		UnVar3)
(000070EB 15 14 0		JMP 000070FC)
(000070EE 5 5		UnVar5)
(000070F0 9 72 3		':CANCEL)
(000070F3 38		=)
(000070F4 13 5 0		nil->JMP 000070FC)
(000070F7 100 4		UNVar4)
(000070F9 15 0 0		JMP 000070FC)
(000070FC 5 4		UnVar4)
(000070FE 13 57 0		nil->JMP 0000713A)
(00007101 5 0		UnVar0)
(00007103 5 4		UnVar4)
(00007105 5 1		UnVar1)
(00007107 40		car)
(00007108 5 1		UnVar1)
(0000710A 41		cdr)
(0000710B 5 3		UnVar3)
(0000710D 81 5 11 2 1 0		TBuf.write-region)
(00007113 13 11 0		nil->JMP 00007121)
(00007116 5 0		UnVar0)
(00007118 1		nil)
(00007119 1		nil)
(0000711A 81 3 208 2 1 0		TWin.cpos<-)
(00007120 22		ret)
(00007121 3 92 1		*error-alert*)
(00007124 9 107 3		"VLMSG.DLL")
(00007127 51 168 82 0 0		21160)
(0000712C 81 2 106 3 1 0		string-resource)
(00007132 5 4		UnVar4)
(00007134 47 3 85 3 32 32		alert)
(0000713A 1		nil)
(0000713B 22		ret)
;;;def !editor-indent-block 28988
(0000713C 20 12 1 2 0)
(00007141 100 2		UNVar2)
(00007143 100 3		UNVar3)
(00007145 100 4		UNVar4)
(00007147 100 5		UNVar5)
(00007149 100 6		UNVar6)
(0000714B 100 7		UNVar7)
(0000714D 100 8		UNVar8)
(0000714F 5 0		UnVar0)
(00007151 81 1 135 3 1 0		TWinp)
(00007157 13 3 0		nil->JMP 0000715D)
(0000715A 15 5 0		JMP 00007162)
(0000715D 3 205 2		*active-mdiwindow*)
(00007160 8 0		UnVar0)
(00007162 5 0		UnVar0)
(00007164 8 8		UnVar8)
(00007166 5 8		UnVar8)
(00007168 81 1 30 2 1 0		TWin.sel)
(0000716E 8 7		UnVar7)
(00007170 5 8		UnVar8)
(00007172 81 1 167 2 1 0		TWin.cpos)
(00007178 8 2		UnVar2)
(0000717A 5 7		UnVar7)
(0000717C 53 1 212 2 1 32		seat)
(00007182 40		car)
(00007183 14 2 0		T->JMP 00007188)
(00007186 5 2		UnVar2)
(00007188 8 6		UnVar6)
(0000718A 5 7		UnVar7)
(0000718C 53 1 212 2 1 32		seat)
(00007192 41		cdr)
(00007193 14 2 0		T->JMP 00007198)
(00007196 5 2		UnVar2)
(00007198 8 5		UnVar5)
(0000719A 5 0		UnVar0)
(0000719C 5 0		UnVar0)
(0000719E 5 6		UnVar6)
(000071A0 81 2 99 2 1 0		TBuf.BOL-pos)
(000071A6 81 2 101 2 1 0		TBuf.editablep)
(000071AC 13 141 1		nil->JMP 0000733C)
(000071AF 5 1		UnVar1)
(000071B1 13 3 0		nil->JMP 000071B7)
(000071B4 15 25 0		JMP 000071D0)
(000071B7 9 107 3		"VLMSG.DLL")
(000071BA 51 178 82 0 0		21170)
(000071BF 81 2 106 3 1 0		string-resource)
(000071C5 3 171 0		*last-indent-block-string*)
(000071C8 81 2 184 1 1 0		get-string-dialog)
(000071CE 8 1		UnVar1)
(000071D0 5 1		UnVar1)
(000071D2 13 14 0		nil->JMP 000071E3)
(000071D5 5 1		UnVar1)
(000071D7 9 41 3		"")
(000071DA 81 2 3 3 1 0		equal)
(000071E0 15 1 0		JMP 000071E4)
(000071E3 2		T)
(000071E4 62		T->ret)
(000071E5 5 1		UnVar1)
(000071E7 6 171 0		*last-indent-block-string*)
(000071EA 5 2		UnVar2)
(000071EC 5 6		UnVar6)
(000071EE 81 2 113 2 1 0		=&)
(000071F4 8 2		UnVar2)
(000071F6 5 8		UnVar8)
(000071F8 81 1 203 1 1 0		TWin.TBuf)
(000071FE 8 0		UnVar0)
(00007200 9 45 2		':OWNER)
(00007203 5 0		UnVar0)
(00007205 9 44 2		':SEAT)
(00007208 5 6		UnVar6)
(0000720A 9 202 1		':EXCL)
(0000720D 2		T)
(0000720E 53 6 43 2 1 32		tmark)
(00007214 8 4		UnVar4)
(00007216 5 0		UnVar0)
(00007218 5 6		UnVar6)
(0000721A 81 2 99 2 1 0		TBuf.BOL-pos)
(00007220 8 6		UnVar6)
(00007222 9 45 2		':OWNER)
(00007225 5 0		UnVar0)
(00007227 9 44 2		':SEAT)
(0000722A 5 6		UnVar6)
(0000722C 5 5		UnVar5)
(0000722E 38		=)
(0000722F 13 13 0		nil->JMP 0000723F)
(00007232 5 0		UnVar0)
(00007234 5 5		UnVar5)
(00007236 81 2 121 2 1 0		TBuf.next-pos)
(0000723C 15 2 0		JMP 00007241)
(0000723F 5 5		UnVar5)
(00007241 9 202 1		':EXCL)
(00007244 1		nil)
(00007245 53 6 43 2 1 32		tmark)
(0000724B 8 5		UnVar5)
(0000724D 5 1		UnVar1)
(0000724F 81 1 170 0 1 0		string->list)
(00007255 8 9		UnVar9)
(00007257 100 10		UNVar10)
(00007259 2		T)
(0000725A 8 10		UnVar10)
(0000725C 15 5 0		JMP 00007264)
(0000725F 5 9		UnVar9)
(00007261 41		cdr)
(00007262 8 9		UnVar9)
(00007264 5 9		UnVar9)
(00007266 61 19 0		nil->JMP 0000727C)
(00007269 5 9		UnVar9)
(0000726B 40		car)
(0000726C 8 11		UnVar11)
(0000726E 5 11		UnVar11)
(00007270 9 169 0		'(32 9))
(00007273 81 2 114 3 1 0		memq)
(00007279 11)
(0000727A 8 10		UnVar10)
(0000727C 60 224 255		T->JMP 0000725F)
(0000727F 5 10		UnVar10)
(00007281 8 3		UnVar3)
(00007283 5 0		UnVar0)
(00007285 81 1 42 2 1 0		TBuf.undo-sta)
(0000728B 10)
(0000728C 5 8		UnVar8)
(0000728E 9 236 2		'lex-color-p)
(00007291 81 2 168 0 1 0		slot-value&)
(00007297 1		nil)
(00007298 24 2 0)
(0000729B 15 55 0		JMP 000072D5)
(0000729E 5 3		UnVar3)
(000072A0 61 10 0		nil->JMP 000072AD)
(000072A3 5 0		UnVar0)
(000072A5 5 6		UnVar6)
(000072A7 81 2 98 2 1 0		TBuf.EOL-pos-p)
(000072AD 13 3 0		nil->JMP 000072B3)
(000072B0 15 14 0		JMP 000072C1)
(000072B3 5 0		UnVar0)
(000072B5 5 6		UnVar6)
(000072B7 5 1		UnVar1)
(000072B9 81 3 80 3 1 0		TBuf.insert)
(000072BF 8 6		UnVar6)
(000072C1 5 0		UnVar0)
(000072C3 5 0		UnVar0)
(000072C5 5 6		UnVar6)
(000072C7 81 2 128 2 1 0		TBuf.EOL-pos)
(000072CD 81 2 121 2 1 0		TBuf.next-pos)
(000072D3 8 6		UnVar6)
(000072D5 5 6		UnVar6)
(000072D7 5 5		UnVar5)
(000072D9 53 1 212 2 1 32		seat)
(000072DF 76		<)
(000072E0 60 187 255		T->JMP 0000729E)
(000072E3 25 1 0)
(000072E6 5 0		UnVar0)
(000072E8 81 1 41 2 1 0		TBuf.undo-end)
(000072EE 10)
(000072EF 5 7		UnVar7)
(000072F1 53 1 212 2 1 32		seat)
(000072F7 11)
(000072F8 8 1		UnVar1)
(000072FA 13 21 0		nil->JMP 00007312)
(000072FD 5 7		UnVar7)
(000072FF 5 4		UnVar4)
(00007301 53 1 212 2 1 32		seat)
(00007307 5 1		UnVar1)
(00007309 41		cdr)
(0000730A 42		cons)
(0000730B 53 2 221 2 1 32		seat<-)
(00007311 10)
(00007312 5 2		UnVar2)
(00007314 13 17 0		nil->JMP 00007328)
(00007317 5 8		UnVar8)
(00007319 5 4		UnVar4)
(0000731B 53 1 212 2 1 32		seat)
(00007321 81 2 208 2 1 0		TWin.cpos<-)
(00007327 10)
(00007328 5 4		UnVar4)
(0000732A 1		nil)
(0000732B 81 2 201 1 1 0		tmark.owner<-)
(00007331 10)
(00007332 5 5		UnVar5)
(00007334 1		nil)
(00007335 81 2 201 1 1 0		tmark.owner<-)
(0000733B 22		ret)
(0000733C 81 0 206 2 1 0		message-beep)
(00007342 22		ret)
;;;def !editor-unindent-block 29507
(00007343 20 10 1 1 0)
(00007348 100 1		UNVar1)
(0000734A 100 2		UNVar2)
(0000734C 100 3		UNVar3)
(0000734E 100 4		UNVar4)
(00007350 100 5		UNVar5)
(00007352 100 6		UNVar6)
(00007354 100 7		UNVar7)
(00007356 100 8		UNVar8)
(00007358 100 9		UNVar9)
(0000735A 5 0		UnVar0)
(0000735C 81 1 135 3 1 0		TWinp)
(00007362 13 3 0		nil->JMP 00007368)
(00007365 15 5 0		JMP 0000736D)
(00007368 3 205 2		*active-mdiwindow*)
(0000736B 8 0		UnVar0)
(0000736D 5 0		UnVar0)
(0000736F 8 9		UnVar9)
(00007371 5 9		UnVar9)
(00007373 81 1 30 2 1 0		TWin.sel)
(00007379 8 8		UnVar8)
(0000737B 5 9		UnVar9)
(0000737D 81 1 167 2 1 0		TWin.cpos)
(00007383 8 4		UnVar4)
(00007385 5 8		UnVar8)
(00007387 53 1 212 2 1 32		seat)
(0000738D 40		car)
(0000738E 14 2 0		T->JMP 00007393)
(00007391 5 4		UnVar4)
(00007393 8 7		UnVar7)
(00007395 5 8		UnVar8)
(00007397 53 1 212 2 1 32		seat)
(0000739D 41		cdr)
(0000739E 14 2 0		T->JMP 000073A3)
(000073A1 5 4		UnVar4)
(000073A3 8 6		UnVar6)
(000073A5 5 0		UnVar0)
(000073A7 5 0		UnVar0)
(000073A9 5 7		UnVar7)
(000073AB 81 2 99 2 1 0		TBuf.BOL-pos)
(000073B1 81 2 101 2 1 0		TBuf.editablep)
(000073B7 13 92 1		nil->JMP 00007516)
(000073BA 5 4		UnVar4)
(000073BC 5 7		UnVar7)
(000073BE 81 2 113 2 1 0		=&)
(000073C4 8 4		UnVar4)
(000073C6 5 9		UnVar9)
(000073C8 81 1 232 2 1 0		TWin.tab-width)
(000073CE 8 1		UnVar1)
(000073D0 5 9		UnVar9)
(000073D2 81 1 203 1 1 0		TWin.TBuf)
(000073D8 8 0		UnVar0)
(000073DA 9 45 2		':OWNER)
(000073DD 5 0		UnVar0)
(000073DF 9 44 2		':SEAT)
(000073E2 5 7		UnVar7)
(000073E4 9 202 1		':EXCL)
(000073E7 2		T)
(000073E8 53 6 43 2 1 32		tmark)
(000073EE 8 5		UnVar5)
(000073F0 5 0		UnVar0)
(000073F2 5 7		UnVar7)
(000073F4 81 2 99 2 1 0		TBuf.BOL-pos)
(000073FA 8 7		UnVar7)
(000073FC 9 45 2		':OWNER)
(000073FF 5 0		UnVar0)
(00007401 9 44 2		':SEAT)
(00007404 5 7		UnVar7)
(00007406 5 6		UnVar6)
(00007408 38		=)
(00007409 13 13 0		nil->JMP 00007419)
(0000740C 5 0		UnVar0)
(0000740E 5 6		UnVar6)
(00007410 81 2 121 2 1 0		TBuf.next-pos)
(00007416 15 2 0		JMP 0000741B)
(00007419 5 6		UnVar6)
(0000741B 9 202 1		':EXCL)
(0000741E 1		nil)
(0000741F 53 6 43 2 1 32		tmark)
(00007425 8 6		UnVar6)
(00007427 5 0		UnVar0)
(00007429 81 1 42 2 1 0		TBuf.undo-sta)
(0000742F 10)
(00007430 15 127 0		JMP 000074B2)
(00007433 5 0		UnVar0)
(00007435 5 1		UnVar1)
(00007437 5 1		UnVar1)
(00007439 5 7		UnVar7)
(0000743B 81 4 167 0 1 0		TBuf.wcol-spos)
(00007441 8 3		UnVar3)
(00007443 5 3		UnVar3)
(00007445 81 1 40 2 1 0		ZEROP)
(0000744B 13 3 0		nil->JMP 00007451)
(0000744E 15 77 0		JMP 0000749E)
(00007451 5 0		UnVar0)
(00007453 9 102 2		" \t")
(00007456 1		nil)
(00007457 5 7		UnVar7)
(00007459 5 0		UnVar0)
(0000745B 5 7		UnVar7)
(0000745D 81 2 128 2 1 0		TBuf.EOL-pos)
(00007463 81 5 120 2 1 0		TBuf.scan-chars-forward)
(00007469 8 2		UnVar2)
(0000746B 5 2		UnVar2)
(0000746D 13 19 0		nil->JMP 00007483)
(00007470 5 2		UnVar2)
(00007472 5 7		UnVar7)
(00007474 71		-)
(00007475 8 2		UnVar2)
(00007477 5 2		UnVar2)
(00007479 5 3		UnVar3)
(0000747B 81 2 136 2 1 0		MIN)
(00007481 8 3		UnVar3)
(00007483 5 3		UnVar3)
(00007485 81 1 40 2 1 0		ZEROP)
(0000748B 13 3 0		nil->JMP 00007491)
(0000748E 15 13 0		JMP 0000749E)
(00007491 5 0		UnVar0)
(00007493 5 7		UnVar7)
(00007495 5 3		UnVar3)
(00007497 81 3 103 2 1 0		TBuf.delete)
(0000749D 10)
(0000749E 5 0		UnVar0)
(000074A0 5 0		UnVar0)
(000074A2 5 7		UnVar7)
(000074A4 81 2 128 2 1 0		TBuf.EOL-pos)
(000074AA 81 2 121 2 1 0		TBuf.next-pos)
(000074B0 8 7		UnVar7)
(000074B2 5 7		UnVar7)
(000074B4 5 6		UnVar6)
(000074B6 53 1 212 2 1 32		seat)
(000074BC 76		<)
(000074BD 60 115 255		T->JMP 00007433)
(000074C0 5 0		UnVar0)
(000074C2 81 1 41 2 1 0		TBuf.undo-end)
(000074C8 10)
(000074C9 5 8		UnVar8)
(000074CB 53 1 212 2 1 32		seat)
(000074D1 11)
(000074D2 8 3		UnVar3)
(000074D4 13 21 0		nil->JMP 000074EC)
(000074D7 5 8		UnVar8)
(000074D9 5 5		UnVar5)
(000074DB 53 1 212 2 1 32		seat)
(000074E1 5 3		UnVar3)
(000074E3 41		cdr)
(000074E4 42		cons)
(000074E5 53 2 221 2 1 32		seat<-)
(000074EB 10)
(000074EC 5 4		UnVar4)
(000074EE 13 17 0		nil->JMP 00007502)
(000074F1 5 9		UnVar9)
(000074F3 5 5		UnVar5)
(000074F5 53 1 212 2 1 32		seat)
(000074FB 81 2 208 2 1 0		TWin.cpos<-)
(00007501 10)
(00007502 5 5		UnVar5)
(00007504 1		nil)
(00007505 81 2 201 1 1 0		tmark.owner<-)
(0000750B 10)
(0000750C 5 6		UnVar6)
(0000750E 1		nil)
(0000750F 81 2 201 1 1 0		tmark.owner<-)
(00007515 22		ret)
(00007516 3 207 2		*stop-beep*)
(00007519 81 1 206 2 1 0		message-beep)
(0000751F 22		ret)
;;;def append-str-to-eols 29984
(00007520 20 5 4 4 0)
(00007525 100 4		UNVar4)
(00007527 5 2		UnVar2)
(00007529 8 4		UnVar4)
(0000752B 5 0		UnVar0)
(0000752D 5 2		UnVar2)
(0000752F 81 2 99 2 1 0		TBuf.BOL-pos)
(00007535 8 2		UnVar2)
(00007537 9 45 2		':OWNER)
(0000753A 5 0		UnVar0)
(0000753C 9 44 2		':SEAT)
(0000753F 5 0		UnVar0)
(00007541 5 3		UnVar3)
(00007543 81 2 100 2 1 0		TBuf.BOL-pos-p)
(00007549 13 5 0		nil->JMP 00007551)
(0000754C 5 3		UnVar3)
(0000754E 15 18 0		JMP 00007563)
(00007551 5 0		UnVar0)
(00007553 5 0		UnVar0)
(00007555 5 3		UnVar3)
(00007557 81 2 128 2 1 0		TBuf.EOL-pos)
(0000755D 81 2 121 2 1 0		TBuf.next-pos)
(00007563 9 202 1		':EXCL)
(00007566 1		nil)
(00007567 53 6 43 2 1 32		tmark)
(0000756D 8 3		UnVar3)
(0000756F 5 0		UnVar0)
(00007571 81 1 42 2 1 0		TBuf.undo-sta)
(00007577 10)
(00007578 5 0		UnVar0)
(0000757A 9 236 2		'lex-color-p)
(0000757D 81 2 168 0 1 0		slot-value&)
(00007583 1		nil)
(00007584 24 2 0)
(00007587 15 30 0		JMP 000075A8)
(0000758A 5 0		UnVar0)
(0000758C 5 0		UnVar0)
(0000758E 5 0		UnVar0)
(00007590 5 2		UnVar2)
(00007592 81 2 128 2 1 0		TBuf.EOL-pos)
(00007598 5 1		UnVar1)
(0000759A 81 3 80 3 1 0		TBuf.insert)
(000075A0 81 2 121 2 1 0		TBuf.next-pos)
(000075A6 8 2		UnVar2)
(000075A8 5 2		UnVar2)
(000075AA 5 3		UnVar3)
(000075AC 53 1 212 2 1 32		seat)
(000075B2 76		<)
(000075B3 60 212 255		T->JMP 0000758A)
(000075B6 25 1 0)
(000075B9 5 0		UnVar0)
(000075BB 81 1 41 2 1 0		TBuf.undo-end)
(000075C1 10)
(000075C2 5 3		UnVar3)
(000075C4 1		nil)
(000075C5 81 2 201 1 1 0		tmark.owner<-)
(000075CB 10)
(000075CC 5 0		UnVar0)
(000075CE 5 0		UnVar0)
(000075D0 5 4		UnVar4)
(000075D2 81 2 128 2 1 0		TBuf.EOL-pos)
(000075D8 1		nil)
(000075D9 81 3 208 2 1 0		TWin.cpos<-)
(000075DF 10)
(000075E0 5 0		UnVar0)
(000075E2 5 0		UnVar0)
(000075E4 5 2		UnVar2)
(000075E6 81 2 128 2 1 0		TBuf.EOL-pos)
(000075EC 47 2 48 2 32 32		!mark-ring-add)
;;;def !editor-append-string-to-lines 30194
(000075F2 20 4 1 2 0)
(000075F7 100 2		UNVar2)
(000075F9 100 3		UNVar3)
(000075FB 5 0		UnVar0)
(000075FD 81 1 135 3 1 0		TWinp)
(00007603 13 3 0		nil->JMP 00007609)
(00007606 15 11 0		JMP 00007614)
(00007609 3 205 2		*active-mdiwindow*)
(0000760C 14 3 0		T->JMP 00007612)
(0000760F 3 92 3		*console*)
(00007612 8 0		UnVar0)
(00007614 5 0		UnVar0)
(00007616 81 1 30 2 1 0		TWin.sel)
(0000761C 53 1 212 2 1 32		seat)
(00007622 8 2		UnVar2)
(00007624 5 2		UnVar2)
(00007626 40		car)
(00007627 14 8 0		T->JMP 00007632)
(0000762A 5 0		UnVar0)
(0000762C 81 1 167 2 1 0		TWin.cpos)
(00007632 8 3		UnVar3)
(00007634 5 2		UnVar2)
(00007636 41		cdr)
(00007637 14 2 0		T->JMP 0000763C)
(0000763A 5 3		UnVar3)
(0000763C 8 2		UnVar2)
(0000763E 5 0		UnVar0)
(00007640 5 3		UnVar3)
(00007642 81 2 101 2 1 0		TBuf.editablep)
(00007648 13 96 0		nil->JMP 000076AB)
(0000764B 5 1		UnVar1)
(0000764D 37 4		stringp)
(0000764F 13 3 0		nil->JMP 00007655)
(00007652 15 25 0		JMP 0000766E)
(00007655 9 107 3		"VLMSG.DLL")
(00007658 51 188 82 0 0		21180)
(0000765D 81 2 106 3 1 0		string-resource)
(00007663 3 166 0		*last-append-string-to-lines*)
(00007666 81 2 184 1 1 0		get-string-dialog)
(0000766C 8 1		UnVar1)
(0000766E 5 1		UnVar1)
(00007670 13 14 0		nil->JMP 00007681)
(00007673 5 1		UnVar1)
(00007675 9 41 3		"")
(00007678 81 2 3 3 1 0		equal)
(0000767E 15 1 0		JMP 00007682)
(00007681 2		T)
(00007682 62		T->ret)
(00007683 5 1		UnVar1)
(00007685 6 166 0		*last-append-string-to-lines*)
(00007688 5 0		UnVar0)
(0000768A 5 1		UnVar1)
(0000768C 5 3		UnVar3)
(0000768E 5 2		UnVar2)
(00007690 95 4 32 117 0 0		append-str-to-eols)
(00007696 10)
(00007697 5 0		UnVar0)
(00007699 5 0		UnVar0)
(0000769B 5 3		UnVar3)
(0000769D 81 2 128 2 1 0		TBuf.EOL-pos)
(000076A3 1		nil)
(000076A4 81 3 208 2 1 0		TWin.cpos<-)
(000076AA 22		ret)
(000076AB 3 207 2		*stop-beep*)
(000076AE 81 1 206 2 1 0		message-beep)
(000076B4 22		ret)
;;;def tbuf-lines-list 30389
(000076B5 20 5 1 3 0)
(000076BA 100 3		UNVar3)
(000076BC 100 4		UNVar4)
(000076BE 5 1		UnVar1)
(000076C0 37 2		consp)
(000076C2 13 31 0		nil->JMP 000076E4)
(000076C5 5 1		UnVar1)
(000076C7 40		car)
(000076C8 5 1		UnVar1)
(000076CA 41		cdr)
(000076CB 81 2 134 2 1 0		MAX)
(000076D1 8 2		UnVar2)
(000076D3 5 1		UnVar1)
(000076D5 41		cdr)
(000076D6 5 1		UnVar1)
(000076D8 40		car)
(000076D9 81 2 136 2 1 0		MIN)
(000076DF 8 1		UnVar1)
(000076E1 15 30 0		JMP 00007702)
(000076E4 5 1		UnVar1)
(000076E6 13 3 0		nil->JMP 000076EC)
(000076E9 15 4 0		JMP 000076F0)
(000076EC 50 0		0)
(000076EE 8 1		UnVar1)
(000076F0 5 2		UnVar2)
(000076F2 13 3 0		nil->JMP 000076F8)
(000076F5 15 10 0		JMP 00007702)
(000076F8 5 0		UnVar0)
(000076FA 81 1 209 2 1 0		TBuf.length)
(00007700 8 2		UnVar2)
(00007702 15 49 0		JMP 00007736)
(00007705 5 0		UnVar0)
(00007707 5 1		UnVar1)
(00007709 81 2 128 2 1 0		TBuf.EOL-pos)
(0000770F 8 4		UnVar4)
(00007711 5 0		UnVar0)
(00007713 5 1		UnVar1)
(00007715 5 4		UnVar4)
(00007717 5 2		UnVar2)
(00007719 81 2 136 2 1 0		MIN)
(0000771F 81 3 96 2 1 0		TBuf.subseq)
(00007725 5 3		UnVar3)
(00007727 42		cons)
(00007728 8 3		UnVar3)
(0000772A 5 0		UnVar0)
(0000772C 5 4		UnVar4)
(0000772E 81 2 121 2 1 0		TBuf.next-pos)
(00007734 8 1		UnVar1)
(00007736 5 1		UnVar1)
(00007738 5 2		UnVar2)
(0000773A 76		<)
(0000773B 60 199 255		T->JMP 00007705)
(0000773E 5 3		UnVar3)
(00007740 81 1 12 3 1 0		nreverse)
(00007746 22		ret)
;;;def !editor-sort-lines 30535
(00007747 20 5 1 1 0)
(0000774C 100 1		UNVar1)
(0000774E 100 2		UNVar2)
(00007750 100 3		UNVar3)
(00007752 100 4		UNVar4)
(00007754 5 0		UnVar0)
(00007756 81 1 135 3 1 0		TWinp)
(0000775C 13 3 0		nil->JMP 00007762)
(0000775F 15 11 0		JMP 0000776D)
(00007762 3 205 2		*active-mdiwindow*)
(00007765 14 3 0		T->JMP 0000776B)
(00007768 3 92 3		*console*)
(0000776B 8 0		UnVar0)
(0000776D 5 0		UnVar0)
(0000776F 53 1 217 2 1 32		selection)
(00007775 8 4		UnVar4)
(00007777 5 4		UnVar4)
(00007779 40		car)
(0000777A 5 4		UnVar4)
(0000777C 41		cdr)
(0000777D 81 2 134 2 1 0		MAX)
(00007783 8 3		UnVar3)
(00007785 5 4		UnVar4)
(00007787 41		cdr)
(00007788 5 4		UnVar4)
(0000778A 40		car)
(0000778B 81 2 136 2 1 0		MIN)
(00007791 8 4		UnVar4)
(00007793 5 4		UnVar4)
(00007795 5 0		UnVar0)
(00007797 81 1 167 2 1 0		TWin.cpos)
(0000779D 38		=)
(0000779E 8 1		UnVar1)
(000077A0 5 0		UnVar0)
(000077A2 5 4		UnVar4)
(000077A4 81 2 98 2 1 0		TBuf.EOL-pos-p)
(000077AA 13 13 0		nil->JMP 000077BA)
(000077AD 5 0		UnVar0)
(000077AF 5 4		UnVar4)
(000077B1 81 2 121 2 1 0		TBuf.next-pos)
(000077B7 15 10 0		JMP 000077C4)
(000077BA 5 0		UnVar0)
(000077BC 5 4		UnVar4)
(000077BE 81 2 99 2 1 0		TBuf.BOL-pos)
(000077C4 8 4		UnVar4)
(000077C6 5 0		UnVar0)
(000077C8 5 3		UnVar3)
(000077CA 81 2 100 2 1 0		TBuf.BOL-pos-p)
(000077D0 13 3 0		nil->JMP 000077D6)
(000077D3 15 20 0		JMP 000077EA)
(000077D6 5 0		UnVar0)
(000077D8 5 0		UnVar0)
(000077DA 5 3		UnVar3)
(000077DC 81 2 128 2 1 0		TBuf.EOL-pos)
(000077E2 81 2 121 2 1 0		TBuf.next-pos)
(000077E8 8 3		UnVar3)
(000077EA 5 0		UnVar0)
(000077EC 5 4		UnVar4)
(000077EE 81 2 101 2 1 0		TBuf.editablep)
(000077F4 13 27 0		nil->JMP 00007812)
(000077F7 50 2		2)
(000077F9 5 0		UnVar0)
(000077FB 5 4		UnVar4)
(000077FD 5 3		UnVar3)
(000077FF 95 3 181 118 0 0		tbuf-lines-list)
(00007805 11)
(00007806 8 2		UnVar2)
(00007808 81 1 229 1 1 0		length)
(0000780E 75		>)
(0000780F 15 1 0		JMP 00007813)
(00007812 2		T)
(00007813 13 10 0		nil->JMP 00007820)
(00007816 3 207 2		*stop-beep*)
(00007819 81 1 206 2 1 0		message-beep)
(0000781F 22		ret)
(00007820 5 2		UnVar2)
(00007822 3 89 2		*editor-match-case*)
(00007825 13 6 0		nil->JMP 0000782E)
(00007828 9 249 1		'string<)
(0000782B 15 3 0		JMP 00007831)
(0000782E 9 165 0		'string-lessp)
(00007831 81 2 248 1 1 0		sort)
(00007837 8 2		UnVar2)
(00007839 5 0		UnVar0)
(0000783B 81 1 42 2 1 0		TBuf.undo-sta)
(00007841 10)
(00007842 5 0		UnVar0)
(00007844 9 236 2		'lex-color-p)
(00007847 81 2 168 0 1 0		slot-value&)
(0000784D 1		nil)
(0000784E 24 2 0)
(00007851 5 0		UnVar0)
(00007853 5 4		UnVar4)
(00007855 5 3		UnVar3)
(00007857 5 4		UnVar4)
(00007859 71		-)
(0000785A 81 3 103 2 1 0		TBuf.delete)
(00007860 10)
(00007861 5 1		UnVar1)
(00007863 13 7 0		nil->JMP 0000786D)
(00007866 5 4		UnVar4)
(00007868 8 1		UnVar1)
(0000786A 15 4 0		JMP 00007871)
(0000786D 5 4		UnVar4)
(0000786F 8 3		UnVar3)
(00007871 15 35 0		JMP 00007897)
(00007874 5 0		UnVar0)
(00007876 5 4		UnVar4)
(00007878 5 2		UnVar2)
(0000787A 40		car)
(0000787B 81 3 80 3 1 0		TBuf.insert)
(00007881 8 4		UnVar4)
(00007883 5 0		UnVar0)
(00007885 5 4		UnVar4)
(00007887 9 164 0		"\n")
(0000788A 81 3 80 3 1 0		TBuf.insert)
(00007890 8 4		UnVar4)
(00007892 5 2		UnVar2)
(00007894 41		cdr)
(00007895 8 2		UnVar2)
(00007897 5 2		UnVar2)
(00007899 60 216 255		T->JMP 00007874)
(0000789C 5 1		UnVar1)
(0000789E 60 4 0		T->JMP 000078A5)
(000078A1 5 4		UnVar4)
(000078A3 8 1		UnVar1)
(000078A5 25 1 0)
(000078A8 5 0		UnVar0)
(000078AA 81 1 41 2 1 0		TBuf.undo-end)
(000078B0 10)
(000078B1 5 0		UnVar0)
(000078B3 5 1		UnVar1)
(000078B5 1		nil)
(000078B6 81 3 208 2 1 0		TWin.cpos<-)
(000078BC 10)
(000078BD 5 0		UnVar0)
(000078BF 5 3		UnVar3)
(000078C1 47 2 48 2 32 32		!mark-ring-add)
;;;def !?ed-comm-blk 30919
(000078C7 20 1 1 1 0)
(000078CC 5 0		UnVar0)
(000078CE 53 1 91 3 1 32		editorp)
(000078D4 63		nil->ret)
(000078D5 5 0		UnVar0)
(000078D7 81 1 101 2 1 0		TBuf.editablep)
(000078DD 63		nil->ret)
(000078DE 5 0		UnVar0)
(000078E0 81 1 132 2 1 0		TBuf.lex-scanner-id)
(000078E6 22		ret)
;;;def !editor-comment-block 30951
(000078E7 20 2 0 1 0)
(000078EC 100 1		UNVar1)
(000078EE 5 0		UnVar0)
(000078F0 53 1 91 3 1 32		editorp)
(000078F6 13 3 0		nil->JMP 000078FC)
(000078F9 15 5 0		JMP 00007901)
(000078FC 3 205 2		*active-mdiwindow*)
(000078FF 8 0		UnVar0)
(00007901 5 0		UnVar0)
(00007903 95 1 199 120 0 0		!?ed-comm-blk)
(00007909 11)
(0000790A 8 1		UnVar1)
(0000790C 13 20 0		nil->JMP 00007923)
(0000790F 5 0		UnVar0)
(00007911 5 1		UnVar1)
(00007913 3 163 0		*xsi-comment-alist*)
(00007916 81 2 16 3 1 0		assq)
(0000791C 41		cdr)
(0000791D 96 2 60 113 0 0		!editor-indent-block)
(00007923 81 0 206 2 1 0		message-beep)
(00007929 22		ret)
;;;def !editor-uncomment-block 31018
(0000792A 20 7 0 1 0)
(0000792F 100 1		UNVar1)
(00007931 100 2		UNVar2)
(00007933 100 3		UNVar3)
(00007935 100 4		UNVar4)
(00007937 100 5		UNVar5)
(00007939 100 6		UNVar6)
(0000793B 5 0		UnVar0)
(0000793D 53 1 91 3 1 32		editorp)
(00007943 13 3 0		nil->JMP 00007949)
(00007946 15 5 0		JMP 0000794E)
(00007949 3 205 2		*active-mdiwindow*)
(0000794C 8 0		UnVar0)
(0000794E 5 0		UnVar0)
(00007950 95 1 199 120 0 0		!?ed-comm-blk)
(00007956 11)
(00007957 8 6		UnVar6)
(00007959 61 114 0		nil->JMP 000079CE)
(0000795C 5 6		UnVar6)
(0000795E 3 163 0		*xsi-comment-alist*)
(00007961 81 2 16 3 1 0		assq)
(00007967 41		cdr)
(00007968 11)
(00007969 8 5		UnVar5)
(0000796B 61 96 0		nil->JMP 000079CE)
(0000796E 5 0		UnVar0)
(00007970 81 1 30 2 1 0		TWin.sel)
(00007976 53 1 212 2 1 32		seat)
(0000797C 8 4		UnVar4)
(0000797E 5 0		UnVar0)
(00007980 81 1 167 2 1 0		TWin.cpos)
(00007986 8 3		UnVar3)
(00007988 5 0		UnVar0)
(0000798A 5 4		UnVar4)
(0000798C 40		car)
(0000798D 14 2 0		T->JMP 00007992)
(00007990 5 3		UnVar3)
(00007992 81 2 99 2 1 0		TBuf.BOL-pos)
(00007998 8 2		UnVar2)
(0000799A 9 45 2		':OWNER)
(0000799D 5 0		UnVar0)
(0000799F 9 44 2		':SEAT)
(000079A2 5 4		UnVar4)
(000079A4 41		cdr)
(000079A5 14 2 0		T->JMP 000079AA)
(000079A8 5 3		UnVar3)
(000079AA 9 202 1		':EXCL)
(000079AD 1		nil)
(000079AE 53 6 43 2 1 32		tmark)
(000079B4 8 1		UnVar1)
(000079B6 5 5		UnVar5)
(000079B8 50 0		0)
(000079BA 50 1		1)
(000079BC 81 3 171 1 1 0		substr)
(000079C2 8 5		UnVar5)
(000079C4 5 0		UnVar0)
(000079C6 5 2		UnVar2)
(000079C8 81 2 101 2 1 0		TBuf.editablep)
(000079CE 13 124 0		nil->JMP 00007A4D)
(000079D1 5 4		UnVar4)
(000079D3 13 3 0		nil->JMP 000079D9)
(000079D6 15 19 0		JMP 000079EC)
(000079D9 5 1		UnVar1)
(000079DB 5 0		UnVar0)
(000079DD 5 1		UnVar1)
(000079DF 81 2 121 2 1 0		TBuf.next-pos)
(000079E5 53 2 221 2 1 32		seat<-)
(000079EB 10)
(000079EC 5 0		UnVar0)
(000079EE 81 1 42 2 1 0		TBuf.undo-sta)
(000079F4 10)
(000079F5 15 62 0		JMP 00007A36)
(000079F8 5 0		UnVar0)
(000079FA 5 5		UnVar5)
(000079FC 1		nil)
(000079FD 5 2		UnVar2)
(000079FF 81 4 120 2 1 0		TBuf.scan-chars-forward)
(00007A05 8 3		UnVar3)
(00007A07 5 2		UnVar2)
(00007A09 5 3		UnVar3)
(00007A0B 38		=)
(00007A0C 13 3 0		nil->JMP 00007A12)
(00007A0F 15 16 0		JMP 00007A22)
(00007A12 5 0		UnVar0)
(00007A14 5 2		UnVar2)
(00007A16 5 3		UnVar3)
(00007A18 5 2		UnVar2)
(00007A1A 71		-)
(00007A1B 81 3 103 2 1 0		TBuf.delete)
(00007A21 10)
(00007A22 5 0		UnVar0)
(00007A24 5 0		UnVar0)
(00007A26 5 2		UnVar2)
(00007A28 81 2 128 2 1 0		TBuf.EOL-pos)
(00007A2E 81 2 121 2 1 0		TBuf.next-pos)
(00007A34 8 2		UnVar2)
(00007A36 5 2		UnVar2)
(00007A38 5 1		UnVar1)
(00007A3A 53 1 212 2 1 32		seat)
(00007A40 76		<)
(00007A41 60 180 255		T->JMP 000079F8)
(00007A44 5 0		UnVar0)
(00007A46 81 1 41 2 1 0		TBuf.undo-end)
(00007A4C 22		ret)
(00007A4D 81 0 206 2 1 0		message-beep)
(00007A53 22		ret)
;;;def transform-selected-text 31316
(00007A54 20 4 2 2 0)
(00007A59 100 2		UNVar2)
(00007A5B 100 3		UNVar3)
(00007A5D 5 0		UnVar0)
(00007A5F 81 1 101 2 1 0		TBuf.editablep)
(00007A65 61 11 0		nil->JMP 00007A73)
(00007A68 5 0		UnVar0)
(00007A6A 53 1 162 0 1 32		selected-text)
(00007A70 11)
(00007A71 8 2		UnVar2)
(00007A73 13 34 0		nil->JMP 00007A98)
(00007A76 5 0		UnVar0)
(00007A78 81 1 42 2 1 0		TBuf.undo-sta)
(00007A7E 10)
(00007A7F 5 0		UnVar0)
(00007A81 5 2		UnVar2)
(00007A83 5 1		UnVar1)
(00007A85 52 1 1		)
(00007A88 53 2 85 1 1 32		selected-text<-)
(00007A8E 10)
(00007A8F 5 0		UnVar0)
(00007A91 81 1 41 2 1 0		TBuf.undo-end)
(00007A97 22		ret)
(00007A98 81 0 206 2 1 0		message-beep)
(00007A9E 22		ret)
;;;def nil 31391
(00007A9F 20 2 2 2 0)
(00007AA4 5 0		UnVar0)
(00007AA6 81 1 135 3 1 0		TWinp)
(00007AAC 60 5 0		T->JMP 00007AB4)
(00007AAF 3 205 2		*active-mdiwindow*)
(00007AB2 8 0		UnVar0)
(00007AB4 5 0		UnVar0)
(00007AB6 81 1 218 2 1 0		TWin.has-selection-p)
(00007ABC 60 18 0		T->JMP 00007AD1)
(00007ABF 5 0		UnVar0)
(00007AC1 5 0		UnVar0)
(00007AC3 81 1 121 2 1 0		TBuf.next-pos)
(00007AC9 2		T)
(00007ACA 81 3 208 2 1 0		TWin.cpos<-)
(00007AD0 10)
(00007AD1 5 0		UnVar0)
(00007AD3 5 1		UnVar1)
(00007AD5 96 2 84 122 0 0		transform-selected-text)
;;;def !ed-upcase 31451
(00007ADB 20 1 1 1 0)
(00007AE0 5 0		UnVar0)
(00007AE2 9 161 0		'nstring-upcase)
(00007AE5 96 2 159 122 0 0		func 00007A9F)
;;;def !ed-downcase 31467
(00007AEB 20 1 1 1 0)
(00007AF0 5 0		UnVar0)
(00007AF2 9 160 0		'nstring-downcase)
(00007AF5 96 2 159 122 0 0		func 00007A9F)
;;;def !ed-capitalize 31483
(00007AFB 20 1 1 1 0)
(00007B00 5 0		UnVar0)
(00007B02 9 159 0		'nstring-capitalize)
(00007B05 96 2 159 122 0 0		func 00007A9F)
;;;def !choose-date-format 31499
(00007B0B 21 11 0 1 0)
(00007B10 5 0		UnVar0)
(00007B12 81 1 135 3 1 0		TWinp)
(00007B18 13 3 0		nil->JMP 00007B1E)
(00007B1B 15 5 0		JMP 00007B23)
(00007B1E 3 205 2		*active-mdiwindow*)
(00007B21 8 0		UnVar0)
(00007B23 51 70 0 70 0		4587590)
(00007B28 9 158 0		'("~@@d/~@@m/~@@y" "~V@d/~V@m/~@@y" "~@@m/~@@d/~@@y" "~V@m/~V@d/~@@y" "~V@d ~VVm, ~@@y" "~V@d-~@@@m-~@@y" "~@@d.~@@m.~@@y" "~V@d.~V@m.~@@y" "~V@d. ~VVm ~@@y"))
(00007B2B 8 2		UnVar2)
(00007B2D 100 3		UNVar3)
(00007B2F 15 29 0		JMP 00007B4F)
(00007B32 5 2		UnVar2)
(00007B34 40		car)
(00007B35 8 4		UnVar4)
(00007B37 5 4		UnVar4)
(00007B39 5 4		UnVar4)
(00007B3B 3 157 0		*vlisp-date-format*)
(00007B3E 81 2 88 2 1 0		string-equal)
(00007B44 42		cons)
(00007B45 5 3		UnVar3)
(00007B47 42		cons)
(00007B48 8 3		UnVar3)
(00007B4A 5 2		UnVar2)
(00007B4C 41		cdr)
(00007B4D 8 2		UnVar2)
(00007B4F 5 2		UnVar2)
(00007B51 60 222 255		T->JMP 00007B32)
(00007B54 5 3		UnVar3)
(00007B56 81 1 12 3 1 0		nreverse)
(00007B5C 9 156 0		':SHOW-FUN)
(00007B5F 15 14 0		JMP 00007B70)
(00007B62 20 1 1 1 0)
(00007B67 1		nil)
(00007B68 5 0		UnVar0)
(00007B6A 47 2 155 0 32 32		date-format)
(00007B70 9 154 3		'(31586 nil))
(00007B73 53 4 154 0 1 32		shaded-list-box)
(00007B79 8 1		UnVar1)
(00007B7B 51 70 0 70 0		4587590)
(00007B80 9 153 0		'("~@@h:~@@i:~@@s" "~@@h:~@@i" "~vh:~@@i:~@@s ~:h" "~vh:~@@i ~:h" "~@@h.~@@i.~@@s" "~@@h.~@@i"))
(00007B83 8 3		UnVar3)
(00007B85 100 4		UNVar4)
(00007B87 15 29 0		JMP 00007BA7)
(00007B8A 5 3		UnVar3)
(00007B8C 40		car)
(00007B8D 8 5		UnVar5)
(00007B8F 5 5		UnVar5)
(00007B91 5 5		UnVar5)
(00007B93 3 152 0		*vlisp-time-format*)
(00007B96 81 2 88 2 1 0		string-equal)
(00007B9C 42		cons)
(00007B9D 5 4		UnVar4)
(00007B9F 42		cons)
(00007BA0 8 4		UnVar4)
(00007BA2 5 3		UnVar3)
(00007BA4 41		cdr)
(00007BA5 8 3		UnVar3)
(00007BA7 5 3		UnVar3)
(00007BA9 60 222 255		T->JMP 00007B8A)
(00007BAC 5 4		UnVar4)
(00007BAE 81 1 12 3 1 0		nreverse)
(00007BB4 9 156 0		':SHOW-FUN)
(00007BB7 15 14 0		JMP 00007BC8)
(00007BBA 20 1 1 1 0)
(00007BBF 1		nil)
(00007BC0 5 0		UnVar0)
(00007BC2 47 2 155 0 32 32		date-format)
(00007BC8 9 153 3		'(31674 nil))
(00007BCB 53 4 154 0 1 32		shaded-list-box)
(00007BD1 8 2		UnVar2)
(00007BD3 15 73 0		JMP 00007C1F)
(00007BD6 20 3 1 1 0)
(00007BDB 100 1		UNVar1)
(00007BDD 100 2		UNVar2)
(00007BDF 4 1 1		UpVar1-1)
(00007BE2 53 1 151 0 1 32		list-box-selection)
(00007BE8 8 2		UnVar2)
(00007BEA 4 1 2		UpVar1-2)
(00007BED 53 1 151 0 1 32		list-box-selection)
(00007BF3 8 1		UnVar1)
(00007BF5 5 2		UnVar2)
(00007BF7 13 6 0		nil->JMP 00007C00)
(00007BFA 5 1		UnVar1)
(00007BFC 35		not)
(00007BFD 15 1 0		JMP 00007C01)
(00007C00 2		T)
(00007C01 13 7 0		nil->JMP 00007C0B)
(00007C04 81 0 206 2 1 0		message-beep)
(00007C0A 22		ret)
(00007C0B 5 2		UnVar2)
(00007C0D 40		car)
(00007C0E 6 157 0		*vlisp-date-format*)
(00007C11 5 1		UnVar1)
(00007C13 40		car)
(00007C14 6 152 0		*vlisp-time-format*)
(00007C17 5 0		UnVar0)
(00007C19 47 1 94 3 32 32		destroy-host-spouse)
(00007C1F 12 152 3		'(31702 nil))
(00007C22 8 3		UnVar3)
(00007C24 51 36 0 13 0		852004)
(00007C29 9 107 3		"VLMSG.DLL")
(00007C2C 51 84 61 0 0		15700)
(00007C31 81 2 106 3 1 0		string-resource)
(00007C37 5 3		UnVar3)
(00007C39 53 3 109 1 1 32		push-button)
(00007C3F 8 4		UnVar4)
(00007C41 1		nil)
(00007C42 1		nil)
(00007C43 9 107 3		"VLMSG.DLL")
(00007C46 51 198 82 0 0		21190)
(00007C4B 81 2 106 3 1 0		string-resource)
(00007C51 9 213 0		':VC)
(00007C54 50 7		7)
(00007C56 9 250 0		':H)
(00007C59 50 7		7)
(00007C5B 51 70 0 12 0		786502)
(00007C60 9 107 3		"VLMSG.DLL")
(00007C63 51 208 82 0 0		21200)
(00007C68 81 2 106 3 1 0		string-resource)
(00007C6E 53 2 13 1 1 32		static-text)
(00007C74 50 7		7)
(00007C76 51 70 0 12 0		786502)
(00007C7B 9 107 3		"VLMSG.DLL")
(00007C7E 51 218 82 0 0		21210)
(00007C83 81 2 106 3 1 0		string-resource)
(00007C89 53 2 13 1 1 32		static-text)
(00007C8F 50 7		7)
(00007C91 57 6 0		list)
(00007C94 50 2		2)
(00007C96 9 250 0		':H)
(00007C99 50 7		7)
(00007C9B 5 1		UnVar1)
(00007C9D 50 7		7)
(00007C9F 5 2		UnVar2)
(00007CA1 50 7		7)
(00007CA3 57 6 0		list)
(00007CA6 50 4		4)
(00007CA8 9 250 0		':H)
(00007CAB 50 4		4)
(00007CAD 5 4		UnVar4)
(00007CAF 50 20		20)
(00007CB1 51 36 0 13 0		852004)
(00007CB6 9 107 3		"VLMSG.DLL")
(00007CB9 51 228 82 0 0		21220)
(00007CBE 81 2 106 3 1 0		string-resource)
(00007CC4 9 94 3		'destroy-host-spouse)
(00007CC7 53 3 109 1 1 32		push-button)
(00007CCD 50 4		4)
(00007CCF 57 6 0		list)
(00007CD2 50 7		7)
(00007CD4 57 8 0		list)
(00007CD7 9 98 1		':DEFAULT-PUSH-BUTTON)
(00007CDA 5 4		UnVar4)
(00007CDC 9 100 1		':FONT)
(00007CDF 3 248 0		*inspector-font*)
(00007CE2 9 99 1		':PITCH)
(00007CE5 3 247 0		*inspector-pitch*)
(00007CE8 53 10 244 0 1 32		dialog-fmt)
(00007CEE 8 5		UnVar5)
(00007CF0 5 5		UnVar5)
(00007CF2 9 66 2		"vldlg.dll")
(00007CF5 50 123		123)
(00007CF7 5 5		UnVar5)
(00007CF9 9 68 2		'items)
(00007CFC 81 2 86 3 1 0		slot-value)
(00007D02 8 6		UnVar6)
(00007D04 51 157 4 0 0		1181)
(00007D09 51 158 4 0 0		1182)
(00007D0E 51 39 5 0 0		1319)
(00007D13 51 40 5 0 0		1320)
(00007D18 50 1		1)
(00007D1A 50 2		2)
(00007D1C 57 6 0		list)
(00007D1F 8 7		UnVar7)
(00007D21 100 8		UNVar8)
(00007D23 15 31 0		JMP 00007D45)
(00007D26 5 6		UnVar6)
(00007D28 40		car)
(00007D29 8 9		UnVar9)
(00007D2B 5 7		UnVar7)
(00007D2D 40		car)
(00007D2E 8 10		UnVar10)
(00007D30 5 9		UnVar9)
(00007D32 40		car)
(00007D33 5 10		UnVar10)
(00007D35 42		cons)
(00007D36 5 8		UnVar8)
(00007D38 42		cons)
(00007D39 8 8		UnVar8)
(00007D3B 5 6		UnVar6)
(00007D3D 41		cdr)
(00007D3E 8 6		UnVar6)
(00007D40 5 7		UnVar7)
(00007D42 41		cdr)
(00007D43 8 7		UnVar7)
(00007D45 5 6		UnVar6)
(00007D47 61 2 0		nil->JMP 00007D4C)
(00007D4A 5 7		UnVar7)
(00007D4C 60 215 255		T->JMP 00007D26)
(00007D4F 5 8		UnVar8)
(00007D51 81 1 12 3 1 0		nreverse)
(00007D57 53 4 65 2 1 32		dialog-update-from-res)
(00007D5D 10)
(00007D5E 5 5		UnVar5)
(00007D60 47 1 64 2 32 32		modal-dialog!!)
;;;def editor-ctrl-x! 32102
(00007D66 20 1 1 1 0)
(00007D6B 3 150 0		*editor-ctrl-x-menu-items*)
(00007D6E 63		nil->ret)
(00007D6F 9 46 1		'menu)
(00007D72 9 149 0		"Ctrl-Shift-X")
(00007D75 9 148 0		"Ctrl-Shift-X commands")
(00007D78 3 150 0		*editor-ctrl-x-menu-items*)
(00007D7B 81 3 186 2 1 0		list*)
(00007D81 83		apply)
(00007D82 5 0		UnVar0)
(00007D84 47 2 42 1 32 32		mdiwin-track-popup-menu)
;;;def editor-add-ctrl-x-item 32138
(00007D8A 20 1 1 1 0)
(00007D8F 5 0		UnVar0)
(00007D91 3 150 0		*editor-ctrl-x-menu-items*)
(00007D94 42		cons)
(00007D95 6 150 0		*editor-ctrl-x-menu-items*)
(00007D98 2		T)
(00007D99 22		ret)
;;;def nil 32154
(00007D9A 20 0 0 0 0)
(00007D9F 2		T)
(00007DA0 81 1 225 0 1 0		get-logfont)
(00007DA6 22		ret)
;;;def nil 32167
(00007DA7 20 1 1 1 0)
(00007DAC 5 0		UnVar0)
(00007DAE 63		nil->ret)
(00007DAF 5 0		UnVar0)
(00007DB1 2		T)
(00007DB2 81 2 223 0 1 0		set-logfont)
(00007DB8 22		ret)
;;;def nil 32185
(00007DB9 20 2 2 2 0)
(00007DBE 5 1		UnVar1)
(00007DC0 13 29 0		nil->JMP 00007DE0)
(00007DC3 3 147 0		*inch-per-mm*)
(00007DC6 5 0		UnVar0)
(00007DC8 81 2 146 0 1 0		*)
(00007DCE 2		T)
(00007DCF 50 2		2)
(00007DD1 50 2		2)
(00007DD3 81 4 145 0 1 0		FTOA)
(00007DD9 81 1 144 0 1 0		ATOF)
(00007DDF 22		ret)
(00007DE0 5 0		UnVar0)
(00007DE2 22		ret)
;;;def nil 32227
(00007DE3 20 2 2 2 0)
(00007DE8 5 1		UnVar1)
(00007DEA 13 29 0		nil->JMP 00007E0A)
(00007DED 9 143 0		25.4)
(00007DF0 5 0		UnVar0)
(00007DF2 81 2 146 0 1 0		*)
(00007DF8 2		T)
(00007DF9 50 1		1)
(00007DFB 50 1		1)
(00007DFD 81 4 145 0 1 0		FTOA)
(00007E03 81 1 144 0 1 0		ATOF)
(00007E09 22		ret)
(00007E0A 5 0		UnVar0)
(00007E0C 22		ret)
;;;def _margin-value-item 32269
(00007E0D 21 2 2 2 0)
(00007E12 51 20 0 12 0		786452)
(00007E17 15 27 0		JMP 00007E35)
(00007E1A 20 0 0 0 0)
(00007E1F 4 1 0		UpVar1-0)
(00007E22 81 1 226 2 1 0		symbol-value)
(00007E28 3 142 0		*print-inch-or-mm*)
(00007E2B 9 141 0		':INCH)
(00007E2E 38		=)
(00007E2F 96 2 185 125 0 0		func 00007DB9)
(00007E35 12 151 3		'(32282 nil))
(00007E38 15 17 0		JMP 00007E4C)
(00007E3B 20 1 1 1 0)
(00007E40 4 1 0		UpVar1-0)
(00007E43 5 0		UnVar0)
(00007E45 81 2 140 0 1 0		set)
(00007E4B 22		ret)
(00007E4C 12 150 3		'(32315 nil))
(00007E4F 57 2 0		list)
(00007E52 9 107 3		"VLMSG.DLL")
(00007E55 51 66 89 0 0		22850)
(00007E5A 81 2 106 3 1 0		string-resource)
(00007E60 1		nil)
(00007E61 15 183 0		JMP 00007F1B)
(00007E64 20 6 4 4 0)
(00007E69 100 4		UNVar4)
(00007E6B 5 0		UnVar0)
(00007E6D 5 1		UnVar1)
(00007E6F 5 2		UnVar2)
(00007E71 5 3		UnVar3)
(00007E73 53 4 139 0 1 32		_protected-read)
(00007E79 8 4		UnVar4)
(00007E7B 5 4		UnVar4)
(00007E7D 81 1 138 0 1 0		NUMBERP)
(00007E83 61 44 0		nil->JMP 00007EB2)
(00007E86 5 4		UnVar4)
(00007E88 3 142 0		*print-inch-or-mm*)
(00007E8B 9 141 0		':INCH)
(00007E8E 38		=)
(00007E8F 95 2 227 125 0 0		func 00007DE3)
(00007E95 11)
(00007E96 8 4		UnVar4)
(00007E98 61 23 0		nil->JMP 00007EB2)
(00007E9B 50 0		0)
(00007E9D 5 4		UnVar4)
(00007E9F 81 2 137 0 1 0		<=)
(00007EA5 61 10 0		nil->JMP 00007EB2)
(00007EA8 5 4		UnVar4)
(00007EAA 50 100		100)
(00007EAC 81 2 79 2 1 0		<)
(00007EB2 13 3 0		nil->JMP 00007EB8)
(00007EB5 5 4		UnVar4)
(00007EB7 22		ret)
(00007EB8 5 0		UnVar0)
(00007EBA 6 136 0		_%reinput%)
(00007EBD 5 3		UnVar3)
(00007EBF 1		nil)
(00007EC0 9 107 3		"VLMSG.DLL")
(00007EC3 51 76 89 0 0		22860)
(00007EC8 81 2 106 3 1 0		string-resource)
(00007ECE 4 1 1		UpVar1-1)
(00007ED1 3 142 0		*print-inch-or-mm*)
(00007ED4 8 5		UnVar5)
(00007ED6 5 5		UnVar5)
(00007ED8 9 135 0		':MM)
(00007EDB 38		=)
(00007EDC 13 17 0		nil->JMP 00007EF0)
(00007EDF 9 107 3		"VLMSG.DLL")
(00007EE2 51 86 89 0 0		22870)
(00007EE7 81 2 106 3 1 0		string-resource)
(00007EED 15 27 0		JMP 00007F0B)
(00007EF0 5 5		UnVar5)
(00007EF2 9 141 0		':INCH)
(00007EF5 38		=)
(00007EF6 13 17 0		nil->JMP 00007F0A)
(00007EF9 9 107 3		"VLMSG.DLL")
(00007EFC 51 96 89 0 0		22880)
(00007F01 81 2 106 3 1 0		string-resource)
(00007F07 15 1 0		JMP 00007F0B)
(00007F0A 1		nil)
(00007F0B 53 4 1 3 1 32		format)
(00007F11 81 2 134 0 1 0		unbox<-)
(00007F17 10)
(00007F18 5 3		UnVar3)
(00007F1A 22		ret)
(00007F1B 12 149 3		'(32356 nil))
(00007F1E 47 5 133 0 32 32		accessed-editable-text)
;;;def nil 32548
(00007F24 20 5 1 1 0)
(00007F29 100 1		UNVar1)
(00007F2B 5 0		UnVar0)
(00007F2D 8 2		UnVar2)
(00007F2F 100 3		UNVar3)
(00007F31 15 113 0		JMP 00007FA5)
(00007F34 5 2		UnVar2)
(00007F36 40		car)
(00007F37 8 3		UnVar3)
(00007F39 5 2		UnVar2)
(00007F3B 41		cdr)
(00007F3C 8 2		UnVar2)
(00007F3E 3 142 0		*print-inch-or-mm*)
(00007F41 8 4		UnVar4)
(00007F43 5 4		UnVar4)
(00007F45 9 135 0		':MM)
(00007F48 38		=)
(00007F49 13 32 0		nil->JMP 00007F6C)
(00007F4C 5 3		UnVar3)
(00007F4E 5 3		UnVar3)
(00007F50 9 132 0		'tmp)
(00007F53 81 2 86 3 1 0		slot-value)
(00007F59 81 1 131 0 1 0		prin1-to-string)
(00007F5F 9 241 0		'text)
(00007F62 81 3 78 3 1 0		slot-value<-)
(00007F68 10)
(00007F69 15 48 0		JMP 00007F9C)
(00007F6C 5 4		UnVar4)
(00007F6E 9 141 0		':INCH)
(00007F71 38		=)
(00007F72 13 39 0		nil->JMP 00007F9C)
(00007F75 5 3		UnVar3)
(00007F77 5 3		UnVar3)
(00007F79 9 132 0		'tmp)
(00007F7C 81 2 86 3 1 0		slot-value)
(00007F82 2		T)
(00007F83 95 2 185 125 0 0		func 00007DB9)
(00007F89 81 1 131 0 1 0		prin1-to-string)
(00007F8F 9 241 0		'text)
(00007F92 81 3 78 3 1 0		slot-value<-)
(00007F98 10)
(00007F99 15 0 0		JMP 00007F9C)
(00007F9C 5 3		UnVar3)
(00007F9E 53 1 102 3 1 32		update-host-spouse)
(00007FA4 10)
(00007FA5 5 2		UnVar2)
(00007FA7 60 138 255		T->JMP 00007F34)
(00007FAA 1		nil)
(00007FAB 22		ret)
;;;def _correct-margin 32684
(00007FAC 20 3 3 3 0)
(00007FB1 3 130 0		_%err%)
(00007FB4 5 2		UnVar2)
(00007FB6 81 2 134 0 1 0		unbox<-)
(00007FBC 10)
(00007FBD 5 0		UnVar0)
(00007FBF 5 1		UnVar1)
(00007FC1 3 142 0		*print-inch-or-mm*)
(00007FC4 9 141 0		':INCH)
(00007FC7 38		=)
(00007FC8 95 2 185 125 0 0		func 00007DB9)
(00007FCE 81 1 131 0 1 0		prin1-to-string)
(00007FD4 53 2 219 1 1 32		editable-text.text<-)
(00007FDA 10)
(00007FDB 5 0		UnVar0)
(00007FDD 6 136 0		_%reinput%)
(00007FE0 5 0		UnVar0)
(00007FE2 53 1 102 3 1 32		update-host-spouse)
(00007FE8 10)
(00007FE9 1		nil)
(00007FEA 22		ret)
;;;def _verify-margins 32747
(00007FEB 20 18 2 2 0)
(00007FF0 100 2		UNVar2)
(00007FF2 5 0		UnVar0)
(00007FF4 8 3		UnVar3)
(00007FF6 5 3		UnVar3)
(00007FF8 44 11		IDFun11)
(00007FFA 8 4		UnVar4)
(00007FFC 5 3		UnVar3)
(00007FFE 5 4		UnVar4)
(00008000 9 14 1		':LEFT)
(00008003 53 3 61 2 1 32		_label-getf)
(00008009 8 5		UnVar5)
(0000800B 5 3		UnVar3)
(0000800D 5 4		UnVar4)
(0000800F 9 129 0		':TOP)
(00008012 53 3 61 2 1 32		_label-getf)
(00008018 8 6		UnVar6)
(0000801A 5 3		UnVar3)
(0000801C 5 4		UnVar4)
(0000801E 9 128 0		':BOTTOM)
(00008021 53 3 61 2 1 32		_label-getf)
(00008027 8 7		UnVar7)
(00008029 5 3		UnVar3)
(0000802B 5 4		UnVar4)
(0000802D 9 9 1		':RIGHT)
(00008030 53 3 61 2 1 32		_label-getf)
(00008036 8 8		UnVar8)
(00008038 5 3		UnVar3)
(0000803A 5 4		UnVar4)
(0000803C 9 100 1		':FONT)
(0000803F 53 3 61 2 1 32		_label-getf)
(00008045 8 9		UnVar9)
(00008047 5 1		UnVar1)
(00008049 81 1 127 0 1 0		printer-page)
(0000804F 8 2		UnVar2)
(00008051 5 2		UnVar2)
(00008053 13 228 1		nil->JMP 0000823A)
(00008056 5 2		UnVar2)
(00008058 40		car)
(00008059 81 1 253 2 1 0		ipoint-h)
(0000805F 8 10		UnVar10)
(00008061 5 2		UnVar2)
(00008063 40		car)
(00008064 81 1 251 2 1 0		ipoint-v)
(0000806A 8 11		UnVar11)
(0000806C 5 2		UnVar2)
(0000806E 41		cdr)
(0000806F 40		car)
(00008070 81 1 253 2 1 0		ipoint-h)
(00008076 8 12		UnVar12)
(00008078 5 2		UnVar2)
(0000807A 41		cdr)
(0000807B 40		car)
(0000807C 81 1 251 2 1 0		ipoint-v)
(00008082 8 13		UnVar13)
(00008084 5 2		UnVar2)
(00008086 41		cdr)
(00008087 41		cdr)
(00008088 40		car)
(00008089 81 1 253 2 1 0		ipoint-h)
(0000808F 8 14		UnVar14)
(00008091 5 2		UnVar2)
(00008093 41		cdr)
(00008094 41		cdr)
(00008095 40		car)
(00008096 81 1 251 2 1 0		ipoint-v)
(0000809C 8 15		UnVar15)
(0000809E 100 16		UNVar16)
(000080A0 100 17		UNVar17)
(000080A2 5 10		UnVar10)
(000080A4 5 14		UnVar14)
(000080A6 5 12		UnVar12)
(000080A8 70		+)
(000080A9 71		-)
(000080AA 8 16		UnVar16)
(000080AC 5 11		UnVar11)
(000080AE 5 15		UnVar15)
(000080B0 5 13		UnVar13)
(000080B2 70		+)
(000080B3 71		-)
(000080B4 8 17		UnVar17)
(000080B6 5 5		UnVar5)
(000080B8 9 132 0		'tmp)
(000080BB 81 2 86 3 1 0		slot-value)
(000080C1 5 14		UnVar14)
(000080C3 81 2 79 2 1 0		<)
(000080C9 13 24 0		nil->JMP 000080E4)
(000080CC 5 5		UnVar5)
(000080CE 5 14		UnVar14)
(000080D0 9 107 3		"VLMSG.DLL")
(000080D3 51 106 89 0 0		22890)
(000080D8 81 2 106 3 1 0		string-resource)
(000080DE 97 3 177 127 0 0		offset 00007FB1)
(000080E4 5 6		UnVar6)
(000080E6 9 132 0		'tmp)
(000080E9 81 2 86 3 1 0		slot-value)
(000080EF 5 15		UnVar15)
(000080F1 81 2 79 2 1 0		<)
(000080F7 13 24 0		nil->JMP 00008112)
(000080FA 5 6		UnVar6)
(000080FC 5 15		UnVar15)
(000080FE 9 107 3		"VLMSG.DLL")
(00008101 51 116 89 0 0		22900)
(00008106 81 2 106 3 1 0		string-resource)
(0000810C 97 3 177 127 0 0		offset 00007FB1)
(00008112 5 8		UnVar8)
(00008114 9 132 0		'tmp)
(00008117 81 2 86 3 1 0		slot-value)
(0000811D 5 16		UnVar16)
(0000811F 81 2 79 2 1 0		<)
(00008125 13 24 0		nil->JMP 00008140)
(00008128 5 8		UnVar8)
(0000812A 5 16		UnVar16)
(0000812C 9 107 3		"VLMSG.DLL")
(0000812F 51 126 89 0 0		22910)
(00008134 81 2 106 3 1 0		string-resource)
(0000813A 97 3 177 127 0 0		offset 00007FB1)
(00008140 5 7		UnVar7)
(00008142 9 132 0		'tmp)
(00008145 81 2 86 3 1 0		slot-value)
(0000814B 5 17		UnVar17)
(0000814D 81 2 79 2 1 0		<)
(00008153 13 24 0		nil->JMP 0000816E)
(00008156 5 7		UnVar7)
(00008158 5 17		UnVar17)
(0000815A 9 107 3		"VLMSG.DLL")
(0000815D 51 126 89 0 0		22910)
(00008162 81 2 106 3 1 0		string-resource)
(00008168 97 3 177 127 0 0		offset 00007FB1)
(0000816E 5 11		UnVar11)
(00008170 5 7		UnVar7)
(00008172 9 132 0		'tmp)
(00008175 81 2 86 3 1 0		slot-value)
(0000817B 81 2 59 2 1 0		-)
(00008181 5 6		UnVar6)
(00008183 9 132 0		'tmp)
(00008186 81 2 86 3 1 0		slot-value)
(0000818C 81 2 59 2 1 0		-)
(00008192 50 12		12)
(00008194 81 2 79 2 1 0		<)
(0000819A 13 54 0		nil->JMP 000081D3)
(0000819D 5 7		UnVar7)
(0000819F 5 17		UnVar17)
(000081A1 50 5		5)
(000081A3 81 2 39 2 1 0		+)
(000081A9 9 41 3		"")
(000081AC 95 3 172 127 0 0		_correct-margin)
(000081B2 10)
(000081B3 5 6		UnVar6)
(000081B5 5 15		UnVar15)
(000081B7 50 5		5)
(000081B9 81 2 39 2 1 0		+)
(000081BF 9 107 3		"VLMSG.DLL")
(000081C2 51 136 89 0 0		22920)
(000081C7 81 2 106 3 1 0		string-resource)
(000081CD 97 3 177 127 0 0		offset 00007FB1)
(000081D3 5 10		UnVar10)
(000081D5 5 5		UnVar5)
(000081D7 9 132 0		'tmp)
(000081DA 81 2 86 3 1 0		slot-value)
(000081E0 81 2 59 2 1 0		-)
(000081E6 5 8		UnVar8)
(000081E8 9 132 0		'tmp)
(000081EB 81 2 86 3 1 0		slot-value)
(000081F1 81 2 59 2 1 0		-)
(000081F7 50 12		12)
(000081F9 81 2 79 2 1 0		<)
(000081FF 13 54 0		nil->JMP 00008238)
(00008202 5 5		UnVar5)
(00008204 5 16		UnVar16)
(00008206 50 5		5)
(00008208 81 2 39 2 1 0		+)
(0000820E 9 41 3		"")
(00008211 95 3 172 127 0 0		_correct-margin)
(00008217 10)
(00008218 5 8		UnVar8)
(0000821A 5 14		UnVar14)
(0000821C 50 5		5)
(0000821E 81 2 39 2 1 0		+)
(00008224 9 107 3		"VLMSG.DLL")
(00008227 51 146 89 0 0		22930)
(0000822C 81 2 106 3 1 0		string-resource)
(00008232 97 3 177 127 0 0		offset 00007FB1)
(00008238 2		T)
(00008239 22		ret)
(0000823A 3 130 0		_%err%)
(0000823D 9 107 3		"VLMSG.DLL")
(00008240 51 156 89 0 0		22940)
(00008245 81 2 106 3 1 0		string-resource)
(0000824B 81 2 134 0 1 0		unbox<-)
(00008251 10)
(00008252 5 9		UnVar9)
(00008254 6 136 0		_%reinput%)
(00008257 1		nil)
(00008258 22		ret)
;;;def _setpage-ok 33369
(00008259 20 2 2 2 0)
(0000825E 9 136 0		'_%reinput%)
(00008261 1		nil)
(00008262 9 130 0		'_%err%)
(00008265 1		nil)
(00008266 81 1 7 2 1 0		box)
(0000826C 9 214 2		'_%curr-rep-cntx%)
(0000826F 5 0		UnVar0)
(00008271 9 229 2		'l-context)
(00008274 81 2 86 3 1 0		slot-value)
(0000827A 14 3 0		T->JMP 00008280)
(0000827D 3 214 2		_%curr-rep-cntx%)
(00008280 24 6 0)
(00008283 5 0		UnVar0)
(00008285 53 1 38 2 1 32		accessed-verify)
(0000828B 61 10 0		nil->JMP 00008298)
(0000828E 5 0		UnVar0)
(00008290 5 1		UnVar1)
(00008292 95 2 235 127 0 0		_verify-margins)
(00008298 13 20 0		nil->JMP 000082AF)
(0000829B 5 0		UnVar0)
(0000829D 53 1 56 2 1 32		sync-down)
(000082A3 10)
(000082A4 5 0		UnVar0)
(000082A6 53 1 94 3 1 32		destroy-host-spouse)
(000082AC 15 48 0		JMP 000082DF)
(000082AF 3 130 0		_%err%)
(000082B2 81 1 126 0 1 0		unbox)
(000082B8 13 27 0		nil->JMP 000082D6)
(000082BB 5 0		UnVar0)
(000082BD 3 136 0		_%reinput%)
(000082C0 3 130 0		_%err%)
(000082C3 81 1 126 0 1 0		unbox)
(000082C9 53 3 125 0 1 32		dialog.reinput)
(000082CF 10)
(000082D0 3 130 0		_%err%)
(000082D3 15 9 0		JMP 000082DF)
(000082D6 9 124 0		"Internal: error")
(000082D9 53 1 123 0 1 32		error)
(000082DF 25 3 0)
(000082E2 22		ret)
;;;def !printer-font-setup 33507
(000082E3 20 2 1 1 0)
(000082E8 100 1		UNVar1)
(000082EA 2		T)
(000082EB 81 1 225 0 1 0		get-logfont)
(000082F1 2		T)
(000082F2 5 0		UnVar0)
(000082F4 53 1 194 0 1 32		dialogp)
(000082FA 61 2 0		nil->JMP 000082FF)
(000082FD 5 0		UnVar0)
(000082FF 81 3 224 0 1 0		choose-log-font)
(00008305 8 1		UnVar1)
(00008307 5 1		UnVar1)
(00008309 63		nil->ret)
(0000830A 5 1		UnVar1)
(0000830C 2		T)
(0000830D 81 2 223 0 1 0		set-logfont)
(00008313 22		ret)
;;;def !page-setup-dialog 33556
(00008314 21 23 0 1 0)
(00008319 100 1		UNVar1)
(0000831B 5 0		UnVar0)
(0000831D 81 1 135 3 1 0		TWinp)
(00008323 13 3 0		nil->JMP 00008329)
(00008326 15 5 0		JMP 0000832E)
(00008329 3 205 2		*active-mdiwindow*)
(0000832C 8 0		UnVar0)
(0000832E 5 0		UnVar0)
(00008330 81 1 135 3 1 0		TWinp)
(00008336 61 11 0		nil->JMP 00008344)
(00008339 5 0		UnVar0)
(0000833B 9 229 2		'l-context)
(0000833E 81 2 86 3 1 0		slot-value)
(00008344 14 3 0		T->JMP 0000834A)
(00008347 3 214 2		_%curr-rep-cntx%)
(0000834A 8 1		UnVar1)
(0000834C 51 150 0 12 0		786582)
(00008351 15 10 0		JMP 0000835E)
(00008354 20 0 0 0 0)
(00008359 3 122 0		*printer-header*)
(0000835C 40		car)
(0000835D 22		ret)
(0000835E 9 148 3		'(33620 nil))
(00008361 15 30 0		JMP 00008382)
(00008364 20 1 1 1 0)
(00008369 5 0		UnVar0)
(0000836B 6 122 0		*printer-header*)
(0000836E 3 121 0		*print-header/footer-state*)
(00008371 50 1		1)
(00008373 3 122 0		*printer-header*)
(00008376 40		car)
(00008377 53 3 120 0 1 32		_set-bit)
(0000837D 11)
(0000837E 6 121 0		*print-header/footer-state*)
(00008381 22		ret)
(00008382 9 147 3		'(33636 nil))
(00008385 57 2 0		list)
(00008388 9 107 3		"VLMSG.DLL")
(0000838B 51 166 89 0 0		22950)
(00008390 81 2 106 3 1 0		string-resource)
(00008396 1		nil)
(00008397 9 146 3		'(34950 parse-header-footer-string))
(0000839A 53 5 119 0 1 32		accessed-editable-string)
(000083A0 8 2		UnVar2)
(000083A2 51 150 0 12 0		786582)
(000083A7 15 10 0		JMP 000083B4)
(000083AA 20 0 0 0 0)
(000083AF 3 118 0		*printer-footer*)
(000083B2 40		car)
(000083B3 22		ret)
(000083B4 9 145 3		'(33706 nil))
(000083B7 15 30 0		JMP 000083D8)
(000083BA 20 1 1 1 0)
(000083BF 5 0		UnVar0)
(000083C1 6 118 0		*printer-footer*)
(000083C4 3 121 0		*print-header/footer-state*)
(000083C7 50 2		2)
(000083C9 3 118 0		*printer-footer*)
(000083CC 40		car)
(000083CD 53 3 120 0 1 32		_set-bit)
(000083D3 11)
(000083D4 6 121 0		*print-header/footer-state*)
(000083D7 22		ret)
(000083D8 9 144 3		'(33722 nil))
(000083DB 57 2 0		list)
(000083DE 9 107 3		"VLMSG.DLL")
(000083E1 51 166 89 0 0		22950)
(000083E6 81 2 106 3 1 0		string-resource)
(000083EC 1		nil)
(000083ED 9 146 3		'(34950 parse-header-footer-string))
(000083F0 53 5 119 0 1 32		accessed-editable-string)
(000083F6 8 3		UnVar3)
(000083F8 51 46 0 13 0		852014)
(000083FD 9 107 3		"VLMSG.DLL")
(00008400 51 176 89 0 0		22960)
(00008405 81 2 106 3 1 0		string-resource)
(0000840B 15 13 0		JMP 0000841B)
(0000840E 20 1 1 1 0)
(00008413 5 0		UnVar0)
(00008415 96 1 227 130 0 0		!printer-font-setup)
(0000841B 9 143 3		'(33806 nil))
(0000841E 53 3 109 1 1 32		push-button)
(00008424 8 4		UnVar4)
(00008426 9 117 0		'*print-left-margin*)
(00008429 9 107 3		"VLMSG.DLL")
(0000842C 51 186 89 0 0		22970)
(00008431 81 2 106 3 1 0		string-resource)
(00008437 53 2 116 0 1 32		_margin-value-item)
(0000843D 8 5		UnVar5)
(0000843F 9 115 0		'*print-right-margin*)
(00008442 9 107 3		"VLMSG.DLL")
(00008445 51 196 89 0 0		22980)
(0000844A 81 2 106 3 1 0		string-resource)
(00008450 53 2 116 0 1 32		_margin-value-item)
(00008456 8 6		UnVar6)
(00008458 9 114 0		'*print-top-margin*)
(0000845B 9 107 3		"VLMSG.DLL")
(0000845E 51 206 89 0 0		22990)
(00008463 81 2 106 3 1 0		string-resource)
(00008469 53 2 116 0 1 32		_margin-value-item)
(0000846F 8 7		UnVar7)
(00008471 9 113 0		'*print-bottom-margin*)
(00008474 9 107 3		"VLMSG.DLL")
(00008477 51 216 89 0 0		23000)
(0000847C 81 2 106 3 1 0		string-resource)
(00008482 53 2 116 0 1 32		_margin-value-item)
(00008488 8 8		UnVar8)
(0000848A 51 46 0 12 0		786478)
(0000848F 9 142 0		'*print-inch-or-mm*)
(00008492 9 141 0		':INCH)
(00008495 1		nil)
(00008496 9 107 3		"VLMSG.DLL")
(00008499 51 226 89 0 0		23010)
(0000849E 81 2 106 3 1 0		string-resource)
(000084A4 1		nil)
(000084A5 9 107 3		"VLMSG.DLL")
(000084A8 51 236 89 0 0		23020)
(000084AD 81 2 106 3 1 0		string-resource)
(000084B3 53 7 112 0 1 32		accessed-radio-button)
(000084B9 8 9		UnVar9)
(000084BB 51 46 0 12 0		786478)
(000084C0 9 142 0		'*print-inch-or-mm*)
(000084C3 9 135 0		':MM)
(000084C6 1		nil)
(000084C7 9 107 3		"VLMSG.DLL")
(000084CA 51 246 89 0 0		23030)
(000084CF 81 2 106 3 1 0		string-resource)
(000084D5 1		nil)
(000084D6 9 107 3		"VLMSG.DLL")
(000084D9 51 0 90 0 0		23040)
(000084DE 81 2 106 3 1 0		string-resource)
(000084E4 53 7 112 0 1 32		accessed-radio-button)
(000084EA 8 10		UnVar10)
(000084EC 51 46 0 13 0		852014)
(000084F1 9 107 3		"VLMSG.DLL")
(000084F4 51 84 61 0 0		15700)
(000084F9 81 2 106 3 1 0		string-resource)
(000084FF 15 16 0		JMP 00008512)
(00008502 20 1 1 1 0)
(00008507 5 0		UnVar0)
(00008509 4 1 0		UpVar1-0)
(0000850C 96 2 89 130 0 0		_setpage-ok)
(00008512 12 142 3		'(34050 nil))
(00008515 9 107 3		"VLMSG.DLL")
(00008518 51 94 61 0 0		15710)
(0000851D 81 2 106 3 1 0		string-resource)
(00008523 53 4 109 1 1 32		push-button)
(00008529 8 11		UnVar11)
(0000852B 9 107 3		"VLMSG.DLL")
(0000852E 51 10 90 0 0		23050)
(00008533 81 2 106 3 1 0		string-resource)
(00008539 8 12		UnVar12)
(0000853B 100 13		UNVar13)
(0000853D 100 14		UNVar14)
(0000853F 100 15		UNVar15)
(00008541 5 5		UnVar5)
(00008543 5 6		UnVar6)
(00008545 5 7		UnVar7)
(00008547 5 8		UnVar8)
(00008549 57 4 0		list)
(0000854C 8 13		UnVar13)
(0000854E 15 124 0		JMP 000085CD)
(00008551 20 1 1 1 0)
(00008556 4 1 15		UpVar1-15)
(00008559 4 1 13		UpVar1-13)
(0000855C 53 2 111 0 1 32		verify-dialog)
(00008562 13 65 0		nil->JMP 000085A6)
(00008565 4 1 9		UpVar1-9)
(00008568 53 1 56 2 1 32		sync-down)
(0000856E 10)
(0000856F 4 1 10		UpVar1-10)
(00008572 53 1 56 2 1 32		sync-down)
(00008578 10)
(00008579 5 0		UnVar0)
(0000857B 53 1 110 0 1 32		dialog-status)
(00008581 9 41 3		"")
(00008584 9 241 0		'text)
(00008587 81 3 78 3 1 0		slot-value<-)
(0000858D 10)
(0000858E 5 0		UnVar0)
(00008590 53 1 110 0 1 32		dialog-status)
(00008596 53 1 102 3 1 32		update-host-spouse)
(0000859C 10)
(0000859D 4 1 13		UpVar1-13)
(000085A0 96 1 36 127 0 0		func 00007F24)
(000085A6 4 1 9		UpVar1-9)
(000085A9 53 1 70 2 1 32		sync-up)
(000085AF 10)
(000085B0 4 1 10		UpVar1-10)
(000085B3 53 1 70 2 1 32		sync-up)
(000085B9 10)
(000085BA 4 1 9		UpVar1-9)
(000085BD 53 1 102 3 1 32		update-host-spouse)
(000085C3 10)
(000085C4 4 1 10		UpVar1-10)
(000085C7 47 1 102 3 32 32		update-host-spouse)
(000085CD 12 141 3		'(34129 nil))
(000085D0 8 14		UnVar14)
(000085D2 5 9		UnVar9)
(000085D4 5 14		UnVar14)
(000085D6 9 54 2		'command)
(000085D9 81 3 78 3 1 0		slot-value<-)
(000085DF 10)
(000085E0 5 10		UnVar10)
(000085E2 5 14		UnVar14)
(000085E4 9 54 2		'command)
(000085E7 81 3 78 3 1 0		slot-value<-)
(000085ED 10)
(000085EE 1		nil)
(000085EF 1		nil)
(000085F0 9 107 3		"VLMSG.DLL")
(000085F3 51 20 90 0 0		23060)
(000085F8 81 2 106 3 1 0		string-resource)
(000085FE 9 250 0		':H)
(00008601 50 5		5)
(00008603 9 103 1		':V)
(00008606 9 222 0		':GROUP)
(00008609 9 107 3		"VLMSG.DLL")
(0000860C 51 30 90 0 0		23070)
(00008611 81 2 106 3 1 0		string-resource)
(00008617 9 103 1		':V)
(0000861A 9 250 0		':H)
(0000861D 50 2		2)
(0000861F 5 2		UnVar2)
(00008621 50 1		1)
(00008623 57 4 0		list)
(00008626 50 2		2)
(00008628 9 250 0		':H)
(0000862B 50 2		2)
(0000862D 5 3		UnVar3)
(0000862F 50 1		1)
(00008631 57 4 0		list)
(00008634 50 1		1)
(00008636 57 5 0		list)
(00008639 57 3 0		list)
(0000863C 50 2		2)
(0000863E 9 222 0		':GROUP)
(00008641 9 107 3		"VLMSG.DLL")
(00008644 51 40 90 0 0		23080)
(00008649 81 2 106 3 1 0		string-resource)
(0000864F 9 250 0		':H)
(00008652 50 2		2)
(00008654 9 103 1		':V)
(00008657 5 9		UnVar9)
(00008659 50 2		2)
(0000865B 5 10		UnVar10)
(0000865D 57 4 0		list)
(00008660 50 6		6)
(00008662 9 103 1		':V)
(00008665 50 2		2)
(00008667 51 24 0 12 0		786456)
(0000866C 9 107 3		"VLMSG.DLL")
(0000866F 51 180 55 0 0		14260)
(00008674 81 2 106 3 1 0		string-resource)
(0000867A 53 2 13 1 1 32		static-text)
(00008680 50 2		2)
(00008682 51 24 0 12 0		786456)
(00008687 9 107 3		"VLMSG.DLL")
(0000868A 51 200 55 0 0		14280)
(0000868F 81 2 106 3 1 0		string-resource)
(00008695 53 2 13 1 1 32		static-text)
(0000869B 57 5 0		list)
(0000869E 50 2		2)
(000086A0 9 103 1		':V)
(000086A3 5 5		UnVar5)
(000086A5 50 2		2)
(000086A7 5 6		UnVar6)
(000086A9 50 2		2)
(000086AB 57 5 0		list)
(000086AE 50 6		6)
(000086B0 9 103 1		':V)
(000086B3 50 2		2)
(000086B5 51 24 0 12 0		786456)
(000086BA 9 107 3		"VLMSG.DLL")
(000086BD 51 104 76 0 0		19560)
(000086C2 81 2 106 3 1 0		string-resource)
(000086C8 53 2 13 1 1 32		static-text)
(000086CE 50 2		2)
(000086D0 51 24 0 12 0		786456)
(000086D5 9 107 3		"VLMSG.DLL")
(000086D8 51 50 90 0 0		23090)
(000086DD 81 2 106 3 1 0		string-resource)
(000086E3 53 2 13 1 1 32		static-text)
(000086E9 57 5 0		list)
(000086EC 50 2		2)
(000086EE 9 103 1		':V)
(000086F1 5 7		UnVar7)
(000086F3 50 2		2)
(000086F5 5 8		UnVar8)
(000086F7 50 2		2)
(000086F9 57 5 0		list)
(000086FC 50 2		2)
(000086FE 57 12 0		list)
(00008701 57 3 0		list)
(00008704 50 2		2)
(00008706 57 5 0		list)
(00008709 50 6		6)
(0000870B 9 103 1		':V)
(0000870E 50 5		5)
(00008710 51 46 0 13 0		852014)
(00008715 9 107 3		"VLMSG.DLL")
(00008718 51 202 88 0 0		22730)
(0000871D 81 2 106 3 1 0		string-resource)
(00008723 15 17 0		JMP 00008737)
(00008726 20 1 1 1 0)
(0000872B 3 156 2		*info-alert*)
(0000872E 4 1 12		UpVar1-12)
(00008731 47 2 85 3 32 32		alert)
(00008737 12 140 3		'(34598 nil))
(0000873A 53 3 109 1 1 32		push-button)
(00008740 50 2		2)
(00008742 5 4		UnVar4)
(00008744 50 10		10)
(00008746 5 11		UnVar11)
(00008748 50 2		2)
(0000874A 51 46 0 13 0		852014)
(0000874F 9 107 3		"VLMSG.DLL")
(00008752 51 228 82 0 0		21220)
(00008757 81 2 106 3 1 0		string-resource)
(0000875D 9 94 3		'destroy-host-spouse)
(00008760 9 107 3		"VLMSG.DLL")
(00008763 51 60 90 0 0		23100)
(00008768 81 2 106 3 1 0		string-resource)
(0000876E 53 4 109 1 1 32		push-button)
(00008774 50 2		2)
(00008776 57 10 0		list)
(00008779 50 5		5)
(0000877B 57 6 0		list)
(0000877E 9 98 1		':DEFAULT-PUSH-BUTTON)
(00008781 5 11		UnVar11)
(00008783 9 20 3		':L-CONTEXT)
(00008786 5 1		UnVar1)
(00008788 9 100 1		':FONT)
(0000878B 3 248 0		*inspector-font*)
(0000878E 9 99 1		':PITCH)
(00008791 3 247 0		*inspector-pitch*)
(00008794 9 245 0		':STATUS)
(00008797 50 1		1)
(00008799 9 109 0		':LABELS)
(0000879C 9 129 0		':TOP)
(0000879F 5 7		UnVar7)
(000087A1 9 14 1		':LEFT)
(000087A4 5 5		UnVar5)
(000087A6 9 128 0		':BOTTOM)
(000087A9 5 8		UnVar8)
(000087AB 9 9 1		':RIGHT)
(000087AE 5 6		UnVar6)
(000087B0 9 100 1		':FONT)
(000087B3 5 4		UnVar4)
(000087B5 57 10 0		list)
(000087B8 53 16 244 0 1 32		dialog-fmt)
(000087BE 8 15		UnVar15)
(000087C0 100 16		UNVar16)
(000087C2 100 17		UNVar17)
(000087C4 51 208 4 0 0		1232)
(000087C9 51 209 4 0 0		1233)
(000087CE 51 207 4 0 0		1231)
(000087D3 51 211 4 0 0		1235)
(000087D8 51 212 4 0 0		1236)
(000087DD 51 214 4 0 0		1238)
(000087E2 51 215 4 0 0		1239)
(000087E7 51 74 4 0 0		1098)
(000087EC 51 78 4 0 0		1102)
(000087F1 51 213 4 0 0		1237)
(000087F6 51 216 4 0 0		1240)
(000087FB 51 79 4 0 0		1103)
(00008800 51 80 4 0 0		1104)
(00008805 51 210 4 0 0		1234)
(0000880A 51 217 4 0 0		1241)
(0000880F 51 218 4 0 0		1242)
(00008814 50 1		1)
(00008816 50 2		2)
(00008818 51 219 4 0 0		1243)
(0000881D 57 19 0		list)
(00008820 8 16		UnVar16)
(00008822 5 15		UnVar15)
(00008824 9 68 2		'items)
(00008827 81 2 86 3 1 0		slot-value)
(0000882D 8 18		UnVar18)
(0000882F 5 16		UnVar16)
(00008831 8 19		UnVar19)
(00008833 100 20		UNVar20)
(00008835 15 31 0		JMP 00008857)
(00008838 5 18		UnVar18)
(0000883A 40		car)
(0000883B 8 21		UnVar21)
(0000883D 5 19		UnVar19)
(0000883F 40		car)
(00008840 8 22		UnVar22)
(00008842 5 21		UnVar21)
(00008844 40		car)
(00008845 5 22		UnVar22)
(00008847 42		cons)
(00008848 5 20		UnVar20)
(0000884A 42		cons)
(0000884B 8 20		UnVar20)
(0000884D 5 18		UnVar18)
(0000884F 41		cdr)
(00008850 8 18		UnVar18)
(00008852 5 19		UnVar19)
(00008854 41		cdr)
(00008855 8 19		UnVar19)
(00008857 5 18		UnVar18)
(00008859 61 2 0		nil->JMP 0000885E)
(0000885C 5 19		UnVar19)
(0000885E 60 215 255		T->JMP 00008838)
(00008861 5 20		UnVar20)
(00008863 81 1 12 3 1 0		nreverse)
(00008869 8 17		UnVar17)
(0000886B 5 15		UnVar15)
(0000886D 9 66 2		"vldlg.dll")
(00008870 51 133 0 0 0		133)
(00008875 5 17		UnVar17)
(00008877 53 4 65 2 1 32		dialog-update-from-res)
(0000887D 10)
(0000887E 5 15		UnVar15)
(00008880 47 1 64 2 32 32		modal-dialog!!)
;;;def parse-header-footer-string 34950
(00008886 20 14 4 4 0)
(0000888B 100 4		UNVar4)
(0000888D 100 5		UNVar5)
(0000888F 100 6		UNVar6)
(00008891 100 7		UNVar7)
(00008893 100 8		UNVar8)
(00008895 100 9		UNVar9)
(00008897 100 10		UNVar10)
(00008899 100 11		UNVar11)
(0000889B 5 2		UnVar2)
(0000889D 8 11		UnVar11)
(0000889F 81 0 159 1 1 0		make-string-output-stream)
(000088A5 8 7		UnVar7)
(000088A7 5 11		UnVar11)
(000088A9 13 26 0		nil->JMP 000088C6)
(000088AC 5 7		UnVar7)
(000088AE 5 11		UnVar11)
(000088B0 5 3		UnVar3)
(000088B2 50 0		0)
(000088B4 95 4 235 137 0 0		func 000089EB)
(000088BA 8 12		UnVar12)
(000088BC 5 12		UnVar12)
(000088BE 40		car)
(000088BF 8 10		UnVar10)
(000088C1 5 12		UnVar12)
(000088C3 41		cdr)
(000088C4 8 11		UnVar11)
(000088C6 5 11		UnVar11)
(000088C8 13 1 1		nil->JMP 000089CC)
(000088CB 15 220 0		JMP 000089AA)
(000088CE 5 11		UnVar11)
(000088D0 50 1		1)
(000088D2 81 2 195 2 1 0		char)
(000088D8 8 12		UnVar12)
(000088DA 5 12		UnVar12)
(000088DC 50 108		108)
(000088DE 81 2 3 3 1 0		equal)
(000088E4 13 29 0		nil->JMP 00008904)
(000088E7 5 7		UnVar7)
(000088E9 5 11		UnVar11)
(000088EB 5 3		UnVar3)
(000088ED 50 2		2)
(000088EF 95 4 235 137 0 0		func 000089EB)
(000088F5 8 13		UnVar13)
(000088F7 5 13		UnVar13)
(000088F9 40		car)
(000088FA 8 6		UnVar6)
(000088FC 5 13		UnVar13)
(000088FE 41		cdr)
(000088FF 8 11		UnVar11)
(00008901 15 124 0		JMP 00008980)
(00008904 5 12		UnVar12)
(00008906 50 99		99)
(00008908 81 2 3 3 1 0		equal)
(0000890E 13 29 0		nil->JMP 0000892E)
(00008911 5 7		UnVar7)
(00008913 5 11		UnVar11)
(00008915 5 3		UnVar3)
(00008917 50 2		2)
(00008919 95 4 235 137 0 0		func 000089EB)
(0000891F 8 13		UnVar13)
(00008921 5 13		UnVar13)
(00008923 40		car)
(00008924 8 5		UnVar5)
(00008926 5 13		UnVar13)
(00008928 41		cdr)
(00008929 8 11		UnVar11)
(0000892B 15 82 0		JMP 00008980)
(0000892E 5 12		UnVar12)
(00008930 50 114		114)
(00008932 81 2 3 3 1 0		equal)
(00008938 13 29 0		nil->JMP 00008958)
(0000893B 5 7		UnVar7)
(0000893D 5 11		UnVar11)
(0000893F 5 3		UnVar3)
(00008941 50 2		2)
(00008943 95 4 235 137 0 0		func 000089EB)
(00008949 8 13		UnVar13)
(0000894B 5 13		UnVar13)
(0000894D 40		car)
(0000894E 8 4		UnVar4)
(00008950 5 13		UnVar13)
(00008952 41		cdr)
(00008953 8 11		UnVar11)
(00008955 15 40 0		JMP 00008980)
(00008958 5 3		UnVar3)
(0000895A 1		nil)
(0000895B 9 107 3		"VLMSG.DLL")
(0000895E 51 70 90 0 0		23110)
(00008963 81 2 106 3 1 0		string-resource)
(00008969 5 11		UnVar11)
(0000896B 50 1		1)
(0000896D 81 2 195 2 1 0		char)
(00008973 53 3 1 3 1 32		format)
(00008979 81 2 134 0 1 0		unbox<-)
(0000897F 10)
(00008980 5 6		UnVar6)
(00008982 13 9 0		nil->JMP 0000898E)
(00008985 5 10		UnVar10)
(00008987 14 2 0		T->JMP 0000898C)
(0000898A 5 6		UnVar6)
(0000898C 8 10		UnVar10)
(0000898E 5 4		UnVar4)
(00008990 13 9 0		nil->JMP 0000899C)
(00008993 5 8		UnVar8)
(00008995 14 2 0		T->JMP 0000899A)
(00008998 5 4		UnVar4)
(0000899A 8 8		UnVar8)
(0000899C 5 5		UnVar5)
(0000899E 13 9 0		nil->JMP 000089AA)
(000089A1 5 9		UnVar9)
(000089A3 14 2 0		T->JMP 000089A8)
(000089A6 5 5		UnVar5)
(000089A8 8 9		UnVar9)
(000089AA 5 11		UnVar11)
(000089AC 61 26 0		nil->JMP 000089C9)
(000089AF 5 3		UnVar3)
(000089B1 81 1 126 0 1 0		unbox)
(000089B7 13 4 0		nil->JMP 000089BE)
(000089BA 1		nil)
(000089BB 15 11 0		JMP 000089C9)
(000089BE 5 11		UnVar11)
(000089C0 81 1 93 2 1 0		string-length)
(000089C6 50 1		1)
(000089C8 75		>)
(000089C9 60 2 255		T->JMP 000088CE)
(000089CC 5 3		UnVar3)
(000089CE 81 1 126 0 1 0		unbox)
(000089D4 13 8 0		nil->JMP 000089DF)
(000089D7 5 0		UnVar0)
(000089D9 6 136 0		_%reinput%)
(000089DC 5 3		UnVar3)
(000089DE 22		ret)
(000089DF 5 2		UnVar2)
(000089E1 5 10		UnVar10)
(000089E3 5 9		UnVar9)
(000089E5 5 8		UnVar8)
(000089E7 57 4 0		list)
(000089EA 22		ret)
;;;def nil 35307
(000089EB 20 10 4 4 0)
(000089F0 100 4		UNVar4)
(000089F2 100 5		UNVar5)
(000089F4 100 6		UNVar6)
(000089F6 5 1		UnVar1)
(000089F8 81 1 93 2 1 0		string-length)
(000089FE 50 1		1)
(00008A00 71		-)
(00008A01 8 4		UnVar4)
(00008A03 5 3		UnVar3)
(00008A05 8 7		UnVar7)
(00008A07 15 138 0		JMP 00008A94)
(00008A0A 5 1		UnVar1)
(00008A0C 5 7		UnVar7)
(00008A0E 81 2 195 2 1 0		char)
(00008A14 8 8		UnVar8)
(00008A16 5 8		UnVar8)
(00008A18 50 38		38)
(00008A1A 81 2 3 3 1 0		equal)
(00008A20 13 85 0		nil->JMP 00008A78)
(00008A23 5 7		UnVar7)
(00008A25 5 4		UnVar4)
(00008A27 76		<)
(00008A28 13 74 0		nil->JMP 00008A75)
(00008A2B 5 1		UnVar1)
(00008A2D 5 7		UnVar7)
(00008A2F 50 1		1)
(00008A31 70		+)
(00008A32 81 2 195 2 1 0		char)
(00008A38 8 9		UnVar9)
(00008A3A 5 9		UnVar9)
(00008A3C 9 108 0		'(116 100 112 102 38))
(00008A3F 81 2 114 3 1 0		memq)
(00008A45 13 41 0		nil->JMP 00008A71)
(00008A48 50 38		38)
(00008A4A 5 0		UnVar0)
(00008A4C 81 2 107 0 1 0		write-char)
(00008A52 10)
(00008A53 5 1		UnVar1)
(00008A55 5 7		UnVar7)
(00008A57 50 1		1)
(00008A59 70		+)
(00008A5A 81 2 195 2 1 0		char)
(00008A60 5 0		UnVar0)
(00008A62 81 2 107 0 1 0		write-char)
(00008A68 10)
(00008A69 5 7		UnVar7)
(00008A6B 79		1+)
(00008A6C 8 7		UnVar7)
(00008A6E 15 4 0		JMP 00008A75)
(00008A71 5 7		UnVar7)
(00008A73 8 6		UnVar6)
(00008A75 15 19 0		JMP 00008A8B)
(00008A78 5 1		UnVar1)
(00008A7A 5 7		UnVar7)
(00008A7C 81 2 195 2 1 0		char)
(00008A82 5 0		UnVar0)
(00008A84 81 2 107 0 1 0		write-char)
(00008A8A 10)
(00008A8B 5 7		UnVar7)
(00008A8D 79		1+)
(00008A8E 8 8		UnVar8)
(00008A90 5 8		UnVar8)
(00008A92 8 7		UnVar7)
(00008A94 5 6		UnVar6)
(00008A96 14 5 0		T->JMP 00008A9E)
(00008A99 5 7		UnVar7)
(00008A9B 5 4		UnVar4)
(00008A9D 75		>)
(00008A9E 35		not)
(00008A9F 60 104 255		T->JMP 00008A0A)
(00008AA2 9 2 2		" ")
(00008AA5 5 0		UnVar0)
(00008AA7 81 1 126 1 1 0		get-output-stream-string)
(00008AAD 81 2 40 3 1 0		string-right-trim)
(00008AB3 8 5		UnVar5)
(00008AB5 5 5		UnVar5)
(00008AB7 81 1 93 2 1 0		string-length)
(00008ABD 81 1 40 2 1 0		ZEROP)
(00008AC3 13 2 0		nil->JMP 00008AC8)
(00008AC6 100 5		UNVar5)
(00008AC8 5 6		UnVar6)
(00008ACA 13 26 0		nil->JMP 00008AE7)
(00008ACD 5 6		UnVar6)
(00008ACF 81 1 40 2 1 0		ZEROP)
(00008AD5 60 12 0		T->JMP 00008AE4)
(00008AD8 5 1		UnVar1)
(00008ADA 5 6		UnVar6)
(00008ADC 81 2 106 0 1 0		string-subseq)
(00008AE2 8 1		UnVar1)
(00008AE4 15 2 0		JMP 00008AE9)
(00008AE7 100 1		UNVar1)
(00008AE9 5 5		UnVar5)
(00008AEB 5 1		UnVar1)
(00008AED 42		cons)
(00008AEE 22		ret)
;;;def nil 35567
(00008AEF 20 10 4 4 0)
(00008AF4 100 4		UNVar4)
(00008AF6 100 5		UNVar5)
(00008AF8 100 6		UNVar6)
(00008AFA 5 1		UnVar1)
(00008AFC 81 1 93 2 1 0		string-length)
(00008B02 8 5		UnVar5)
(00008B04 50 0		0)
(00008B06 8 7		UnVar7)
(00008B08 15 250 0		JMP 00008C05)
(00008B0B 5 1		UnVar1)
(00008B0D 5 7		UnVar7)
(00008B0F 81 2 195 2 1 0		char)
(00008B15 8 8		UnVar8)
(00008B17 5 8		UnVar8)
(00008B19 50 38		38)
(00008B1B 81 2 3 3 1 0		equal)
(00008B21 13 197 0		nil->JMP 00008BE9)
(00008B24 5 1		UnVar1)
(00008B26 5 7		UnVar7)
(00008B28 50 1		1)
(00008B2A 70		+)
(00008B2B 81 2 195 2 1 0		char)
(00008B31 8 9		UnVar9)
(00008B33 5 9		UnVar9)
(00008B35 50 116		116)
(00008B37 81 2 3 3 1 0		equal)
(00008B3D 13 23 0		nil->JMP 00008B57)
(00008B40 53 0 105 0 1 32		current-time-string)
(00008B46 5 0		UnVar0)
(00008B48 81 2 127 3 1 0		princ)
(00008B4E 10)
(00008B4F 5 7		UnVar7)
(00008B51 79		1+)
(00008B52 8 7		UnVar7)
(00008B54 15 143 0		JMP 00008BE6)
(00008B57 5 9		UnVar9)
(00008B59 50 100		100)
(00008B5B 81 2 3 3 1 0		equal)
(00008B61 13 23 0		nil->JMP 00008B7B)
(00008B64 53 0 104 0 1 32		current-date-string)
(00008B6A 5 0		UnVar0)
(00008B6C 81 2 127 3 1 0		princ)
(00008B72 10)
(00008B73 5 7		UnVar7)
(00008B75 79		1+)
(00008B76 8 7		UnVar7)
(00008B78 15 107 0		JMP 00008BE6)
(00008B7B 5 9		UnVar9)
(00008B7D 50 112		112)
(00008B7F 81 2 3 3 1 0		equal)
(00008B85 13 19 0		nil->JMP 00008B9B)
(00008B88 5 3		UnVar3)
(00008B8A 5 0		UnVar0)
(00008B8C 81 2 127 3 1 0		princ)
(00008B92 10)
(00008B93 5 7		UnVar7)
(00008B95 79		1+)
(00008B96 8 7		UnVar7)
(00008B98 15 75 0		JMP 00008BE6)
(00008B9B 5 9		UnVar9)
(00008B9D 50 102		102)
(00008B9F 81 2 3 3 1 0		equal)
(00008BA5 13 19 0		nil->JMP 00008BBB)
(00008BA8 5 2		UnVar2)
(00008BAA 5 0		UnVar0)
(00008BAC 81 2 127 3 1 0		princ)
(00008BB2 10)
(00008BB3 5 7		UnVar7)
(00008BB5 79		1+)
(00008BB6 8 7		UnVar7)
(00008BB8 15 43 0		JMP 00008BE6)
(00008BBB 5 9		UnVar9)
(00008BBD 50 38		38)
(00008BBF 81 2 3 3 1 0		equal)
(00008BC5 13 19 0		nil->JMP 00008BDB)
(00008BC8 50 38		38)
(00008BCA 5 0		UnVar0)
(00008BCC 81 2 107 0 1 0		write-char)
(00008BD2 10)
(00008BD3 5 7		UnVar7)
(00008BD5 79		1+)
(00008BD6 8 7		UnVar7)
(00008BD8 15 11 0		JMP 00008BE6)
(00008BDB 50 95		95)
(00008BDD 5 0		UnVar0)
(00008BDF 81 2 107 0 1 0		write-char)
(00008BE5 10)
(00008BE6 15 19 0		JMP 00008BFC)
(00008BE9 5 1		UnVar1)
(00008BEB 5 7		UnVar7)
(00008BED 81 2 195 2 1 0		char)
(00008BF3 5 0		UnVar0)
(00008BF5 81 2 107 0 1 0		write-char)
(00008BFB 10)
(00008BFC 5 7		UnVar7)
(00008BFE 79		1+)
(00008BFF 8 8		UnVar8)
(00008C01 5 8		UnVar8)
(00008C03 8 7		UnVar7)
(00008C05 5 7		UnVar7)
(00008C07 5 5		UnVar5)
(00008C09 77		>=)
(00008C0A 35		not)
(00008C0B 60 253 254		T->JMP 00008B0B)
(00008C0E 5 0		UnVar0)
(00008C10 81 1 126 1 1 0		get-output-stream-string)
(00008C16 22		ret)
;;;def nil 35863
(00008C17 20 12 4 4 0)
(00008C1C 5 0		UnVar0)
(00008C1E 40		car)
(00008C1F 8 4		UnVar4)
(00008C21 5 0		UnVar0)
(00008C23 41		cdr)
(00008C24 40		car)
(00008C25 8 5		UnVar5)
(00008C27 5 0		UnVar0)
(00008C29 41		cdr)
(00008C2A 41		cdr)
(00008C2B 40		car)
(00008C2C 8 6		UnVar6)
(00008C2E 81 0 159 1 1 0		make-string-output-stream)
(00008C34 8 7		UnVar7)
(00008C36 5 1		UnVar1)
(00008C38 9 87 3		'caption)
(00008C3B 81 2 86 3 1 0		slot-value)
(00008C41 8 8		UnVar8)
(00008C43 50 0		0)
(00008C45 8 9		UnVar9)
(00008C47 5 3		UnVar3)
(00008C49 50 2		2)
(00008C4B 81 2 103 0 1 0		/)
(00008C51 8 10		UnVar10)
(00008C53 5 4		UnVar4)
(00008C55 13 16 0		nil->JMP 00008C68)
(00008C58 5 7		UnVar7)
(00008C5A 5 4		UnVar4)
(00008C5C 5 8		UnVar8)
(00008C5E 5 2		UnVar2)
(00008C60 95 4 239 138 0 0		func 00008AEF)
(00008C66 8 4		UnVar4)
(00008C68 5 6		UnVar6)
(00008C6A 13 16 0		nil->JMP 00008C7D)
(00008C6D 5 7		UnVar7)
(00008C6F 5 6		UnVar6)
(00008C71 5 8		UnVar8)
(00008C73 5 2		UnVar2)
(00008C75 95 4 239 138 0 0		func 00008AEF)
(00008C7B 8 6		UnVar6)
(00008C7D 5 5		UnVar5)
(00008C7F 13 16 0		nil->JMP 00008C92)
(00008C82 5 7		UnVar7)
(00008C84 5 5		UnVar5)
(00008C86 5 8		UnVar8)
(00008C88 5 2		UnVar2)
(00008C8A 95 4 239 138 0 0		func 00008AEF)
(00008C90 8 5		UnVar5)
(00008C92 5 4		UnVar4)
(00008C94 13 21 0		nil->JMP 00008CAC)
(00008C97 5 4		UnVar4)
(00008C99 5 7		UnVar7)
(00008C9B 81 2 127 3 1 0		princ)
(00008CA1 10)
(00008CA2 5 4		UnVar4)
(00008CA4 81 1 93 2 1 0		string-length)
(00008CAA 8 9		UnVar9)
(00008CAC 5 5		UnVar5)
(00008CAE 13 92 0		nil->JMP 00008D0D)
(00008CB1 5 10		UnVar10)
(00008CB3 5 5		UnVar5)
(00008CB5 81 1 93 2 1 0		string-length)
(00008CBB 50 2		2)
(00008CBD 81 2 103 0 1 0		/)
(00008CC3 71		-)
(00008CC4 8 10		UnVar10)
(00008CC6 5 9		UnVar9)
(00008CC8 5 10		UnVar10)
(00008CCA 81 2 79 2 1 0		<)
(00008CD0 13 34 0		nil->JMP 00008CF5)
(00008CD3 5 10		UnVar10)
(00008CD5 5 9		UnVar9)
(00008CD7 71		-)
(00008CD8 8 11		UnVar11)
(00008CDA 15 16 0		JMP 00008CED)
(00008CDD 50 32		32)
(00008CDF 5 7		UnVar7)
(00008CE1 81 2 107 0 1 0		write-char)
(00008CE7 10)
(00008CE8 5 11		UnVar11)
(00008CEA 80		1-)
(00008CEB 8 11		UnVar11)
(00008CED 5 11		UnVar11)
(00008CEF 50 0		0)
(00008CF1 75		>)
(00008CF2 60 232 255		T->JMP 00008CDD)
(00008CF5 5 5		UnVar5)
(00008CF7 5 7		UnVar7)
(00008CF9 81 2 127 3 1 0		princ)
(00008CFF 10)
(00008D00 5 10		UnVar10)
(00008D02 5 5		UnVar5)
(00008D04 81 1 93 2 1 0		string-length)
(00008D0A 70		+)
(00008D0B 8 9		UnVar9)
(00008D0D 5 6		UnVar6)
(00008D0F 13 71 0		nil->JMP 00008D59)
(00008D12 5 9		UnVar9)
(00008D14 5 3		UnVar3)
(00008D16 5 6		UnVar6)
(00008D18 81 1 93 2 1 0		string-length)
(00008D1E 71		-)
(00008D1F 76		<)
(00008D20 13 43 0		nil->JMP 00008D4E)
(00008D23 5 3		UnVar3)
(00008D25 5 6		UnVar6)
(00008D27 81 1 93 2 1 0		string-length)
(00008D2D 71		-)
(00008D2E 5 9		UnVar9)
(00008D30 71		-)
(00008D31 8 11		UnVar11)
(00008D33 15 16 0		JMP 00008D46)
(00008D36 50 32		32)
(00008D38 5 7		UnVar7)
(00008D3A 81 2 107 0 1 0		write-char)
(00008D40 10)
(00008D41 5 11		UnVar11)
(00008D43 80		1-)
(00008D44 8 11		UnVar11)
(00008D46 5 11		UnVar11)
(00008D48 50 0		0)
(00008D4A 75		>)
(00008D4B 60 232 255		T->JMP 00008D36)
(00008D4E 5 6		UnVar6)
(00008D50 5 7		UnVar7)
(00008D52 81 2 127 3 1 0		princ)
(00008D58 10)
(00008D59 5 7		UnVar7)
(00008D5B 81 1 126 1 1 0		get-output-stream-string)
(00008D61 22		ret)
;;;def _print-header-hook 36194
(00008D62 20 3 3 3 0)
(00008D67 3 122 0		*printer-header*)
(00008D6A 41		cdr)
(00008D6B 5 0		UnVar0)
(00008D6D 5 1		UnVar1)
(00008D6F 5 2		UnVar2)
(00008D71 96 4 23 140 0 0		func 00008C17)
;;;def _print-footer-hook 36215
(00008D77 20 3 3 3 0)
(00008D7C 3 118 0		*printer-footer*)
(00008D7F 41		cdr)
(00008D80 5 0		UnVar0)
(00008D82 5 1		UnVar1)
(00008D84 5 2		UnVar2)
(00008D86 96 4 23 140 0 0		func 00008C17)
;;;def *print-file-hook* 36236
(00008D8C 20 1 0 0 0)
(00008D91 100 0		UNVar0)
(00008D93 9 107 3		"VLMSG.DLL")
(00008D96 51 80 90 0 0		23120)
(00008D9B 81 2 106 3 1 0		string-resource)
(00008DA1 9 107 3		"VLMSG.DLL")
(00008DA4 51 90 90 0 0		23130)
(00008DA9 81 2 106 3 1 0		string-resource)
(00008DAF 9 102 0		"*.prn")
(00008DB2 57 2 0		list)
(00008DB5 1		nil)
(00008DB6 81 3 173 2 1 0		choose-file-dialog)
(00008DBC 8 0		UnVar0)
(00008DBE 5 0		UnVar0)
(00008DC0 63		nil->ret)
(00008DC1 5 0		UnVar0)
(00008DC3 47 1 172 0 32 32		_filename4save)
;;;def nil 36297
(00008DC9 20 11 7 7 0)
(00008DCE 100 7		UNVar7)
(00008DD0 100 8		UNVar8)
(00008DD2 100 9		UNVar9)
(00008DD4 5 0		UnVar0)
(00008DD6 8 10		UnVar10)
(00008DD8 9 41 3		"")
(00008DDB 5 10		UnVar10)
(00008DDD 45 0		IDFun0)
(00008DDF 10)
(00008DE0 5 5		UnVar5)
(00008DE2 9 101 0		':FL)
(00008DE5 38		=)
(00008DE6 13 27 0		nil->JMP 00008E04)
(00008DE9 5 0		UnVar0)
(00008DEB 3 100 0		*TB_DLG-FL-BORDER*)
(00008DEE 81 2 99 0 1 0		dialog._border-style<-)
(00008DF4 10)
(00008DF5 5 0		UnVar0)
(00008DF7 3 98 0		*WS_TB-FLOAT-STYLE*)
(00008DFA 81 2 97 0 1 0		dialog._msw-style<-)
(00008E00 10)
(00008E01 15 39 0		JMP 00008E2B)
(00008E04 5 0		UnVar0)
(00008E06 5 5		UnVar5)
(00008E08 9 250 0		':H)
(00008E0B 38		=)
(00008E0C 13 6 0		nil->JMP 00008E15)
(00008E0F 3 96 0		*TB_DLG-H-BORDER*)
(00008E12 15 3 0		JMP 00008E18)
(00008E15 3 95 0		*TB_DLG-V-BORDER*)
(00008E18 81 2 99 0 1 0		dialog._border-style<-)
(00008E1E 10)
(00008E1F 5 0		UnVar0)
(00008E21 3 94 0		*WS_TB-RIBBON-STYLE*)
(00008E24 81 2 97 0 1 0		dialog._msw-style<-)
(00008E2A 10)
(00008E2B 5 0		UnVar0)
(00008E2D 9 93 0		':COLOR_BTNFACE)
(00008E30 53 1 92 0 1 32		sys-color)
(00008E36 81 2 91 0 1 0		dialog.bcolor<-)
(00008E3C 10)
(00008E3D 5 5		UnVar5)
(00008E3F 9 101 0		':FL)
(00008E42 38		=)
(00008E43 13 127 0		nil->JMP 00008EC5)
(00008E46 50 40		40)
(00008E48 50 16		16)
(00008E4A 53 1 245 2 1 32		auto-scale-y)
(00008E50 81 2 249 2 1 0		make-ipoint)
(00008E56 5 3		UnVar3)
(00008E58 9 14 1		':LEFT)
(00008E5B 53 3 13 1 1 32		static-text)
(00008E61 8 7		UnVar7)
(00008E63 5 7		UnVar7)
(00008E65 2		T)
(00008E66 81 2 90 0 1 0		dialog-item.has-pix-pos<-)
(00008E6C 10)
(00008E6D 5 7		UnVar7)
(00008E6F 2		T)
(00008E70 81 2 105 1 1 0		dialog-item.has-pix-size<-)
(00008E76 10)
(00008E77 5 7		UnVar7)
(00008E79 2		T)
(00008E7A 81 2 111 1 1 0		dialog-item.color-enabled<-)
(00008E80 10)
(00008E81 5 7		UnVar7)
(00008E83 9 89 0		':COLOR_CAPTIONTEXT)
(00008E86 53 1 92 0 1 32		sys-color)
(00008E8C 81 2 113 1 1 0		dialog-item.fcolor<-)
(00008E92 10)
(00008E93 5 7		UnVar7)
(00008E95 9 88 0		':COLOR_ACTIVECAPTION)
(00008E98 53 1 92 0 1 32		sys-color)
(00008E9E 81 2 112 1 1 0		dialog-item.bcolor<-)
(00008EA4 10)
(00008EA5 9 87 0		':VR)
(00008EA8 9 250 0		':H)
(00008EAB 5 7		UnVar7)
(00008EAD 9 103 1		':V)
(00008EB0 50 3		3)
(00008EB2 3 86 0		*close-dlg-bmp-pb*)
(00008EB5 57 3 0		list)
(00008EB8 57 3 0		list)
(00008EBB 5 4		UnVar4)
(00008EBD 57 3 0		list)
(00008EC0 8 4		UnVar4)
(00008EC2 15 60 0		JMP 00008F01)
(00008EC5 5 5		UnVar5)
(00008EC7 9 250 0		':H)
(00008ECA 38		=)
(00008ECB 13 27 0		nil->JMP 00008EE9)
(00008ECE 9 103 1		':V)
(00008ED1 50 2		2)
(00008ED3 9 250 0		':H)
(00008ED6 50 2		2)
(00008ED8 5 4		UnVar4)
(00008EDA 50 2		2)
(00008EDC 57 4 0		list)
(00008EDF 50 2		2)
(00008EE1 57 4 0		list)
(00008EE4 8 4		UnVar4)
(00008EE6 15 24 0		JMP 00008F01)
(00008EE9 9 103 1		':V)
(00008EEC 50 2		2)
(00008EEE 9 250 0		':H)
(00008EF1 50 2		2)
(00008EF3 5 4		UnVar4)
(00008EF5 50 2		2)
(00008EF7 57 4 0		list)
(00008EFA 50 2		2)
(00008EFC 57 4 0		list)
(00008EFF 8 4		UnVar4)
(00008F01 50 0		0)
(00008F03 50 0		0)
(00008F05 42		cons)
(00008F06 8 8		UnVar8)
(00008F08 5 4		UnVar4)
(00008F0A 50 0		0)
(00008F0C 5 8		UnVar8)
(00008F0E 53 3 85 0 1 32		di-fmt-pos-alist)
(00008F14 81 1 12 3 1 0		nreverse)
(00008F1A 5 10		UnVar10)
(00008F1C 45 5		IDFun5)
(00008F1E 10)
(00008F1F 5 2		UnVar2)
(00008F21 14 12 0		T->JMP 00008F30)
(00008F24 5 8		UnVar8)
(00008F26 40		car)
(00008F27 5 8		UnVar8)
(00008F29 41		cdr)
(00008F2A 81 2 249 2 1 0		make-ipoint)
(00008F30 5 10		UnVar10)
(00008F32 45 2		IDFun2)
(00008F34 10)
(00008F35 5 7		UnVar7)
(00008F37 13 55 0		nil->JMP 00008F71)
(00008F3A 5 7		UnVar7)
(00008F3C 5 8		UnVar8)
(00008F3E 40		car)
(00008F3F 50 16		16)
(00008F41 53 1 245 2 1 32		auto-scale-y)
(00008F47 81 2 249 2 1 0		make-ipoint)
(00008F4D 9 254 2		'size)
(00008F50 81 3 78 3 1 0		slot-value<-)
(00008F56 10)
(00008F57 5 10		UnVar10)
(00008F59 44 5		IDFun5)
(00008F5B 40		car)
(00008F5C 8 9		UnVar9)
(00008F5E 5 9		UnVar9)
(00008F60 50 1		1)
(00008F62 50 1		1)
(00008F64 81 2 249 2 1 0		make-ipoint)
(00008F6A 81 2 225 2 1 0		setcdr)
(00008F70 10)
(00008F71 5 1		UnVar1)
(00008F73 13 7 0		nil->JMP 00008F7D)
(00008F76 5 1		UnVar1)
(00008F78 5 10		UnVar10)
(00008F7A 45 1		IDFun1)
(00008F7C 10)
(00008F7D 5 5		UnVar5)
(00008F7F 9 101 0		':FL)
(00008F82 38		=)
(00008F83 13 18 0		nil->JMP 00008F98)
(00008F86 9 84 0		"SansSerif")
(00008F89 5 10		UnVar10)
(00008F8B 45 3		IDFun3)
(00008F8D 10)
(00008F8E 50 9		9)
(00008F90 5 10		UnVar10)
(00008F92 45 4		IDFun4)
(00008F94 10)
(00008F95 15 15 0		JMP 00008FA7)
(00008F98 9 83 0		"System")
(00008F9B 5 10		UnVar10)
(00008F9D 45 3		IDFun3)
(00008F9F 10)
(00008FA0 50 9		9)
(00008FA2 5 10		UnVar10)
(00008FA4 45 4		IDFun4)
(00008FA6 10)
(00008FA7 5 6		UnVar6)
(00008FA9 13 7 0		nil->JMP 00008FB3)
(00008FAC 5 6		UnVar6)
(00008FAE 5 10		UnVar10)
(00008FB0 45 7		IDFun7)
(00008FB2 10)
(00008FB3 5 0		UnVar0)
(00008FB5 22		ret)
;;;def nil 36790
(00008FB6 20 6 6 6 0)
(00008FBB 9 82 0		'toolbar-multydialog)
(00008FBE 53 1 81 0 1 32		allocate-instance)
(00008FC4 5 0		UnVar0)
(00008FC6 5 1		UnVar1)
(00008FC8 5 2		UnVar2)
(00008FCA 5 3		UnVar3)
(00008FCC 5 4		UnVar4)
(00008FCE 5 5		UnVar5)
(00008FD0 96 7 201 141 0 0		func 00008DC9)
;;;def nil 36822
(00008FD6 20 3 1 1 0)
(00008FDB 5 0		UnVar0)
(00008FDD 37 3		symbolp)
(00008FDF 13 9 0		nil->JMP 00008FEB)
(00008FE2 5 0		UnVar0)
(00008FE4 81 1 226 2 1 0		symbol-value)
(00008FEA 22		ret)
(00008FEB 5 0		UnVar0)
(00008FED 36		atom)
(00008FEE 13 3 0		nil->JMP 00008FF4)
(00008FF1 5 0		UnVar0)
(00008FF3 22		ret)
(00008FF4 5 0		UnVar0)
(00008FF6 8 1		UnVar1)
(00008FF8 100 2		UNVar2)
(00008FFA 15 19 0		JMP 00009010)
(00008FFD 5 1		UnVar1)
(00008FFF 40		car)
(00009000 95 1 214 143 0 0		func 00008FD6)
(00009006 5 2		UnVar2)
(00009008 42		cons)
(00009009 8 2		UnVar2)
(0000900B 5 1		UnVar1)
(0000900D 41		cdr)
(0000900E 8 1		UnVar1)
(00009010 5 1		UnVar1)
(00009012 60 232 255		T->JMP 00008FFD)
(00009015 5 2		UnVar2)
(00009017 81 1 12 3 1 0		nreverse)
(0000901D 22		ret)
;;;def nil 36894
(0000901E 20 2 2 2 0)
(00009023 5 0		UnVar0)
(00009025 61 7 0		nil->JMP 0000902F)
(00009028 5 0		UnVar0)
(0000902A 41		cdr)
(0000902B 40		car)
(0000902C 5 1		UnVar1)
(0000902E 38		=)
(0000902F 13 16 0		nil->JMP 00009042)
(00009032 5 0		UnVar0)
(00009034 41		cdr)
(00009035 41		cdr)
(00009036 40		car)
(00009037 5 0		UnVar0)
(00009039 40		car)
(0000903A 5 0		UnVar0)
(0000903C 41		cdr)
(0000903D 41		cdr)
(0000903E 41		cdr)
(0000903F 42		cons)
(00009040 42		cons)
(00009041 22		ret)
(00009042 1		nil)
(00009043 5 0		UnVar0)
(00009045 42		cons)
(00009046 22		ret)
;;;def register-toolbar-multidialog 36935
(00009047 20 21 3 4 0)
(0000904C 100 4		UNVar4)
(0000904E 100 5		UNVar5)
(00009050 100 6		UNVar6)
(00009052 100 7		UNVar7)
(00009054 100 8		UNVar8)
(00009056 100 9		UNVar9)
(00009058 100 10		UNVar10)
(0000905A 100 11		UNVar11)
(0000905C 100 12		UNVar12)
(0000905E 100 13		UNVar13)
(00009060 100 14		UNVar14)
(00009062 100 15		UNVar15)
(00009064 100 16		UNVar16)
(00009066 100 17		UNVar17)
(00009068 100 18		UNVar18)
(0000906A 5 0		UnVar0)
(0000906C 95 1 214 143 0 0		func 00008FD6)
(00009072 8 0		UnVar0)
(00009074 5 0		UnVar0)
(00009076 40		car)
(00009077 8 19		UnVar19)
(00009079 5 0		UnVar0)
(0000907B 41		cdr)
(0000907C 8 0		UnVar0)
(0000907E 5 19		UnVar19)
(00009080 8 18		UnVar18)
(00009082 9 101 0		':FL)
(00009085 5 0		UnVar0)
(00009087 81 2 16 3 1 0		assq)
(0000908D 8 17		UnVar17)
(0000908F 9 250 0		':H)
(00009092 5 0		UnVar0)
(00009094 81 2 16 3 1 0		assq)
(0000909A 8 16		UnVar16)
(0000909C 9 103 1		':V)
(0000909F 5 0		UnVar0)
(000090A1 81 2 16 3 1 0		assq)
(000090A7 8 15		UnVar15)
(000090A9 5 16		UnVar16)
(000090AB 9 80 0		':SIZE)
(000090AE 95 2 30 144 0 0		func 0000901E)
(000090B4 8 19		UnVar19)
(000090B6 5 19		UnVar19)
(000090B8 40		car)
(000090B9 8 14		UnVar14)
(000090BB 5 19		UnVar19)
(000090BD 41		cdr)
(000090BE 8 16		UnVar16)
(000090C0 5 15		UnVar15)
(000090C2 9 80 0		':SIZE)
(000090C5 95 2 30 144 0 0		func 0000901E)
(000090CB 8 19		UnVar19)
(000090CD 5 19		UnVar19)
(000090CF 40		car)
(000090D0 8 13		UnVar13)
(000090D2 5 19		UnVar19)
(000090D4 41		cdr)
(000090D5 8 15		UnVar15)
(000090D7 5 17		UnVar17)
(000090D9 9 80 0		':SIZE)
(000090DC 95 2 30 144 0 0		func 0000901E)
(000090E2 8 19		UnVar19)
(000090E4 5 19		UnVar19)
(000090E6 40		car)
(000090E7 8 12		UnVar12)
(000090E9 5 19		UnVar19)
(000090EB 41		cdr)
(000090EC 8 17		UnVar17)
(000090EE 5 16		UnVar16)
(000090F0 9 98 1		':DEFAULT-PUSH-BUTTON)
(000090F3 95 2 30 144 0 0		func 0000901E)
(000090F9 8 19		UnVar19)
(000090FB 5 19		UnVar19)
(000090FD 40		car)
(000090FE 8 11		UnVar11)
(00009100 5 19		UnVar19)
(00009102 41		cdr)
(00009103 8 16		UnVar16)
(00009105 5 15		UnVar15)
(00009107 9 98 1		':DEFAULT-PUSH-BUTTON)
(0000910A 95 2 30 144 0 0		func 0000901E)
(00009110 8 19		UnVar19)
(00009112 5 19		UnVar19)
(00009114 40		car)
(00009115 8 10		UnVar10)
(00009117 5 19		UnVar19)
(00009119 41		cdr)
(0000911A 8 15		UnVar15)
(0000911C 5 17		UnVar17)
(0000911E 9 98 1		':DEFAULT-PUSH-BUTTON)
(00009121 95 2 30 144 0 0		func 0000901E)
(00009127 8 19		UnVar19)
(00009129 5 19		UnVar19)
(0000912B 40		car)
(0000912C 8 9		UnVar9)
(0000912E 5 19		UnVar19)
(00009130 41		cdr)
(00009131 8 17		UnVar17)
(00009133 5 17		UnVar17)
(00009135 13 3 0		nil->JMP 0000913B)
(00009138 15 10 0		JMP 00009145)
(0000913B 9 101 0		':FL)
(0000913E 5 16		UnVar16)
(00009140 57 2 0		list)
(00009143 8 17		UnVar17)
(00009145 5 15		UnVar15)
(00009147 13 3 0		nil->JMP 0000914D)
(0000914A 15 9 0		JMP 00009156)
(0000914D 9 103 1		':V)
(00009150 5 16		UnVar16)
(00009152 41		cdr)
(00009153 42		cons)
(00009154 8 15		UnVar15)
(00009156 1		nil)
(00009157 5 14		UnVar14)
(00009159 5 18		UnVar18)
(0000915B 5 16		UnVar16)
(0000915D 95 1 214 143 0 0		func 00008FD6)
(00009163 9 250 0		':H)
(00009166 5 11		UnVar11)
(00009168 95 1 214 143 0 0		func 00008FD6)
(0000916E 95 6 182 143 0 0		func 00008FB6)
(00009174 8 8		UnVar8)
(00009176 1		nil)
(00009177 5 13		UnVar13)
(00009179 5 18		UnVar18)
(0000917B 5 15		UnVar15)
(0000917D 95 1 214 143 0 0		func 00008FD6)
(00009183 9 103 1		':V)
(00009186 5 10		UnVar10)
(00009188 95 1 214 143 0 0		func 00008FD6)
(0000918E 95 6 182 143 0 0		func 00008FB6)
(00009194 8 7		UnVar7)
(00009196 1		nil)
(00009197 5 12		UnVar12)
(00009199 5 18		UnVar18)
(0000919B 5 17		UnVar17)
(0000919D 41		cdr)
(0000919E 40		car)
(0000919F 95 1 214 143 0 0		func 00008FD6)
(000091A5 9 101 0		':FL)
(000091A8 5 9		UnVar9)
(000091AA 95 1 214 143 0 0		func 00008FD6)
(000091B0 95 6 182 143 0 0		func 00008FB6)
(000091B6 8 6		UnVar6)
(000091B8 9 101 0		':FL)
(000091BB 5 6		UnVar6)
(000091BD 42		cons)
(000091BE 9 79 0		':HT)
(000091C1 5 8		UnVar8)
(000091C3 42		cons)
(000091C4 9 102 1		':HD)
(000091C7 5 8		UnVar8)
(000091C9 42		cons)
(000091CA 9 78 0		':VL)
(000091CD 5 7		UnVar7)
(000091CF 42		cons)
(000091D0 9 87 0		':VR)
(000091D3 5 7		UnVar7)
(000091D5 42		cons)
(000091D6 57 5 0		list)
(000091D9 8 4		UnVar4)
(000091DB 5 8		UnVar8)
(000091DD 5 7		UnVar7)
(000091DF 5 6		UnVar6)
(000091E1 57 3 0		list)
(000091E4 8 19		UnVar19)
(000091E6 100 20		UNVar20)
(000091E8 15 52 0		JMP 0000921F)
(000091EB 5 19		UnVar19)
(000091ED 40		car)
(000091EE 8 20		UnVar20)
(000091F0 5 19		UnVar19)
(000091F2 41		cdr)
(000091F3 8 19		UnVar19)
(000091F5 5 20		UnVar20)
(000091F7 5 1		UnVar1)
(000091F9 9 77 0		'register-symbol)
(000091FC 81 3 78 3 1 0		slot-value<-)
(00009202 10)
(00009203 5 20		UnVar20)
(00009205 5 3		UnVar3)
(00009207 9 76 0		'update-on-idle)
(0000920A 81 3 78 3 1 0		slot-value<-)
(00009210 10)
(00009211 5 20		UnVar20)
(00009213 5 4		UnVar4)
(00009215 9 75 0		'states)
(00009218 81 3 78 3 1 0		slot-value<-)
(0000921E 10)
(0000921F 5 19		UnVar19)
(00009221 60 199 255		T->JMP 000091EB)
(00009224 5 2		UnVar2)
(00009226 37 2		consp)
(00009228 13 27 0		nil->JMP 00009246)
(0000922B 5 2		UnVar2)
(0000922D 41		cdr)
(0000922E 8 5		UnVar5)
(00009230 9 101 0		':FL)
(00009233 8 2		UnVar2)
(00009235 5 5		UnVar5)
(00009237 9 101 0		':FL)
(0000923A 5 4		UnVar4)
(0000923C 81 2 15 1 1 0		assoc)
(00009242 41		cdr)
(00009243 45 1		IDFun1)
(00009245 10)
(00009246 5 1		UnVar1)
(00009248 5 2		UnVar2)
(0000924A 5 4		UnVar4)
(0000924C 81 2 15 1 1 0		assoc)
(00009252 41		cdr)
(00009253 81 2 140 0 1 0		set)
(00009259 22		ret)
;;;def nil 37466
(0000925A 20 4 1 1 0)
(0000925F 100 1		UNVar1)
(00009261 100 2		UNVar2)
(00009263 5 0		UnVar0)
(00009265 8 3		UnVar3)
(00009267 5 0		UnVar0)
(00009269 53 1 103 3 1 32		host-spouse-exists-p)
(0000926F 63		nil->ret)
(00009270 5 0		UnVar0)
(00009272 5 3		UnVar3)
(00009274 44 9		IDFun9)
(00009276 81 2 240 0 1 0		rassoc)
(0000927C 8 1		UnVar1)
(0000927E 5 1		UnVar1)
(00009280 9 74 0		"Illegal toolbar dialog state")
(00009283 53 2 17 3 1 32		assert)
(00009289 10)
(0000928A 5 1		UnVar1)
(0000928C 9 101 0		':FL)
(0000928F 81 2 8 3 1 0		eqcar)
(00009295 13 10 0		nil->JMP 000092A2)
(00009298 5 3		UnVar3)
(0000929A 44 11		IDFun11)
(0000929C 5 3		UnVar3)
(0000929E 44 1		IDFun1)
(000092A0 42		cons)
(000092A1 22		ret)
(000092A2 5 3		UnVar3)
(000092A4 44 11		IDFun11)
(000092A6 22		ret)
;;;def desktop-save-toolbar 37543
(000092A7 20 10 0 0 0)
(000092AC 100 0		UNVar0)
(000092AE 100 1		UNVar1)
(000092B0 100 2		UNVar2)
(000092B2 100 3		UNVar3)
(000092B4 3 73 0		*toolbars-list*)
(000092B7 8 4		UnVar4)
(000092B9 100 5		UNVar5)
(000092BB 15 51 0		JMP 000092F1)
(000092BE 5 4		UnVar4)
(000092C0 40		car)
(000092C1 8 5		UnVar5)
(000092C3 5 4		UnVar4)
(000092C5 41		cdr)
(000092C6 8 4		UnVar4)
(000092C8 5 5		UnVar5)
(000092CA 41		cdr)
(000092CB 40		car)
(000092CC 81 1 226 2 1 0		symbol-value)
(000092D2 8 3		UnVar3)
(000092D4 5 3		UnVar3)
(000092D6 13 10 0		nil->JMP 000092E3)
(000092D9 5 3		UnVar3)
(000092DB 95 1 90 146 0 0		func 0000925A)
(000092E1 8 0		UnVar0)
(000092E3 5 0		UnVar0)
(000092E5 37 2		consp)
(000092E7 13 7 0		nil->JMP 000092F1)
(000092EA 5 0		UnVar0)
(000092EC 5 2		UnVar2)
(000092EE 42		cons)
(000092EF 8 2		UnVar2)
(000092F1 5 4		UnVar4)
(000092F3 60 200 255		T->JMP 000092BE)
(000092F6 81 0 72 0 1 0		get-tool-bar)
(000092FC 8 4		UnVar4)
(000092FE 100 5		UNVar5)
(00009300 15 70 0		JMP 00009349)
(00009303 5 4		UnVar4)
(00009305 40		car)
(00009306 8 6		UnVar6)
(00009308 5 6		UnVar6)
(0000930A 40		car)
(0000930B 5 6		UnVar6)
(0000930D 41		cdr)
(0000930E 8 7		UnVar7)
(00009310 100 8		UNVar8)
(00009312 15 28 0		JMP 00009331)
(00009315 5 7		UnVar7)
(00009317 40		car)
(00009318 8 9		UnVar9)
(0000931A 5 9		UnVar9)
(0000931C 40		car)
(0000931D 5 9		UnVar9)
(0000931F 41		cdr)
(00009320 95 1 90 146 0 0		func 0000925A)
(00009326 42		cons)
(00009327 5 8		UnVar8)
(00009329 42		cons)
(0000932A 8 8		UnVar8)
(0000932C 5 7		UnVar7)
(0000932E 41		cdr)
(0000932F 8 7		UnVar7)
(00009331 5 7		UnVar7)
(00009333 60 223 255		T->JMP 00009315)
(00009336 5 8		UnVar8)
(00009338 81 1 12 3 1 0		nreverse)
(0000933E 42		cons)
(0000933F 5 5		UnVar5)
(00009341 42		cons)
(00009342 8 5		UnVar5)
(00009344 5 4		UnVar4)
(00009346 41		cdr)
(00009347 8 4		UnVar4)
(00009349 5 4		UnVar4)
(0000934B 60 181 255		T->JMP 00009303)
(0000934E 5 5		UnVar5)
(00009350 81 1 12 3 1 0		nreverse)
(00009356 8 1		UnVar1)
(00009358 9 71 0		':TOOLBAR)
(0000935B 5 1		UnVar1)
(0000935D 9 101 0		':FL)
(00009360 5 2		UnVar2)
(00009362 81 1 12 3 1 0		nreverse)
(00009368 57 4 0		list)
(0000936B 22		ret)
;;;def desktop-restore-toolbar 37740
(0000936C 20 9 1 1 0)
(00009371 100 1		UNVar1)
(00009373 100 2		UNVar2)
(00009375 5 0		UnVar0)
(00009377 9 71 0		':TOOLBAR)
(0000937A 81 2 129 3 1 0		getf)
(00009380 8 3		UnVar3)
(00009382 100 4		UNVar4)
(00009384 15 79 0		JMP 000093D6)
(00009387 5 3		UnVar3)
(00009389 40		car)
(0000938A 8 5		UnVar5)
(0000938C 5 5		UnVar5)
(0000938E 40		car)
(0000938F 5 5		UnVar5)
(00009391 41		cdr)
(00009392 8 6		UnVar6)
(00009394 100 7		UNVar7)
(00009396 15 37 0		JMP 000093BE)
(00009399 5 6		UnVar6)
(0000939B 40		car)
(0000939C 8 8		UnVar8)
(0000939E 5 8		UnVar8)
(000093A0 40		car)
(000093A1 5 8		UnVar8)
(000093A3 41		cdr)
(000093A4 81 1 226 2 1 0		symbol-value)
(000093AA 5 5		UnVar5)
(000093AC 40		car)
(000093AD 95 2 226 148 0 0		func 000094E2)
(000093B3 42		cons)
(000093B4 5 7		UnVar7)
(000093B6 42		cons)
(000093B7 8 7		UnVar7)
(000093B9 5 6		UnVar6)
(000093BB 41		cdr)
(000093BC 8 6		UnVar6)
(000093BE 5 6		UnVar6)
(000093C0 60 214 255		T->JMP 00009399)
(000093C3 5 7		UnVar7)
(000093C5 81 1 12 3 1 0		nreverse)
(000093CB 42		cons)
(000093CC 5 4		UnVar4)
(000093CE 42		cons)
(000093CF 8 4		UnVar4)
(000093D1 5 3		UnVar3)
(000093D3 41		cdr)
(000093D4 8 3		UnVar3)
(000093D6 5 3		UnVar3)
(000093D8 60 172 255		T->JMP 00009387)
(000093DB 5 4		UnVar4)
(000093DD 81 1 12 3 1 0		nreverse)
(000093E3 8 2		UnVar2)
(000093E5 5 2		UnVar2)
(000093E7 81 1 70 0 1 0		attach-tool-bar)
(000093ED 10)
(000093EE 5 0		UnVar0)
(000093F0 9 101 0		':FL)
(000093F3 81 2 129 3 1 0		getf)
(000093F9 8 3		UnVar3)
(000093FB 100 4		UNVar4)
(000093FD 15 48 0		JMP 00009430)
(00009400 5 3		UnVar3)
(00009402 40		car)
(00009403 8 4		UnVar4)
(00009405 5 3		UnVar3)
(00009407 41		cdr)
(00009408 8 3		UnVar3)
(0000940A 5 4		UnVar4)
(0000940C 40		car)
(0000940D 81 1 226 2 1 0		symbol-value)
(00009413 9 101 0		':FL)
(00009416 95 2 226 148 0 0		func 000094E2)
(0000941C 8 1		UnVar1)
(0000941E 5 4		UnVar4)
(00009420 41		cdr)
(00009421 5 1		UnVar1)
(00009423 45 1		IDFun1)
(00009425 10)
(00009426 5 1		UnVar1)
(00009428 1		nil)
(00009429 53 2 101 3 1 32		create-host-spouse)
(0000942F 10)
(00009430 5 3		UnVar3)
(00009432 60 203 255		T->JMP 00009400)
(00009435 2		T)
(00009436 22		ret)
;;;def nil 37943
(00009437 20 1 1 1 0)
(0000943C 5 0		UnVar0)
(0000943E 95 1 90 146 0 0		func 0000925A)
(00009444 37 2		consp)
(00009446 13 16 0		nil->JMP 00009459)
(00009449 5 0		UnVar0)
(0000944B 53 1 94 3 1 32		destroy-host-spouse)
(00009451 10)
(00009452 81 0 72 0 1 0		get-tool-bar)
(00009458 22		ret)
(00009459 5 0		UnVar0)
(0000945B 81 0 72 0 1 0		get-tool-bar)
(00009461 96 2 103 148 0 0		func 00009467)
;;;def nil 37991
(00009467 20 7 2 2 0)
(0000946C 100 2		UNVar2)
(0000946E 100 3		UNVar3)
(00009470 5 1		UnVar1)
(00009472 8 4		UnVar4)
(00009474 100 5		UNVar5)
(00009476 15 56 0		JMP 000094B1)
(00009479 5 4		UnVar4)
(0000947B 40		car)
(0000947C 8 6		UnVar6)
(0000947E 5 0		UnVar0)
(00009480 5 6		UnVar6)
(00009482 41		cdr)
(00009483 81 2 240 0 1 0		rassoc)
(00009489 11)
(0000948A 8 3		UnVar3)
(0000948C 13 22 0		nil->JMP 000094A5)
(0000948F 5 3		UnVar3)
(00009491 5 6		UnVar6)
(00009493 41		cdr)
(00009494 81 2 35 1 1 0		remove)
(0000949A 8 2		UnVar2)
(0000949C 5 6		UnVar6)
(0000949E 40		car)
(0000949F 5 2		UnVar2)
(000094A1 42		cons)
(000094A2 15 2 0		JMP 000094A7)
(000094A5 5 6		UnVar6)
(000094A7 5 5		UnVar5)
(000094A9 42		cons)
(000094AA 8 5		UnVar5)
(000094AC 5 4		UnVar4)
(000094AE 41		cdr)
(000094AF 8 4		UnVar4)
(000094B1 5 4		UnVar4)
(000094B3 60 195 255		T->JMP 00009479)
(000094B6 5 5		UnVar5)
(000094B8 81 1 12 3 1 0		nreverse)
(000094BE 8 1		UnVar1)
(000094C0 9 69 0		'cdr)
(000094C3 5 1		UnVar1)
(000094C5 81 2 6 3 1 0		delete-if-not)
(000094CB 22		ret)
;;;def nil 38092
(000094CC 20 2 1 1 0)
(000094D1 5 0		UnVar0)
(000094D3 8 1		UnVar1)
(000094D5 5 1		UnVar1)
(000094D7 44 12		IDFun12)
(000094D9 63		nil->ret)
(000094DA 5 0		UnVar0)
(000094DC 5 1		UnVar1)
(000094DE 44 12		IDFun12)
(000094E0 46 1		invoke+ret)
;;;def nil 38114
(000094E2 20 4 2 2 0)
(000094E7 100 2		UNVar2)
(000094E9 5 0		UnVar0)
(000094EB 8 3		UnVar3)
(000094ED 5 1		UnVar1)
(000094EF 5 0		UnVar0)
(000094F1 9 75 0		'states)
(000094F4 81 2 86 3 1 0		slot-value)
(000094FA 81 2 15 1 1 0		assoc)
(00009500 8 2		UnVar2)
(00009502 5 2		UnVar2)
(00009504 41		cdr)
(00009505 5 0		UnVar0)
(00009507 38		=)
(00009508 13 3 0		nil->JMP 0000950E)
(0000950B 5 0		UnVar0)
(0000950D 22		ret)
(0000950E 5 3		UnVar3)
(00009510 44 11		IDFun11)
(00009512 5 2		UnVar2)
(00009514 41		cdr)
(00009515 81 2 140 0 1 0		set)
(0000951B 22		ret)
;;;def nil 38172
(0000951C 20 10 1 1 0)
(00009521 100 1		UNVar1)
(00009523 100 2		UNVar2)
(00009525 100 3		UNVar3)
(00009527 100 4		UNVar4)
(00009529 100 5		UNVar5)
(0000952B 100 6		UNVar6)
(0000952D 100 7		UNVar7)
(0000952F 100 8		UNVar8)
(00009531 5 0		UnVar0)
(00009533 9 68 0		'(:HT :HD :VL :VR))
(00009536 81 2 114 3 1 0		memq)
(0000953C 9 67 0		"Bad ribbon position")
(0000953F 53 2 17 3 1 32		assert)
(00009545 10)
(00009546 81 0 66 0 1 0		_mdiclient.apex-and-size)
(0000954C 8 9		UnVar9)
(0000954E 5 9		UnVar9)
(00009550 40		car)
(00009551 8 4		UnVar4)
(00009553 5 9		UnVar9)
(00009555 41		cdr)
(00009556 8 5		UnVar5)
(00009558 81 0 65 0 1 0		_frameclient.apex-and-size)
(0000955E 8 1		UnVar1)
(00009560 5 1		UnVar1)
(00009562 37 2		consp)
(00009564 13 12 0		nil->JMP 00009573)
(00009567 5 1		UnVar1)
(00009569 40		car)
(0000956A 8 3		UnVar3)
(0000956C 5 1		UnVar1)
(0000956E 41		cdr)
(0000956F 8 2		UnVar2)
(00009571 100 1		UNVar1)
(00009573 5 0		UnVar0)
(00009575 8 9		UnVar9)
(00009577 5 9		UnVar9)
(00009579 9 64 0		'(:HT :VL :HD))
(0000957C 81 2 114 3 1 0		memq)
(00009582 13 21 0		nil->JMP 0000959A)
(00009585 5 1		UnVar1)
(00009587 13 5 0		nil->JMP 0000958F)
(0000958A 50 0		0)
(0000958C 15 8 0		JMP 00009597)
(0000958F 5 3		UnVar3)
(00009591 81 1 253 2 1 0		ipoint-h)
(00009597 15 30 0		JMP 000095B8)
(0000959A 5 9		UnVar9)
(0000959C 9 87 0		':VR)
(0000959F 38		=)
(000095A0 13 20 0		nil->JMP 000095B7)
(000095A3 5 4		UnVar4)
(000095A5 81 1 253 2 1 0		ipoint-h)
(000095AB 5 5		UnVar5)
(000095AD 81 1 253 2 1 0		ipoint-h)
(000095B3 70		+)
(000095B4 15 1 0		JMP 000095B8)
(000095B7 1		nil)
(000095B8 8 8		UnVar8)
(000095BA 5 0		UnVar0)
(000095BC 8 9		UnVar9)
(000095BE 5 9		UnVar9)
(000095C0 9 79 0		':HT)
(000095C3 38		=)
(000095C4 13 40 0		nil->JMP 000095EF)
(000095C7 5 1		UnVar1)
(000095C9 13 24 0		nil->JMP 000095E4)
(000095CC 3 63 0		SM_CYMENU)
(000095CF 81 1 62 0 1 0		get-system-metrics)
(000095D5 53 0 61 0 1 32		_W-CAPTION_WIDTH)
(000095DB 81 2 39 2 1 0		+)
(000095E1 15 8 0		JMP 000095EC)
(000095E4 5 3		UnVar3)
(000095E6 81 1 251 2 1 0		ipoint-v)
(000095EC 15 60 0		JMP 0000962B)
(000095EF 5 9		UnVar9)
(000095F1 9 60 0		'(:VR :VL))
(000095F4 81 2 114 3 1 0		memq)
(000095FA 13 11 0		nil->JMP 00009608)
(000095FD 5 4		UnVar4)
(000095FF 81 1 251 2 1 0		ipoint-v)
(00009605 15 35 0		JMP 0000962B)
(00009608 5 9		UnVar9)
(0000960A 9 102 1		':HD)
(0000960D 38		=)
(0000960E 13 25 0		nil->JMP 0000962A)
(00009611 5 4		UnVar4)
(00009613 81 1 251 2 1 0		ipoint-v)
(00009619 5 5		UnVar5)
(0000961B 81 1 251 2 1 0		ipoint-v)
(00009621 81 2 39 2 1 0		+)
(00009627 15 1 0		JMP 0000962B)
(0000962A 1		nil)
(0000962B 8 7		UnVar7)
(0000962D 5 0		UnVar0)
(0000962F 8 9		UnVar9)
(00009631 5 9		UnVar9)
(00009633 9 59 0		'(:HT :HD))
(00009636 81 2 114 3 1 0		memq)
(0000963C 13 28 0		nil->JMP 0000965B)
(0000963F 5 1		UnVar1)
(00009641 13 12 0		nil->JMP 00009650)
(00009644 3 58 0		SM_CXSCREEN)
(00009647 81 1 62 0 1 0		get-system-metrics)
(0000964D 15 8 0		JMP 00009658)
(00009650 5 2		UnVar2)
(00009652 81 1 253 2 1 0		ipoint-h)
(00009658 15 26 0		JMP 00009675)
(0000965B 5 9		UnVar9)
(0000965D 9 57 0		'(:VL :VR))
(00009660 81 2 114 3 1 0		memq)
(00009666 13 11 0		nil->JMP 00009674)
(00009669 5 5		UnVar5)
(0000966B 81 1 251 2 1 0		ipoint-v)
(00009671 15 1 0		JMP 00009675)
(00009674 1		nil)
(00009675 8 6		UnVar6)
(00009677 5 8		UnVar8)
(00009679 5 7		UnVar7)
(0000967B 81 2 249 2 1 0		make-ipoint)
(00009681 5 6		UnVar6)
(00009683 42		cons)
(00009684 22		ret)
;;;def nil 38533
(00009685 20 5 1 1 0)
(0000968A 100 1		UNVar1)
(0000968C 100 2		UNVar2)
(0000968E 50 0		0)
(00009690 8 2		UnVar2)
(00009692 5 0		UnVar0)
(00009694 40		car)
(00009695 9 59 0		'(:HT :HD))
(00009698 81 2 114 3 1 0		memq)
(0000969E 13 6 0		nil->JMP 000096A7)
(000096A1 9 253 2		'ipoint-h)
(000096A4 15 3 0		JMP 000096AA)
(000096A7 9 251 2		'ipoint-v)
(000096AA 8 1		UnVar1)
(000096AC 5 0		UnVar0)
(000096AE 41		cdr)
(000096AF 8 3		UnVar3)
(000096B1 100 4		UNVar4)
(000096B3 15 43 0		JMP 000096E1)
(000096B6 5 3		UnVar3)
(000096B8 40		car)
(000096B9 8 4		UnVar4)
(000096BB 5 3		UnVar3)
(000096BD 41		cdr)
(000096BE 8 3		UnVar3)
(000096C0 5 2		UnVar2)
(000096C2 5 4		UnVar4)
(000096C4 40		car)
(000096C5 81 2 39 2 1 0		+)
(000096CB 8 2		UnVar2)
(000096CD 5 2		UnVar2)
(000096CF 5 4		UnVar4)
(000096D1 41		cdr)
(000096D2 44 2		IDFun2)
(000096D4 5 1		UnVar1)
(000096D6 52 1 1		)
(000096D9 81 2 39 2 1 0		+)
(000096DF 8 2		UnVar2)
(000096E1 5 3		UnVar3)
(000096E3 60 208 255		T->JMP 000096B6)
(000096E6 5 2		UnVar2)
(000096E8 22		ret)
;;;def nil 38633
(000096E9 20 11 1 1 0)
(000096EE 100 1		UNVar1)
(000096F0 100 2		UNVar2)
(000096F2 100 3		UNVar3)
(000096F4 100 4		UNVar4)
(000096F6 100 5		UNVar5)
(000096F8 100 6		UNVar6)
(000096FA 100 7		UNVar7)
(000096FC 100 8		UNVar8)
(000096FE 100 9		UNVar9)
(00009700 5 0		UnVar0)
(00009702 3 73 0		*toolbars-list*)
(00009705 81 2 16 3 1 0		assq)
(0000970B 8 9		UnVar9)
(0000970D 5 9		UnVar9)
(0000970F 41		cdr)
(00009710 41		cdr)
(00009711 40		car)
(00009712 8 7		UnVar7)
(00009714 5 9		UnVar9)
(00009716 41		cdr)
(00009717 40		car)
(00009718 81 1 226 2 1 0		symbol-value)
(0000971E 8 8		UnVar8)
(00009720 5 8		UnVar8)
(00009722 53 1 194 0 1 32		dialogp)
(00009728 9 56 0		"Toolbar dialog lost!")
(0000972B 53 2 17 3 1 32		assert)
(00009731 10)
(00009732 5 8		UnVar8)
(00009734 53 1 103 3 1 32		host-spouse-exists-p)
(0000973A 13 2 0		nil->JMP 0000973F)
(0000973D 1		nil)
(0000973E 22		ret)
(0000973F 5 8		UnVar8)
(00009741 5 7		UnVar7)
(00009743 95 2 226 148 0 0		func 000094E2)
(00009749 8 8		UnVar8)
(0000974B 81 0 72 0 1 0		get-tool-bar)
(00009751 8 6		UnVar6)
(00009753 5 6		UnVar6)
(00009755 81 1 55 0 1 0		reverse)
(0000975B 8 5		UnVar5)
(0000975D 5 7		UnVar7)
(0000975F 5 5		UnVar5)
(00009761 81 2 16 3 1 0		assq)
(00009767 8 4		UnVar4)
(00009769 5 7		UnVar7)
(0000976B 9 59 0		'(:HT :HD))
(0000976E 81 2 114 3 1 0		memq)
(00009774 13 20 0		nil->JMP 0000978B)
(00009777 5 8		UnVar8)
(00009779 9 254 2		'size)
(0000977C 81 2 86 3 1 0		slot-value)
(00009782 81 1 253 2 1 0		ipoint-h)
(00009788 15 17 0		JMP 0000979C)
(0000978B 5 8		UnVar8)
(0000978D 9 254 2		'size)
(00009790 81 2 86 3 1 0		slot-value)
(00009796 81 1 251 2 1 0		ipoint-v)
(0000979C 8 3		UnVar3)
(0000979E 5 7		UnVar7)
(000097A0 95 1 28 149 0 0		func 0000951C)
(000097A6 8 10		UnVar10)
(000097A8 5 10		UnVar10)
(000097AA 40		car)
(000097AB 8 1		UnVar1)
(000097AD 5 10		UnVar10)
(000097AF 41		cdr)
(000097B0 8 2		UnVar2)
(000097B2 5 4		UnVar4)
(000097B4 61 14 0		nil->JMP 000097C5)
(000097B7 5 3		UnVar3)
(000097B9 5 4		UnVar4)
(000097BB 95 1 133 150 0 0		func 00009685)
(000097C1 70		+)
(000097C2 5 2		UnVar2)
(000097C4 76		<)
(000097C5 13 31 0		nil->JMP 000097E7)
(000097C8 5 4		UnVar4)
(000097CA 50 4		4)
(000097CC 5 8		UnVar8)
(000097CE 42		cons)
(000097CF 57 1 0		list)
(000097D2 81 2 182 2 1 0		append)
(000097D8 5 4		UnVar4)
(000097DA 5 6		UnVar6)
(000097DC 81 3 54 0 1 0		subst)
(000097E2 8 6		UnVar6)
(000097E4 15 15 0		JMP 000097F6)
(000097E7 5 7		UnVar7)
(000097E9 50 4		4)
(000097EB 5 8		UnVar8)
(000097ED 42		cons)
(000097EE 57 2 0		list)
(000097F1 5 6		UnVar6)
(000097F3 42		cons)
(000097F4 8 6		UnVar6)
(000097F6 5 6		UnVar6)
(000097F8 81 1 70 0 1 0		attach-tool-bar)
(000097FE 22		ret)
;;;def nil 38911
(000097FF 20 2 1 1 0)
(00009804 100 1		UNVar1)
(00009806 5 0		UnVar0)
(00009808 3 73 0		*toolbars-list*)
(0000980B 81 2 16 3 1 0		assq)
(00009811 8 1		UnVar1)
(00009813 5 1		UnVar1)
(00009815 9 53 0		"Invalid toolbar name")
(00009818 53 2 17 3 1 32		assert)
(0000981E 10)
(0000981F 5 1		UnVar1)
(00009821 41		cdr)
(00009822 40		car)
(00009823 81 1 226 2 1 0		symbol-value)
(00009829 22		ret)
;;;def nil 38954
(0000982A 20 3 1 1 0)
(0000982F 100 1		UNVar1)
(00009831 100 2		UNVar2)
(00009833 5 0		UnVar0)
(00009835 95 1 255 151 0 0		func 000097FF)
(0000983B 8 2		UnVar2)
(0000983D 5 2		UnVar2)
(0000983F 61 8 0		nil->JMP 0000984A)
(00009842 5 2		UnVar2)
(00009844 53 1 103 3 1 32		host-spouse-exists-p)
(0000984A 63		nil->ret)
(0000984B 5 2		UnVar2)
(0000984D 95 1 55 148 0 0		func 00009437)
(00009853 8 1		UnVar1)
(00009855 5 1		UnVar1)
(00009857 81 1 70 0 1 0		attach-tool-bar)
(0000985D 22		ret)
;;;def nil 39006
(0000985E 20 19 3 3 0)
(00009863 100 3		UNVar3)
(00009865 100 4		UNVar4)
(00009867 100 5		UNVar5)
(00009869 100 6		UNVar6)
(0000986B 100 7		UNVar7)
(0000986D 100 8		UNVar8)
(0000986F 100 9		UNVar9)
(00009871 100 10		UNVar10)
(00009873 100 11		UNVar11)
(00009875 100 12		UNVar12)
(00009877 100 13		UNVar13)
(00009879 100 14		UNVar14)
(0000987B 100 15		UNVar15)
(0000987D 100 16		UNVar16)
(0000987F 100 17		UNVar17)
(00009881 5 1		UnVar1)
(00009883 9 68 0		'(:HT :HD :VL :VR))
(00009886 81 2 114 3 1 0		memq)
(0000988C 9 67 0		"Bad ribbon position")
(0000988F 53 2 17 3 1 32		assert)
(00009895 10)
(00009896 5 1		UnVar1)
(00009898 95 1 28 149 0 0		func 0000951C)
(0000989E 8 18		UnVar18)
(000098A0 5 18		UnVar18)
(000098A2 40		car)
(000098A3 8 17		UnVar17)
(000098A5 5 18		UnVar18)
(000098A7 41		cdr)
(000098A8 8 16		UnVar16)
(000098AA 5 2		UnVar2)
(000098AC 5 17		UnVar17)
(000098AE 81 2 52 0 1 0		subtract-ipoints)
(000098B4 8 15		UnVar15)
(000098B6 15 109 1		JMP 00009A26)
(000098B9 5 0		UnVar0)
(000098BB 40		car)
(000098BC 8 18		UnVar18)
(000098BE 5 0		UnVar0)
(000098C0 41		cdr)
(000098C1 8 0		UnVar0)
(000098C3 5 18		UnVar18)
(000098C5 8 14		UnVar14)
(000098C7 5 14		UnVar14)
(000098C9 5 1		UnVar1)
(000098CB 81 2 8 3 1 0		eqcar)
(000098D1 13 82 1		nil->JMP 00009A26)
(000098D4 5 14		UnVar14)
(000098D6 41		cdr)
(000098D7 8 13		UnVar13)
(000098D9 15 63 1		JMP 00009A1B)
(000098DC 5 13		UnVar13)
(000098DE 40		car)
(000098DF 8 12		UnVar12)
(000098E1 5 12		UnVar12)
(000098E3 40		car)
(000098E4 8 11		UnVar11)
(000098E6 5 12		UnVar12)
(000098E8 41		cdr)
(000098E9 8 10		UnVar10)
(000098EB 5 10		UnVar10)
(000098ED 9 255 2		'apex)
(000098F0 81 2 86 3 1 0		slot-value)
(000098F6 8 9		UnVar9)
(000098F8 5 10		UnVar10)
(000098FA 9 254 2		'size)
(000098FD 81 2 86 3 1 0		slot-value)
(00009903 8 8		UnVar8)
(00009905 5 1		UnVar1)
(00009907 9 59 0		'(:HT :HD))
(0000990A 81 2 114 3 1 0		memq)
(00009910 13 64 0		nil->JMP 00009953)
(00009913 5 9		UnVar9)
(00009915 81 1 253 2 1 0		ipoint-h)
(0000991B 5 11		UnVar11)
(0000991D 71		-)
(0000991E 8 7		UnVar7)
(00009920 5 9		UnVar9)
(00009922 81 1 251 2 1 0		ipoint-v)
(00009928 8 5		UnVar5)
(0000992A 5 9		UnVar9)
(0000992C 81 1 253 2 1 0		ipoint-h)
(00009932 5 8		UnVar8)
(00009934 81 1 253 2 1 0		ipoint-h)
(0000993A 70		+)
(0000993B 8 6		UnVar6)
(0000993D 5 9		UnVar9)
(0000993F 81 1 251 2 1 0		ipoint-v)
(00009945 5 8		UnVar8)
(00009947 81 1 251 2 1 0		ipoint-v)
(0000994D 70		+)
(0000994E 8 4		UnVar4)
(00009950 15 61 0		JMP 00009990)
(00009953 5 9		UnVar9)
(00009955 81 1 253 2 1 0		ipoint-h)
(0000995B 8 7		UnVar7)
(0000995D 5 9		UnVar9)
(0000995F 81 1 251 2 1 0		ipoint-v)
(00009965 5 11		UnVar11)
(00009967 71		-)
(00009968 8 5		UnVar5)
(0000996A 5 9		UnVar9)
(0000996C 81 1 253 2 1 0		ipoint-h)
(00009972 5 8		UnVar8)
(00009974 81 1 253 2 1 0		ipoint-h)
(0000997A 70		+)
(0000997B 8 6		UnVar6)
(0000997D 5 9		UnVar9)
(0000997F 81 1 251 2 1 0		ipoint-v)
(00009985 5 8		UnVar8)
(00009987 81 1 251 2 1 0		ipoint-v)
(0000998D 70		+)
(0000998E 8 4		UnVar4)
(00009990 5 15		UnVar15)
(00009992 5 7		UnVar7)
(00009994 5 5		UnVar5)
(00009996 5 6		UnVar6)
(00009998 5 4		UnVar4)
(0000999A 95 5 246 155 0 0		func 00009BF6)
(000099A0 13 7 0		nil->JMP 000099AA)
(000099A3 5 12		UnVar12)
(000099A5 8 3		UnVar3)
(000099A7 15 113 0		JMP 00009A1B)
(000099AA 5 13		UnVar13)
(000099AC 41		cdr)
(000099AD 13 4 0		nil->JMP 000099B4)
(000099B0 1		nil)
(000099B1 15 87 0		JMP 00009A0B)
(000099B4 5 1		UnVar1)
(000099B6 9 59 0		'(:HT :HD))
(000099B9 81 2 114 3 1 0		memq)
(000099BF 13 38 0		nil->JMP 000099E8)
(000099C2 5 5		UnVar5)
(000099C4 5 15		UnVar15)
(000099C6 81 1 251 2 1 0		ipoint-v)
(000099CC 81 2 79 2 1 0		<)
(000099D2 61 16 0		nil->JMP 000099E5)
(000099D5 5 15		UnVar15)
(000099D7 81 1 251 2 1 0		ipoint-v)
(000099DD 5 4		UnVar4)
(000099DF 81 2 79 2 1 0		<)
(000099E5 15 35 0		JMP 00009A0B)
(000099E8 5 7		UnVar7)
(000099EA 5 15		UnVar15)
(000099EC 81 1 253 2 1 0		ipoint-h)
(000099F2 81 2 79 2 1 0		<)
(000099F8 61 16 0		nil->JMP 00009A0B)
(000099FB 5 15		UnVar15)
(000099FD 81 1 253 2 1 0		ipoint-h)
(00009A03 5 6		UnVar6)
(00009A05 81 2 79 2 1 0		<)
(00009A0B 13 8 0		nil->JMP 00009A16)
(00009A0E 2		T)
(00009A0F 8 3		UnVar3)
(00009A11 100 13		UNVar13)
(00009A13 15 5 0		JMP 00009A1B)
(00009A16 5 13		UnVar13)
(00009A18 41		cdr)
(00009A19 8 13		UnVar13)
(00009A1B 5 13		UnVar13)
(00009A1D 61 3 0		nil->JMP 00009A23)
(00009A20 5 3		UnVar3)
(00009A22 35		not)
(00009A23 60 182 254		T->JMP 000098DC)
(00009A26 5 0		UnVar0)
(00009A28 61 3 0		nil->JMP 00009A2E)
(00009A2B 5 3		UnVar3)
(00009A2D 35		not)
(00009A2E 60 136 254		T->JMP 000098B9)
(00009A31 5 3		UnVar3)
(00009A33 61 2 0		nil->JMP 00009A38)
(00009A36 5 14		UnVar14)
(00009A38 5 13		UnVar13)
(00009A3A 5 1		UnVar1)
(00009A3C 9 59 0		'(:HT :HD))
(00009A3F 81 2 114 3 1 0		memq)
(00009A45 13 5 0		nil->JMP 00009A4D)
(00009A48 5 6		UnVar6)
(00009A4A 15 2 0		JMP 00009A4F)
(00009A4D 5 4		UnVar4)
(00009A4F 5 16		UnVar16)
(00009A51 42		cons)
(00009A52 42		cons)
(00009A53 42		cons)
(00009A54 22		ret)
;;;def nil 39509
(00009A55 20 13 4 4 0)
(00009A5A 100 4		UNVar4)
(00009A5C 100 5		UNVar5)
(00009A5E 100 6		UNVar6)
(00009A60 100 7		UNVar7)
(00009A62 100 8		UNVar8)
(00009A64 100 9		UNVar9)
(00009A66 100 10		UNVar10)
(00009A68 100 11		UNVar11)
(00009A6A 81 0 66 0 1 0		_mdiclient.apex-and-size)
(00009A70 8 12		UnVar12)
(00009A72 5 12		UnVar12)
(00009A74 40		car)
(00009A75 8 11		UnVar11)
(00009A77 5 12		UnVar12)
(00009A79 41		cdr)
(00009A7A 8 10		UnVar10)
(00009A7C 5 3		UnVar3)
(00009A7E 5 0		UnVar0)
(00009A80 5 2		UnVar2)
(00009A82 95 3 94 152 0 0		func 0000985E)
(00009A88 8 12		UnVar12)
(00009A8A 5 12		UnVar12)
(00009A8C 40		car)
(00009A8D 8 9		UnVar9)
(00009A8F 5 12		UnVar12)
(00009A91 41		cdr)
(00009A92 40		car)
(00009A93 8 8		UnVar8)
(00009A95 5 12		UnVar12)
(00009A97 41		cdr)
(00009A98 41		cdr)
(00009A99 40		car)
(00009A9A 8 7		UnVar7)
(00009A9C 5 12		UnVar12)
(00009A9E 41		cdr)
(00009A9F 41		cdr)
(00009AA0 41		cdr)
(00009AA1 8 6		UnVar6)
(00009AA3 5 1		UnVar1)
(00009AA5 9 254 2		'size)
(00009AA8 81 2 86 3 1 0		slot-value)
(00009AAE 8 4		UnVar4)
(00009AB0 5 0		UnVar0)
(00009AB2 9 59 0		'(:HT :HD))
(00009AB5 81 2 114 3 1 0		memq)
(00009ABB 13 11 0		nil->JMP 00009AC9)
(00009ABE 5 4		UnVar4)
(00009AC0 81 1 253 2 1 0		ipoint-h)
(00009AC6 15 8 0		JMP 00009AD1)
(00009AC9 5 4		UnVar4)
(00009ACB 81 1 251 2 1 0		ipoint-v)
(00009AD1 8 5		UnVar5)
(00009AD3 5 9		UnVar9)
(00009AD5 13 64 0		nil->JMP 00009B18)
(00009AD8 5 7		UnVar7)
(00009ADA 5 5		UnVar5)
(00009ADC 70		+)
(00009ADD 5 6		UnVar6)
(00009ADF 76		<)
(00009AE0 13 30 0		nil->JMP 00009B01)
(00009AE3 50 4		4)
(00009AE5 5 1		UnVar1)
(00009AE7 42		cons)
(00009AE8 5 8		UnVar8)
(00009AEA 5 9		UnVar9)
(00009AEC 95 3 198 155 0 0		func 00009BC6)
(00009AF2 5 9		UnVar9)
(00009AF4 5 3		UnVar3)
(00009AF6 81 3 54 0 1 0		subst)
(00009AFC 8 3		UnVar3)
(00009AFE 15 20 0		JMP 00009B15)
(00009B01 5 0		UnVar0)
(00009B03 50 4		4)
(00009B05 5 1		UnVar1)
(00009B07 42		cons)
(00009B08 57 1 0		list)
(00009B0B 5 3		UnVar3)
(00009B0D 81 3 51 0 1 0		acons)
(00009B13 8 3		UnVar3)
(00009B15 15 165 0		JMP 00009BBD)
(00009B18 5 2		UnVar2)
(00009B1A 5 11		UnVar11)
(00009B1C 81 1 253 2 1 0		ipoint-h)
(00009B22 5 11		UnVar11)
(00009B24 81 1 251 2 1 0		ipoint-v)
(00009B2A 5 11		UnVar11)
(00009B2C 81 1 253 2 1 0		ipoint-h)
(00009B32 5 10		UnVar10)
(00009B34 81 1 253 2 1 0		ipoint-h)
(00009B3A 70		+)
(00009B3B 5 11		UnVar11)
(00009B3D 81 1 251 2 1 0		ipoint-v)
(00009B43 5 10		UnVar10)
(00009B45 81 1 251 2 1 0		ipoint-v)
(00009B4B 70		+)
(00009B4C 95 5 246 155 0 0		func 00009BF6)
(00009B52 8 12		UnVar12)
(00009B54 5 12		UnVar12)
(00009B56 61 6 0		nil->JMP 00009B5F)
(00009B59 5 0		UnVar0)
(00009B5B 9 102 1		':HD)
(00009B5E 38		=)
(00009B5F 14 47 0		T->JMP 00009B91)
(00009B62 5 12		UnVar12)
(00009B64 61 6 0		nil->JMP 00009B6D)
(00009B67 5 0		UnVar0)
(00009B69 9 87 0		':VR)
(00009B6C 38		=)
(00009B6D 14 33 0		T->JMP 00009B91)
(00009B70 5 12		UnVar12)
(00009B72 13 4 0		nil->JMP 00009B79)
(00009B75 1		nil)
(00009B76 15 6 0		JMP 00009B7F)
(00009B79 5 0		UnVar0)
(00009B7B 9 79 0		':HT)
(00009B7E 38		=)
(00009B7F 14 15 0		T->JMP 00009B91)
(00009B82 5 12		UnVar12)
(00009B84 13 4 0		nil->JMP 00009B8B)
(00009B87 1		nil)
(00009B88 15 6 0		JMP 00009B91)
(00009B8B 5 0		UnVar0)
(00009B8D 9 78 0		':VL)
(00009B90 38		=)
(00009B91 13 18 0		nil->JMP 00009BA6)
(00009B94 5 0		UnVar0)
(00009B96 50 4		4)
(00009B98 5 1		UnVar1)
(00009B9A 42		cons)
(00009B9B 57 2 0		list)
(00009B9E 5 3		UnVar3)
(00009BA0 42		cons)
(00009BA1 8 3		UnVar3)
(00009BA3 15 23 0		JMP 00009BBD)
(00009BA6 5 3		UnVar3)
(00009BA8 5 0		UnVar0)
(00009BAA 50 4		4)
(00009BAC 5 1		UnVar1)
(00009BAE 42		cons)
(00009BAF 57 2 0		list)
(00009BB2 57 1 0		list)
(00009BB5 81 2 182 2 1 0		append)
(00009BBB 8 3		UnVar3)
(00009BBD 5 3		UnVar3)
(00009BBF 81 1 70 0 1 0		attach-tool-bar)
(00009BC5 22		ret)
;;;def nil 39878
(00009BC6 20 3 3 3 0)
(00009BCB 5 2		UnVar2)
(00009BCD 13 32 0		nil->JMP 00009BF0)
(00009BD0 5 1		UnVar1)
(00009BD2 5 2		UnVar2)
(00009BD4 38		=)
(00009BD5 13 6 0		nil->JMP 00009BDE)
(00009BD8 5 0		UnVar0)
(00009BDA 5 2		UnVar2)
(00009BDC 42		cons)
(00009BDD 22		ret)
(00009BDE 5 2		UnVar2)
(00009BE0 40		car)
(00009BE1 5 0		UnVar0)
(00009BE3 5 1		UnVar1)
(00009BE5 5 2		UnVar2)
(00009BE7 41		cdr)
(00009BE8 95 3 198 155 0 0		func 00009BC6)
(00009BEE 42		cons)
(00009BEF 22		ret)
(00009BF0 5 0		UnVar0)
(00009BF2 57 1 0		list)
(00009BF5 22		ret)
;;;def nil 39926
(00009BF6 20 7 5 5 0)
(00009BFB 5 0		UnVar0)
(00009BFD 81 1 253 2 1 0		ipoint-h)
(00009C03 8 5		UnVar5)
(00009C05 5 0		UnVar0)
(00009C07 81 1 251 2 1 0		ipoint-v)
(00009C0D 8 6		UnVar6)
(00009C0F 5 1		UnVar1)
(00009C11 5 5		UnVar5)
(00009C13 81 2 79 2 1 0		<)
(00009C19 63		nil->ret)
(00009C1A 5 5		UnVar5)
(00009C1C 5 3		UnVar3)
(00009C1E 81 2 79 2 1 0		<)
(00009C24 63		nil->ret)
(00009C25 5 2		UnVar2)
(00009C27 5 6		UnVar6)
(00009C29 81 2 79 2 1 0		<)
(00009C2F 63		nil->ret)
(00009C30 5 6		UnVar6)
(00009C32 5 4		UnVar4)
(00009C34 81 2 79 2 1 0		<)
(00009C3A 22		ret)
;;;def !drag-dlg 39995
(00009C3B 20 6 1 1 0)
(00009C40 100 1		UNVar1)
(00009C42 100 2		UNVar2)
(00009C44 100 3		UNVar3)
(00009C46 100 4		UNVar4)
(00009C48 100 5		UNVar5)
(00009C4A 5 0		UnVar0)
(00009C4C 40		car)
(00009C4D 8 4		UnVar4)
(00009C4F 5 0		UnVar0)
(00009C51 41		cdr)
(00009C52 40		car)
(00009C53 8 3		UnVar3)
(00009C55 5 0		UnVar0)
(00009C57 41		cdr)
(00009C58 41		cdr)
(00009C59 40		car)
(00009C5A 8 2		UnVar2)
(00009C5C 5 4		UnVar4)
(00009C5E 95 1 90 146 0 0		func 0000925A)
(00009C64 8 1		UnVar1)
(00009C66 5 2		UnVar2)
(00009C68 9 101 0		':FL)
(00009C6B 38		=)
(00009C6C 61 4 0		nil->JMP 00009C73)
(00009C6F 5 1		UnVar1)
(00009C71 37 2		consp)
(00009C73 13 22 0		nil->JMP 00009C8C)
(00009C76 5 4		UnVar4)
(00009C78 5 3		UnVar3)
(00009C7A 9 255 2		'apex)
(00009C7D 81 3 78 3 1 0		slot-value<-)
(00009C83 10)
(00009C84 5 4		UnVar4)
(00009C86 47 1 102 3 32 32		update-host-spouse)
(00009C8C 5 2		UnVar2)
(00009C8E 9 101 0		':FL)
(00009C91 38		=)
(00009C92 13 51 0		nil->JMP 00009CC8)
(00009C95 5 4		UnVar4)
(00009C97 95 1 55 148 0 0		func 00009437)
(00009C9D 81 1 70 0 1 0		attach-tool-bar)
(00009CA3 10)
(00009CA4 5 4		UnVar4)
(00009CA6 9 101 0		':FL)
(00009CA9 95 2 226 148 0 0		func 000094E2)
(00009CAF 8 4		UnVar4)
(00009CB1 5 4		UnVar4)
(00009CB3 5 3		UnVar3)
(00009CB5 9 255 2		'apex)
(00009CB8 81 3 78 3 1 0		slot-value<-)
(00009CBE 10)
(00009CBF 5 4		UnVar4)
(00009CC1 1		nil)
(00009CC2 47 2 101 3 32 32		create-host-spouse)
(00009CC8 5 4		UnVar4)
(00009CCA 95 1 55 148 0 0		func 00009437)
(00009CD0 8 5		UnVar5)
(00009CD2 5 4		UnVar4)
(00009CD4 5 2		UnVar2)
(00009CD6 95 2 226 148 0 0		func 000094E2)
(00009CDC 8 4		UnVar4)
(00009CDE 5 2		UnVar2)
(00009CE0 5 4		UnVar4)
(00009CE2 5 3		UnVar3)
(00009CE4 5 5		UnVar5)
(00009CE6 96 4 85 154 0 0		func 00009A55)
;;;def nil 40172
(00009CEC 20 0 0 0 0)
(00009CF1 3 50 0		*edt-toolbar-dlg*)
(00009CF4 53 1 194 0 1 32		dialogp)
(00009CFA 63		nil->ret)
(00009CFB 3 50 0		*edt-toolbar-dlg*)
(00009CFE 47 1 103 3 32 32		host-spouse-exists-p)
;;;def nil 40196
(00009D04 20 0 0 0 0)
(00009D09 3 49 0		*console-toolbar-dlg*)
(00009D0C 53 1 194 0 1 32		dialogp)
(00009D12 63		nil->ret)
(00009D13 3 49 0		*console-toolbar-dlg*)
(00009D16 47 1 103 3 32 32		host-spouse-exists-p)
;;;def nil 40220
(00009D1C 20 0 0 0 0)
(00009D21 3 195 0		*sdb-toolbar-dlg*)
(00009D24 53 1 194 0 1 32		dialogp)
(00009D2A 63		nil->ret)
(00009D2B 3 195 0		*sdb-toolbar-dlg*)
(00009D2E 47 1 103 3 32 32		host-spouse-exists-p)
;;;def update-toolbar 40244
(00009D34 20 4 1 1 0)
(00009D39 100 1		UNVar1)
(00009D3B 3 73 0		*toolbars-list*)
(00009D3E 8 2		UnVar2)
(00009D40 100 3		UNVar3)
(00009D42 15 46 0		JMP 00009D73)
(00009D45 5 2		UnVar2)
(00009D47 40		car)
(00009D48 8 3		UnVar3)
(00009D4A 5 2		UnVar2)
(00009D4C 41		cdr)
(00009D4D 8 2		UnVar2)
(00009D4F 5 3		UnVar3)
(00009D51 41		cdr)
(00009D52 40		car)
(00009D53 81 1 226 2 1 0		symbol-value)
(00009D59 11)
(00009D5A 8 1		UnVar1)
(00009D5C 61 8 0		nil->JMP 00009D67)
(00009D5F 5 1		UnVar1)
(00009D61 53 1 103 3 1 32		host-spouse-exists-p)
(00009D67 13 9 0		nil->JMP 00009D73)
(00009D6A 5 1		UnVar1)
(00009D6C 95 1 204 148 0 0		func 000094CC)
(00009D72 10)
(00009D73 5 2		UnVar2)
(00009D75 60 205 255		T->JMP 00009D45)
(00009D78 1		nil)
(00009D79 22		ret)
;;;def edt-toolbar-update 40314
(00009D7A 20 2 1 1 0)
(00009D7F 100 1		UNVar1)
(00009D81 3 48 0		*btn-save*)
(00009D84 5 0		UnVar0)
(00009D86 9 83 3		'save!)
(00009D89 3 205 2		*active-mdiwindow*)
(00009D8C 81 2 186 0 1 0		compute-applicable-methods)
(00009D92 81 3 47 0 1 0		bmp-button.enable)
(00009D98 10)
(00009D99 3 205 2		*active-mdiwindow*)
(00009D9C 53 1 50 2 1 32		tbuf.read-only)
(00009DA2 35		not)
(00009DA3 8 1		UnVar1)
(00009DA5 3 46 0		*btn-replace*)
(00009DA8 5 0		UnVar0)
(00009DAA 5 1		UnVar1)
(00009DAC 81 3 47 0 1 0		bmp-button.enable)
(00009DB2 10)
(00009DB3 3 45 0		*btn-cut*)
(00009DB6 5 0		UnVar0)
(00009DB8 5 1		UnVar1)
(00009DBA 81 3 47 0 1 0		bmp-button.enable)
(00009DC0 10)
(00009DC1 3 44 0		*btn-paste*)
(00009DC4 5 0		UnVar0)
(00009DC6 5 1		UnVar1)
(00009DC8 81 3 47 0 1 0		bmp-button.enable)
(00009DCE 10)
(00009DCF 3 43 0		*btn-copy*)
(00009DD2 5 0		UnVar0)
(00009DD4 2		T)
(00009DD5 81 3 47 0 1 0		bmp-button.enable)
(00009DDB 10)
(00009DDC 3 42 0		*btn-undo*)
(00009DDF 5 0		UnVar0)
(00009DE1 5 1		UnVar1)
(00009DE3 81 3 47 0 1 0		bmp-button.enable)
(00009DE9 10)
(00009DEA 3 41 0		*btn-redo*)
(00009DED 5 0		UnVar0)
(00009DEF 5 1		UnVar1)
(00009DF1 81 3 47 0 1 0		bmp-button.enable)
(00009DF7 10)
(00009DF8 3 40 0		*btn-complete*)
(00009DFB 5 0		UnVar0)
(00009DFD 5 1		UnVar1)
(00009DFF 81 3 47 0 1 0		bmp-button.enable)
(00009E05 22		ret)
;;;def find-toolbar-update 40454
(00009E06 20 2 1 1 0)
(00009E0B 100 1		UNVar1)
(00009E0D 3 46 0		*btn-replace*)
(00009E10 5 0		UnVar0)
(00009E12 3 205 2		*active-mdiwindow*)
(00009E15 53 1 50 2 1 32		tbuf.read-only)
(00009E1B 35		not)
(00009E1C 81 3 47 0 1 0		bmp-button.enable)
(00009E22 10)
(00009E23 3 205 2		*active-mdiwindow*)
(00009E26 53 1 39 0 1 32		!?mark-ring-next/prev)
(00009E2C 8 1		UnVar1)
(00009E2E 3 38 0		*pom-btn*)
(00009E31 5 0		UnVar0)
(00009E33 5 1		UnVar1)
(00009E35 81 3 47 0 1 0		bmp-button.enable)
(00009E3B 10)
(00009E3C 3 37 0		*swmp-btn*)
(00009E3F 5 0		UnVar0)
(00009E41 5 1		UnVar1)
(00009E43 81 3 47 0 1 0		bmp-button.enable)
(00009E49 10)
(00009E4A 3 36 0		*btn-cle-book*)
(00009E4D 5 0		UnVar0)
(00009E4F 5 1		UnVar1)
(00009E51 81 3 47 0 1 0		bmp-button.enable)
(00009E57 22		ret)
;;;def view-toolbar-update 40536
(00009E58 20 1 1 1 0)
(00009E5D 3 35 0		*ribb-acad!-pb*)
(00009E60 5 0		UnVar0)
(00009E62 81 0 148 2 1 0		in-ads-check)
(00009E68 61 1 0		nil->JMP 00009E6C)
(00009E6B 2		T)
(00009E6C 81 3 47 0 1 0		bmp-button.enable)
(00009E72 22		ret)
;;;def console-toolbar-update 40563
(00009E73 20 3 1 1 0)
(00009E78 100 1		UNVar1)
(00009E7A 100 2		UNVar2)
(00009E7C 3 205 2		*active-mdiwindow*)
(00009E7F 53 1 91 3 1 32		editorp)
(00009E85 8 2		UnVar2)
(00009E87 3 34 0		*btn-load-buffer*)
(00009E8A 5 0		UnVar0)
(00009E8C 5 2		UnVar2)
(00009E8E 81 3 47 0 1 0		bmp-button.enable)
(00009E94 10)
(00009E95 3 33 0		*btn-load-select*)
(00009E98 5 0		UnVar0)
(00009E9A 5 2		UnVar2)
(00009E9C 81 3 47 0 1 0		bmp-button.enable)
(00009EA2 10)
(00009EA3 3 205 2		*active-mdiwindow*)
(00009EA6 95 1 10 81 0 0		!?al-check)
(00009EAC 8 1		UnVar1)
(00009EAE 3 32 0		*btn-check-select*)
(00009EB1 5 0		UnVar0)
(00009EB3 5 1		UnVar1)
(00009EB5 81 3 47 0 1 0		bmp-button.enable)
(00009EBB 10)
(00009EBC 3 31 0		*btn-check-buffer*)
(00009EBF 5 0		UnVar0)
(00009EC1 5 1		UnVar1)
(00009EC3 81 3 47 0 1 0		bmp-button.enable)
(00009EC9 10)
(00009ECA 3 205 2		*active-mdiwindow*)
(00009ECD 53 1 30 0 1 32		!?ppf)
(00009ED3 8 1		UnVar1)
(00009ED5 3 29 0		*btn-format-select*)
(00009ED8 5 0		UnVar0)
(00009EDA 5 1		UnVar1)
(00009EDC 81 3 47 0 1 0		bmp-button.enable)
(00009EE2 10)
(00009EE3 3 28 0		*btn-format-buffer*)
(00009EE6 5 0		UnVar0)
(00009EE8 5 1		UnVar1)
(00009EEA 81 3 47 0 1 0		bmp-button.enable)
(00009EF0 10)
(00009EF1 5 2		UnVar2)
(00009EF3 61 10 0		nil->JMP 00009F00)
(00009EF6 3 205 2		*active-mdiwindow*)
(00009EF9 53 1 50 2 1 32		tbuf.read-only)
(00009EFF 35		not)
(00009F00 8 1		UnVar1)
(00009F02 3 27 0		*btn-comment-block*)
(00009F05 5 0		UnVar0)
(00009F07 5 1		UnVar1)
(00009F09 81 3 47 0 1 0		bmp-button.enable)
(00009F0F 10)
(00009F10 3 26 0		*btn-uncomment-block*)
(00009F13 5 0		UnVar0)
(00009F15 5 1		UnVar1)
(00009F17 81 3 47 0 1 0		bmp-button.enable)
(00009F1D 22		ret)
;;;def sdb-toolbar-update 40734
(00009F1E 20 2 1 1 0)
(00009F23 100 1		UNVar1)
(00009F25 3 205 2		*active-mdiwindow*)
(00009F28 95 1 79 65 0 0		!?debug-step)
(00009F2E 8 1		UnVar1)
(00009F30 3 25 0		*step-btn*)
(00009F33 5 0		UnVar0)
(00009F35 5 1		UnVar1)
(00009F37 81 3 47 0 1 0		bmp-button.enable)
(00009F3D 10)
(00009F3E 3 24 0		*stepin-btn*)
(00009F41 5 0		UnVar0)
(00009F43 5 1		UnVar1)
(00009F45 81 3 47 0 1 0		bmp-button.enable)
(00009F4B 10)
(00009F4C 3 23 0		*ret-btn*)
(00009F4F 5 0		UnVar0)
(00009F51 5 1		UnVar1)
(00009F53 81 3 47 0 1 0		bmp-button.enable)
(00009F59 10)
(00009F5A 3 205 2		*active-mdiwindow*)
(00009F5D 53 1 22 0 1 32		lisp-editor-p)
(00009F63 8 1		UnVar1)
(00009F65 3 21 0		*setbpt-btn*)
(00009F68 5 0		UnVar0)
(00009F6A 5 1		UnVar1)
(00009F6C 81 3 47 0 1 0		bmp-button.enable)
(00009F72 10)
(00009F73 3 20 0		*here-btn*)
(00009F76 5 0		UnVar0)
(00009F78 53 0 19 0 1 32		!?show-break-cause-source)
(00009F7E 81 3 47 0 1 0		bmp-button.enable)
(00009F84 10)
(00009F85 53 0 147 2 1 32		debug-quit!?)
(00009F8B 8 1		UnVar1)
(00009F8D 3 18 0		*reset-btn*)
(00009F90 5 0		UnVar0)
(00009F92 5 1		UnVar1)
(00009F94 81 3 47 0 1 0		bmp-button.enable)
(00009F9A 10)
(00009F9B 3 17 0		*quit-btn*)
(00009F9E 5 0		UnVar0)
(00009FA0 5 1		UnVar1)
(00009FA2 81 3 47 0 1 0		bmp-button.enable)
(00009FA8 10)
(00009FA9 3 16 0		*hhand-btn*)
(00009FAC 5 0		UnVar0)
(00009FAE 53 0 15 0 1 32		debug-continue!?)
(00009FB4 81 3 47 0 1 0		bmp-button.enable)
(00009FBA 22		ret)
;;;def get-toolbar 40891
(00009FBB 20 2 1 1 0)
(00009FC0 100 1		UNVar1)
(00009FC2 5 0		UnVar0)
(00009FC4 95 1 255 151 0 0		func 000097FF)
(00009FCA 8 1		UnVar1)
(00009FCC 5 1		UnVar1)
(00009FCE 53 1 194 0 1 32		dialogp)
(00009FD4 63		nil->ret)
(00009FD5 5 1		UnVar1)
(00009FD7 47 1 103 3 32 32		host-spouse-exists-p)
;;;def set-toolbar 40925
(00009FDD 20 2 2 2 0)
(00009FE2 5 0		UnVar0)
(00009FE4 95 1 187 159 0 0		get-toolbar)
(00009FEA 13 15 0		nil->JMP 00009FFC)
(00009FED 5 1		UnVar1)
(00009FEF 13 2 0		nil->JMP 00009FF4)
(00009FF2 1		nil)
(00009FF3 22		ret)
(00009FF4 5 0		UnVar0)
(00009FF6 96 1 42 152 0 0		func 0000982A)
(00009FFC 5 1		UnVar1)
(00009FFE 63		nil->ret)
(00009FFF 5 0		UnVar0)
(0000A001 96 1 233 150 0 0		func 000096E9)
;;;def instantiate-toolbar-check-box 40967
(0000A007 21 3 3 3 0)
(0000A00C 51 54 0 12 0		786486)
(0000A011 15 14 0		JMP 0000A022)
(0000A014 20 0 0 0 0)
(0000A019 4 1 0		UpVar1-0)
(0000A01C 96 1 187 159 0 0		get-toolbar)
(0000A022 12 139 3		'(40980 nil))
(0000A025 15 16 0		JMP 0000A038)
(0000A028 20 1 1 1 0)
(0000A02D 4 1 0		UpVar1-0)
(0000A030 5 0		UnVar0)
(0000A032 96 2 221 159 0 0		set-toolbar)
(0000A038 12 138 3		'(41000 nil))
(0000A03B 57 2 0		list)
(0000A03E 1		nil)
(0000A03F 5 1		UnVar1)
(0000A041 5 2		UnVar2)
(0000A043 47 5 214 0 32 32		accessed-check-box)
;;;def remove-all-toolbars 41033
(0000A049 20 2 0 0 0)
(0000A04E 3 73 0		*toolbars-list*)
(0000A051 8 0		UnVar0)
(0000A053 100 1		UNVar1)
(0000A055 15 20 0		JMP 0000A06C)
(0000A058 5 0		UnVar0)
(0000A05A 40		car)
(0000A05B 8 1		UnVar1)
(0000A05D 5 0		UnVar0)
(0000A05F 41		cdr)
(0000A060 8 0		UnVar0)
(0000A062 5 1		UnVar1)
(0000A064 40		car)
(0000A065 95 1 42 152 0 0		func 0000982A)
(0000A06B 10)
(0000A06C 5 0		UnVar0)
(0000A06E 60 231 255		T->JMP 0000A058)
(0000A071 1		nil)
(0000A072 22		ret)
;;;def add-all-toolbars 41075
(0000A073 20 2 0 0 0)
(0000A078 3 73 0		*toolbars-list*)
(0000A07B 8 0		UnVar0)
(0000A07D 100 1		UNVar1)
(0000A07F 15 20 0		JMP 0000A096)
(0000A082 5 0		UnVar0)
(0000A084 40		car)
(0000A085 8 1		UnVar1)
(0000A087 5 0		UnVar0)
(0000A089 41		cdr)
(0000A08A 8 0		UnVar0)
(0000A08C 5 1		UnVar1)
(0000A08E 40		car)
(0000A08F 95 1 233 150 0 0		func 000096E9)
(0000A095 10)
(0000A096 5 0		UnVar0)
(0000A098 60 231 255		T->JMP 0000A082)
(0000A09B 1		nil)
(0000A09C 22		ret)
;;;def !toolbars 41117
(0000A09D 20 8 0 1 0)
(0000A0A2 100 1		UNVar1)
(0000A0A4 100 2		UNVar2)
(0000A0A6 51 54 0 13 0		852022)
(0000A0AB 9 107 3		"VLMSG.DLL")
(0000A0AE 51 150 90 0 0		23190)
(0000A0B3 81 2 106 3 1 0		string-resource)
(0000A0B9 9 80 2		'verified-sync-down)
(0000A0BC 53 3 109 1 1 32		push-button)
(0000A0C2 8 2		UnVar2)
(0000A0C4 1		nil)
(0000A0C5 1		nil)
(0000A0C6 9 107 3		"VLMSG.DLL")
(0000A0C9 51 160 90 0 0		23200)
(0000A0CE 81 2 106 3 1 0		string-resource)
(0000A0D4 9 14 0		':HC)
(0000A0D7 50 4		4)
(0000A0D9 9 103 1		':V)
(0000A0DC 50 2		2)
(0000A0DE 9 222 0		':GROUP)
(0000A0E1 1		nil)
(0000A0E2 9 250 0		':H)
(0000A0E5 50 2		2)
(0000A0E7 9 213 0		':VC)
(0000A0EA 50 6		6)
(0000A0EC 9 13 0		'*editor-toolbar*)
(0000A0EF 9 107 3		"VLMSG.DLL")
(0000A0F2 51 76 74 0 0		19020)
(0000A0F7 81 2 106 3 1 0		string-resource)
(0000A0FD 9 107 3		"VLMSG.DLL")
(0000A100 51 170 90 0 0		23210)
(0000A105 81 2 106 3 1 0		string-resource)
(0000A10B 53 3 12 0 1 32		instantiate-toolbar-check-box)
(0000A111 50 3		3)
(0000A113 9 11 0		'*find-toolbar*)
(0000A116 9 107 3		"VLMSG.DLL")
(0000A119 51 180 90 0 0		23220)
(0000A11E 81 2 106 3 1 0		string-resource)
(0000A124 9 107 3		"VLMSG.DLL")
(0000A127 51 190 90 0 0		23230)
(0000A12C 81 2 106 3 1 0		string-resource)
(0000A132 53 3 12 0 1 32		instantiate-toolbar-check-box)
(0000A138 50 3		3)
(0000A13A 9 10 0		'*console-toolbar*)
(0000A13D 9 107 3		"VLMSG.DLL")
(0000A140 51 150 50 0 0		12950)
(0000A145 81 2 106 3 1 0		string-resource)
(0000A14B 9 107 3		"VLMSG.DLL")
(0000A14E 51 200 90 0 0		23240)
(0000A153 81 2 106 3 1 0		string-resource)
(0000A159 53 3 12 0 1 32		instantiate-toolbar-check-box)
(0000A15F 50 3		3)
(0000A161 9 9 0		'*debug-toolbar*)
(0000A164 9 107 3		"VLMSG.DLL")
(0000A167 51 38 52 0 0		13350)
(0000A16C 81 2 106 3 1 0		string-resource)
(0000A172 9 107 3		"VLMSG.DLL")
(0000A175 51 210 90 0 0		23250)
(0000A17A 81 2 106 3 1 0		string-resource)
(0000A180 53 3 12 0 1 32		instantiate-toolbar-check-box)
(0000A186 50 3		3)
(0000A188 9 8 0		'*inspect-toolbar*)
(0000A18B 9 107 3		"VLMSG.DLL")
(0000A18E 51 32 48 0 0		12320)
(0000A193 81 2 106 3 1 0		string-resource)
(0000A199 9 107 3		"VLMSG.DLL")
(0000A19C 51 220 90 0 0		23260)
(0000A1A1 81 2 106 3 1 0		string-resource)
(0000A1A7 53 3 12 0 1 32		instantiate-toolbar-check-box)
(0000A1AD 50 0		0)
(0000A1AF 57 12 0		list)
(0000A1B2 50 2		2)
(0000A1B4 57 4 0		list)
(0000A1B7 57 3 0		list)
(0000A1BA 50 4		4)
(0000A1BC 57 4 0		list)
(0000A1BF 50 7		7)
(0000A1C1 9 213 0		':VC)
(0000A1C4 50 4		4)
(0000A1C6 51 54 0 13 0		852022)
(0000A1CB 9 107 3		"VLMSG.DLL")
(0000A1CE 51 230 90 0 0		23270)
(0000A1D3 81 2 106 3 1 0		string-resource)
(0000A1D9 15 29 0		JMP 0000A1F9)
(0000A1DC 20 1 1 1 0)
(0000A1E1 95 0 73 160 0 0		remove-all-toolbars)
(0000A1E7 10)
(0000A1E8 5 0		UnVar0)
(0000A1EA 53 1 70 2 1 32		sync-up)
(0000A1F0 10)
(0000A1F1 5 0		UnVar0)
(0000A1F3 47 1 102 3 32 32		update-host-spouse)
(0000A1F9 9 137 3		'(41436 nil))
(0000A1FC 53 3 109 1 1 32		push-button)
(0000A202 50 4		4)
(0000A204 51 54 0 13 0		852022)
(0000A209 9 107 3		"VLMSG.DLL")
(0000A20C 51 240 90 0 0		23280)
(0000A211 81 2 106 3 1 0		string-resource)
(0000A217 15 29 0		JMP 0000A237)
(0000A21A 20 1 1 1 0)
(0000A21F 95 0 115 160 0 0		add-all-toolbars)
(0000A225 10)
(0000A226 5 0		UnVar0)
(0000A228 53 1 70 2 1 32		sync-up)
(0000A22E 10)
(0000A22F 5 0		UnVar0)
(0000A231 47 1 102 3 32 32		update-host-spouse)
(0000A237 9 136 3		'(41498 nil))
(0000A23A 53 3 109 1 1 32		push-button)
(0000A240 50 8		8)
(0000A242 5 2		UnVar2)
(0000A244 50 4		4)
(0000A246 51 54 0 13 0		852022)
(0000A24B 9 107 3		"VLMSG.DLL")
(0000A24E 51 210 40 0 0		10450)
(0000A253 81 2 106 3 1 0		string-resource)
(0000A259 9 94 3		'destroy-host-spouse)
(0000A25C 53 3 109 1 1 32		push-button)
(0000A262 50 4		4)
(0000A264 57 10 0		list)
(0000A267 50 4		4)
(0000A269 57 6 0		list)
(0000A26C 9 100 1		':FONT)
(0000A26F 3 248 0		*inspector-font*)
(0000A272 9 99 1		':PITCH)
(0000A275 3 247 0		*inspector-pitch*)
(0000A278 9 98 1		':DEFAULT-PUSH-BUTTON)
(0000A27B 5 2		UnVar2)
(0000A27D 53 10 244 0 1 32		dialog-fmt)
(0000A283 8 1		UnVar1)
(0000A285 5 1		UnVar1)
(0000A287 9 66 2		"vldlg.dll")
(0000A28A 51 130 0 0 0		130)
(0000A28F 5 1		UnVar1)
(0000A291 9 68 2		'items)
(0000A294 81 2 86 3 1 0		slot-value)
(0000A29A 8 3		UnVar3)
(0000A29C 51 12 5 0 0		1292)
(0000A2A1 51 13 5 0 0		1293)
(0000A2A6 51 14 5 0 0		1294)
(0000A2AB 51 68 4 0 0		1092)
(0000A2B0 51 75 4 0 0		1099)
(0000A2B5 51 11 5 0 0		1291)
(0000A2BA 51 15 5 0 0		1295)
(0000A2BF 51 16 5 0 0		1296)
(0000A2C4 51 76 4 0 0		1100)
(0000A2C9 51 77 4 0 0		1101)
(0000A2CE 57 10 0		list)
(0000A2D1 8 4		UnVar4)
(0000A2D3 100 5		UNVar5)
(0000A2D5 15 31 0		JMP 0000A2F7)
(0000A2D8 5 3		UnVar3)
(0000A2DA 40		car)
(0000A2DB 8 6		UnVar6)
(0000A2DD 5 4		UnVar4)
(0000A2DF 40		car)
(0000A2E0 8 7		UnVar7)
(0000A2E2 5 6		UnVar6)
(0000A2E4 40		car)
(0000A2E5 5 7		UnVar7)
(0000A2E7 42		cons)
(0000A2E8 5 5		UnVar5)
(0000A2EA 42		cons)
(0000A2EB 8 5		UnVar5)
(0000A2ED 5 3		UnVar3)
(0000A2EF 41		cdr)
(0000A2F0 8 3		UnVar3)
(0000A2F2 5 4		UnVar4)
(0000A2F4 41		cdr)
(0000A2F5 8 4		UnVar4)
(0000A2F7 5 3		UnVar3)
(0000A2F9 61 2 0		nil->JMP 0000A2FE)
(0000A2FC 5 4		UnVar4)
(0000A2FE 60 215 255		T->JMP 0000A2D8)
(0000A301 5 5		UnVar5)
(0000A303 81 1 12 3 1 0		nreverse)
(0000A309 53 4 65 2 1 32		dialog-update-from-res)
(0000A30F 10)
(0000A310 5 1		UnVar1)
(0000A312 47 1 64 2 32 32		modal-dialog!!)
;;;def make-default-tool-bar 41752
(0000A318 20 0 0 0 0)
(0000A31D 9 7 0		'(:TOOLBAR ((:HT (4 . *edt-toolbar-dlg*) (4 . *find-toolbar-dlg*)) (:HT (4 . *sdb-toolbar-dlg*) (4 . *inspect-toolbar-dlg*) (4 . *console-toolbar-dlg*))) :FL nil))
(0000A320 96 1 108 147 0 0		desktop-restore-toolbar)
;;;def do-one-srv-cmd 41766
(0000A326 20 7 1 2 0)
(0000A32B 100 2		UNVar2)
(0000A32D 100 3		UNVar3)
(0000A32F 100 4		UNVar4)
(0000A331 100 5		UNVar5)
(0000A333 100 6		UNVar6)
(0000A335 9 6 0		"FileOpen(\"")
(0000A338 8 6		UnVar6)
(0000A33A 9 5 0		"\")")
(0000A33D 8 5		UnVar5)
(0000A33F 5 1		UnVar1)
(0000A341 14 9 0		T->JMP 0000A34D)
(0000A344 3 205 2		*active-mdiwindow*)
(0000A347 14 3 0		T->JMP 0000A34D)
(0000A34A 3 92 3		*console*)
(0000A34D 8 1		UnVar1)
(0000A34F 50 0		0)
(0000A351 8 4		UnVar4)
(0000A353 15 52 0		JMP 0000A38A)
(0000A356 5 3		UnVar3)
(0000A358 5 5		UnVar5)
(0000A35A 81 1 82 2 1 0		strlen)
(0000A360 70		+)
(0000A361 8 4		UnVar4)
(0000A363 5 0		UnVar0)
(0000A365 5 2		UnVar2)
(0000A367 5 3		UnVar3)
(0000A369 81 3 106 0 1 0		string-subseq)
(0000A36F 1		nil)
(0000A370 1		nil)
(0000A371 2		T)
(0000A372 81 4 47 3 1 0		find-file)
(0000A378 8 2		UnVar2)
(0000A37A 5 2		UnVar2)
(0000A37C 13 11 0		nil->JMP 0000A38A)
(0000A37F 5 2		UnVar2)
(0000A381 5 1		UnVar1)
(0000A383 95 2 126 24 0 0		open-fresh-editor)
(0000A389 10)
(0000A38A 5 6		UnVar6)
(0000A38C 5 0		UnVar0)
(0000A38E 5 4		UnVar4)
(0000A390 81 3 4 0 1 0		string-search)
(0000A396 11)
(0000A397 8 2		UnVar2)
(0000A399 61 27 0		nil->JMP 0000A3B7)
(0000A39C 5 5		UnVar5)
(0000A39E 5 0		UnVar0)
(0000A3A0 5 2		UnVar2)
(0000A3A2 5 6		UnVar6)
(0000A3A4 81 1 82 2 1 0		strlen)
(0000A3AA 70		+)
(0000A3AB 11)
(0000A3AC 8 2		UnVar2)
(0000A3AE 81 3 4 0 1 0		string-search)
(0000A3B4 11)
(0000A3B5 8 3		UnVar3)
(0000A3B7 60 156 255		T->JMP 0000A356)
(0000A3BA 2		T)
(0000A3BB 22		ret)
;;;def do-dde-server-work 41916
(0000A3BC 20 2 0 1 0)
(0000A3C1 100 1		UNVar1)
(0000A3C3 5 0		UnVar0)
(0000A3C5 14 9 0		T->JMP 0000A3D1)
(0000A3C8 3 205 2		*active-mdiwindow*)
(0000A3CB 14 3 0		T->JMP 0000A3D1)
(0000A3CE 3 92 3		*console*)
(0000A3D1 8 0		UnVar0)
(0000A3D3 9 3 0		'*srv-busy*)
(0000A3D6 2		T)
(0000A3D7 24 2 0)
(0000A3DA 15 24 0		JMP 0000A3F5)
(0000A3DD 3 2 0		*srv-cmd*)
(0000A3E0 40		car)
(0000A3E1 8 1		UnVar1)
(0000A3E3 3 2 0		*srv-cmd*)
(0000A3E6 41		cdr)
(0000A3E7 6 2 0		*srv-cmd*)
(0000A3EA 5 1		UnVar1)
(0000A3EC 5 0		UnVar0)
(0000A3EE 95 2 38 163 0 0		do-one-srv-cmd)
(0000A3F4 10)
(0000A3F5 3 2 0		*srv-cmd*)
(0000A3F8 37 2		consp)
(0000A3FA 60 224 255		T->JMP 0000A3DD)
(0000A3FD 2		T)
(0000A3FE 25 1 0)
(0000A401 22		ret)
;;;def *poke-hook* 41986
(0000A402 20 2 2 2 0)
(0000A407 5 0		UnVar0)
(0000A409 81 1 239 0 1 0		intern)
(0000A40F 5 1		UnVar1)
(0000A411 81 2 140 0 1 0		set)
(0000A417 22		ret)
;;;def *peek-hook* 42008
(0000A418 20 1 1 1 0)
(0000A41D 5 0		UnVar0)
(0000A41F 81 1 1 0 1 0		find-symbol)
(0000A425 11)
(0000A426 8 0		UnVar0)
(0000A428 63		nil->ret)
(0000A429 5 0		UnVar0)
(0000A42B 81 1 226 2 1 0		symbol-value)
(0000A431 81 1 131 0 1 0		prin1-to-string)
(0000A437 22		ret)
;;;==========Main==========
(00000000 20 0 0 0 0)
(00000005 1		nil)
(00000006 10)
(00000007 9 108 2		"3/5/18 10:08 PM")
(0000000A 26 107 2		*wincmd-date*)
(0000000D 9 107 2		'*wincmd-date*)
(00000010 10)
(00000011 9 106 2		'wincmd)
(00000014 81 1 105 2 0 0		provide)
(0000001A 10)
(0000001B 9 104 2		'los)
(0000001E 81 1 103 2 0 0		require)
(00000024 10)
(00000025 9 102 2		'winlos)
(00000028 81 1 103 2 0 0		require)
(0000002E 28		[ret])
(0000002F 20 0 0 0 0)
(00000034 1		nil)
(00000035 10)
(00000036 9 101 2		'desktop)
(00000039 81 1 105 2 1 0		provide)
(0000003F 10)
(00000040 1		nil)
(00000041 10)
(00000042 9 81 3		'c-save)
(00000045 26 100 2		c-save)
(00000048 9 100 2		'c-save)
(0000004B 10)
(0000004C 12 80 3		'c-restore)
(0000004F 26 99 2		c-restore)
(00000052 9 99 2		'c-restore)
(00000055 10)
(00000056 9 79 3		'restore-editor)
(00000059 26 98 2		restore-editor)
(0000005C 9 98 2		'restore-editor)
(0000005F 10)
(00000060 12 78 3		'clear-desktop)
(00000063 26 97 2		clear-desktop)
(00000066 9 97 2		'clear-desktop)
(00000069 10)
(0000006A 9 96 2		":/")
(0000006D 9 95 2		"://")
(00000070 3 94 2		*LOCAL-PROFILE-DIR*)
(00000073 9 93 2		"/VLIDE.DSK")
(00000076 81 2 92 2 1 0		concat)
(0000007C 53 1 91 2 1 32		filename-beautify)
(00000082 81 3 90 2 1 0		string-subst)
(00000088 27 89 2		*default-desktop-file*)
(0000008B 9 89 2		'*default-desktop-file*)
(0000008E 10)
(0000008F 2		T)
(00000090 27 88 2		*desktop-save-windows*)
(00000093 9 88 2		'*desktop-save-windows*)
(00000096 10)
(00000097 53 0 87 2 1 32		alesmaint?)
(0000009D 35		not)
(0000009E 27 86 2		*desktop-autosave*)
(000000A1 9 86 2		'*desktop-autosave*)
(000000A4 10)
(000000A5 9 85 2		";# VLIDE desktop file [v.3]. DO NOT EDIT!!!")
(000000A8 26 84 2		_%vill-check-dsk-line%)
(000000AB 9 84 2		'_%vill-check-dsk-line%)
(000000AE 10)
(000000AF 12 77 3		'sv-dsk)
(000000B2 26 83 2		sv-dsk)
(000000B5 9 83 2		'sv-dsk)
(000000B8 10)
(000000B9 9 76 3		'lpp-save-config)
(000000BC 26 82 2		lpp-save-config)
(000000BF 9 82 2		'lpp-save-config)
(000000C2 10)
(000000C3 12 75 3		'lpp-restore-config)
(000000C6 26 81 2		lpp-restore-config)
(000000C9 9 81 2		'lpp-restore-config)
(000000CC 10)
(000000CD 9 74 3		'desktop::clear!)
(000000D0 26 80 2		desktop::clear!)
(000000D3 9 80 2		'desktop::clear!)
(000000D6 10)
(000000D7 9 73 3		'desktop::save!)
(000000DA 26 79 2		desktop::save!)
(000000DD 9 79 2		'desktop::save!)
(000000E0 28		[ret])
(000000E1 20 0 0 0 0)
(000000E6 1		nil)
(000000E7 10)
(000000E8 1		nil)
(000000E9 10)
(000000EA 3 78 2		*lex-options-list*)
(000000ED 27 78 2		*lex-options-list*)
(000000F0 9 78 2		'*lex-options-list*)
(000000F3 10)
(000000F4 3 77 2		*ales-options-list*)
(000000F7 27 77 2		*ales-options-list*)
(000000FA 9 77 2		'*ales-options-list*)
(000000FD 10)
(000000FE 9 72 3		'add-desktop-option)
(00000101 26 76 2		add-desktop-option)
(00000104 9 76 2		'add-desktop-option)
(00000107 10)
(00000108 1		nil)
(00000109 10)
(0000010A 1		nil)
(0000010B 10)
(0000010C 1		nil)
(0000010D 10)
(0000010E 1		nil)
(0000010F 10)
(00000110 9 71 3		'desktop-option.store)
(00000113 26 75 2		desktop-option.store)
(00000116 9 75 2		'desktop-option.store)
(00000119 10)
(0000011A 9 70 3		'desktop-option.restore)
(0000011D 26 74 2		desktop-option.restore)
(00000120 9 74 2		'desktop-option.restore)
(00000123 10)
(00000124 9 69 3		'desktop-option-restore)
(00000127 26 73 2		desktop-option-restore)
(0000012A 9 73 2		'desktop-option-restore)
(0000012D 10)
(0000012E 3 72 2		_%dsk-options%)
(00000131 27 72 2		_%dsk-options%)
(00000134 9 72 2		'_%dsk-options%)
(00000137 10)
(00000138 9 68 3		'store-desktop-options)
(0000013B 26 71 2		store-desktop-options)
(0000013E 9 71 2		'store-desktop-options)
(00000141 10)
(00000142 9 67 3		'restore-desktop-options)
(00000145 26 70 2		restore-desktop-options)
(00000148 9 70 2		'restore-desktop-options)
(0000014B 10)
(0000014C 9 66 3		'delayed-desktop-restore)
(0000014F 26 69 2		delayed-desktop-restore)
(00000152 9 69 2		'delayed-desktop-restore)
(00000155 10)
(00000156 9 68 2		'*editor-make-backup*)
(00000159 9 67 2		':L-CONTEXT)
(0000015C 9 66 2		':AUTOLISP)
(0000015F 53 3 76 2 1 32		add-desktop-option)
(00000165 10)
(00000166 9 65 2		'*editor-backup-by-copy*)
(00000169 9 67 2		':L-CONTEXT)
(0000016C 9 66 2		':AUTOLISP)
(0000016F 53 3 76 2 1 32		add-desktop-option)
(00000175 10)
(00000176 9 64 2		'editor-undo-join)
(00000179 9 63 2		':ACCESSOR)
(0000017C 9 62 2		'(_undo-join))
(0000017F 9 67 2		':L-CONTEXT)
(00000182 9 66 2		':AUTOLISP)
(00000185 53 5 76 2 1 32		add-desktop-option)
(0000018B 10)
(0000018C 9 61 2		'*ext-lex-scanner*)
(0000018F 9 67 2		':L-CONTEXT)
(00000192 9 66 2		':AUTOLISP)
(00000195 53 3 76 2 1 32		add-desktop-option)
(0000019B 10)
(0000019C 9 60 2		'*organize-windows*)
(0000019F 9 67 2		':L-CONTEXT)
(000001A2 9 66 2		':AUTOLISP)
(000001A5 53 3 76 2 1 32		add-desktop-option)
(000001AB 10)
(000001AC 9 59 2		'*organize-zoom*)
(000001AF 9 67 2		':L-CONTEXT)
(000001B2 9 66 2		':AUTOLISP)
(000001B5 53 3 76 2 1 32		add-desktop-option)
(000001BB 10)
(000001BC 9 58 2		'*auto-switch-to-ACAD*)
(000001BF 9 67 2		':L-CONTEXT)
(000001C2 9 66 2		':AUTOLISP)
(000001C5 53 3 76 2 1 32		add-desktop-option)
(000001CB 10)
(000001CC 9 88 2		'*desktop-save-windows*)
(000001CF 9 67 2		':L-CONTEXT)
(000001D2 9 66 2		':AUTOLISP)
(000001D5 53 3 76 2 1 32		add-desktop-option)
(000001DB 10)
(000001DC 9 86 2		'*desktop-autosave*)
(000001DF 9 67 2		':L-CONTEXT)
(000001E2 9 66 2		':AUTOLISP)
(000001E5 53 3 76 2 1 32		add-desktop-option)
(000001EB 10)
(000001EC 9 57 2		'*edit-file-history*)
(000001EF 9 63 2		':ACCESSOR)
(000001F2 15 0 0		JMP 000001F5)
(000001F5 9 65 3		'nil)
(000001F8 15 0 0		JMP 000001FB)
(000001FB 9 64 3		'nil)
(000001FE 57 2 0		list)
(00000201 9 67 2		':L-CONTEXT)
(00000204 9 66 2		':AUTOLISP)
(00000207 53 5 76 2 1 32		add-desktop-option)
(0000020D 10)
(0000020E 9 56 2		'*source-file-added-filters*)
(00000211 9 67 2		':L-CONTEXT)
(00000214 9 66 2		':AUTOLISP)
(00000217 53 3 76 2 1 32		add-desktop-option)
(0000021D 10)
(0000021E 9 55 2		'*protect-assign*)
(00000221 9 67 2		':L-CONTEXT)
(00000224 9 66 2		':AUTOLISP)
(00000227 53 3 76 2 1 32		add-desktop-option)
(0000022D 10)
(0000022E 9 54 2		'*break*)
(00000231 9 67 2		':L-CONTEXT)
(00000234 9 66 2		':AUTOLISP)
(00000237 53 3 76 2 1 32		add-desktop-option)
(0000023D 10)
(0000023E 9 53 2		'*al-check-warning*)
(00000241 9 67 2		':L-CONTEXT)
(00000244 9 66 2		':AUTOLISP)
(00000247 53 3 76 2 1 32		add-desktop-option)
(0000024D 10)
(0000024E 9 52 2		'*load-print*)
(00000251 9 67 2		':L-CONTEXT)
(00000254 9 66 2		':AUTOLISP)
(00000257 53 3 76 2 1 32		add-desktop-option)
(0000025D 10)
(0000025E 9 51 2		'*load-verbose*)
(00000261 9 67 2		':L-CONTEXT)
(00000264 9 66 2		':AUTOLISP)
(00000267 53 3 76 2 1 32		add-desktop-option)
(0000026D 10)
(0000026E 9 50 2		'*prin-echo-ACAD*)
(00000271 9 67 2		':L-CONTEXT)
(00000274 9 66 2		':AUTOLISP)
(00000277 53 3 76 2 1 32		add-desktop-option)
(0000027D 10)
(0000027E 9 49 2		'*SDB-ANIMATE-DELAY*)
(00000281 9 67 2		':L-CONTEXT)
(00000284 9 66 2		':AUTOLISP)
(00000287 53 3 76 2 1 32		add-desktop-option)
(0000028D 10)
(0000028E 9 48 2		'*SDB-SKIP-TOP-LEVEL*)
(00000291 9 67 2		':L-CONTEXT)
(00000294 9 66 2		':AUTOLISP)
(00000297 53 3 76 2 1 32		add-desktop-option)
(0000029D 10)
(0000029E 9 47 2		'*inspect-xdata-Default*)
(000002A1 9 67 2		':L-CONTEXT)
(000002A4 9 66 2		':AUTOLISP)
(000002A7 53 3 76 2 1 32		add-desktop-option)
(000002AD 10)
(000002AE 9 46 2		'*ACAD-INSPECT-VERBOSE*)
(000002B1 9 67 2		':L-CONTEXT)
(000002B4 9 66 2		':AUTOLISP)
(000002B7 53 3 76 2 1 32		add-desktop-option)
(000002BD 10)
(000002BE 1		nil)
(000002BF 10)
(000002C0 9 45 2		'*read-base*)
(000002C3 53 1 76 2 1 32		add-desktop-option)
(000002C9 10)
(000002CA 9 44 2		'*print-base*)
(000002CD 53 1 76 2 1 32		add-desktop-option)
(000002D3 10)
(000002D4 9 43 2		'*print-length*)
(000002D7 53 1 76 2 1 32		add-desktop-option)
(000002DD 10)
(000002DE 9 42 2		'*print-level*)
(000002E1 53 1 76 2 1 32		add-desktop-option)
(000002E7 10)
(000002E8 9 41 2		'*print-radix*)
(000002EB 53 1 76 2 1 32		add-desktop-option)
(000002F1 10)
(000002F2 9 40 2		'*print-escape*)
(000002F5 53 1 76 2 1 32		add-desktop-option)
(000002FB 10)
(000002FC 9 39 2		'*print-vector-size*)
(000002FF 53 1 76 2 1 32		add-desktop-option)
(00000305 10)
(00000306 9 38 2		'*print-readably*)
(00000309 53 1 76 2 1 32		add-desktop-option)
(0000030F 10)
(00000310 9 37 2		'*gc-say*)
(00000313 53 1 76 2 1 32		add-desktop-option)
(00000319 10)
(0000031A 9 36 2		'*gc-nop*)
(0000031D 53 1 76 2 1 32		add-desktop-option)
(00000323 10)
(00000324 9 35 2		'*gc-norat*)
(00000327 53 1 76 2 1 32		add-desktop-option)
(0000032D 10)
(0000032E 9 34 2		'*gc-unintern-symbols*)
(00000331 53 1 76 2 1 32		add-desktop-option)
(00000337 10)
(00000338 9 33 2		'*ext-list*)
(0000033B 53 1 76 2 1 32		add-desktop-option)
(00000341 10)
(00000342 9 32 2		'*lisp-source-ext-list*)
(00000345 53 1 76 2 1 32		add-desktop-option)
(0000034B 10)
(0000034C 9 31 2		'*load-path*)
(0000034F 9 63 2		':ACCESSOR)
(00000352 15 0 0		JMP 00000355)
(00000355 9 63 3		'nil)
(00000358 15 0 0		JMP 0000035B)
(0000035B 9 62 3		'nil)
(0000035E 57 2 0		list)
(00000361 53 3 76 2 1 32		add-desktop-option)
(00000367 10)
(00000368 9 30 2		'*verbose-dll-init*)
(0000036B 53 1 76 2 1 32		add-desktop-option)
(00000371 10)
(00000372 9 29 2		'fast-link)
(00000375 9 63 2		':ACCESSOR)
(00000378 9 28 2		'(fast-link))
(0000037B 53 3 76 2 1 32		add-desktop-option)
(00000381 10)
(00000382 9 27 2		'sys-trace)
(00000385 9 63 2		':ACCESSOR)
(00000388 9 26 2		'(_sys-trace))
(0000038B 53 3 76 2 1 32		add-desktop-option)
(00000391 10)
(00000392 9 25 2		'*backtrace-out-all*)
(00000395 53 1 76 2 1 32		add-desktop-option)
(0000039B 10)
(0000039C 9 24 2		'*warn-obsolete*)
(0000039F 53 1 76 2 1 32		add-desktop-option)
(000003A5 10)
(000003A6 9 23 2		'*symbol-redefinition-hook*)
(000003A9 53 1 76 2 1 32		add-desktop-option)
(000003AF 10)
(000003B0 9 22 2		'_warn-fsubr-eval)
(000003B3 9 63 2		':ACCESSOR)
(000003B6 9 21 2		'(_warn-fsubr-eval))
(000003B9 53 3 76 2 1 32		add-desktop-option)
(000003BF 10)
(000003C0 9 20 2		'_warn-lambda-apply)
(000003C3 9 63 2		':ACCESSOR)
(000003C6 9 19 2		'(_warn-lambda-apply))
(000003C9 53 3 76 2 1 32		add-desktop-option)
(000003CF 10)
(000003D0 9 18 2		'*crunch-fasl*)
(000003D3 53 1 76 2 1 32		add-desktop-option)
(000003D9 10)
(000003DA 9 17 2		'*twin-left-margin*)
(000003DD 9 67 2		':L-CONTEXT)
(000003E0 9 66 2		':AUTOLISP)
(000003E3 53 3 76 2 1 32		add-desktop-option)
(000003E9 10)
(000003EA 9 16 2		'*twin-tab-width*)
(000003ED 9 67 2		':L-CONTEXT)
(000003F0 9 66 2		':AUTOLISP)
(000003F3 53 3 76 2 1 32		add-desktop-option)
(000003F9 10)
(000003FA 1		nil)
(000003FB 10)
(000003FC 9 15 2		':LEX)
(000003FF 9 14 2		':RO)
(00000402 1		nil)
(00000403 57 3 0		list)
(00000406 9 66 2		':AUTOLISP)
(00000409 9 14 2		':RO)
(0000040C 1		nil)
(0000040D 57 3 0		list)
(00000410 57 2 0		list)
(00000413 27 13 2		*editor-sample-window*)
(00000416 9 13 2		'*editor-sample-window*)
(00000419 10)
(0000041A 1		nil)
(0000041B 10)
(0000041C 53 0 87 2 1 32		alesmaint?)
(00000422 13 4 0		nil->JMP 00000429)
(00000425 1		nil)
(00000426 15 25 0		JMP 00000442)
(00000429 9 15 2		':LEX)
(0000042C 3 13 2		*editor-sample-window*)
(0000042F 81 2 12 2 1 0		assq)
(00000435 3 13 2		*editor-sample-window*)
(00000438 81 2 11 2 1 0		delq)
(0000043E 11)
(0000043F 6 13 2		*editor-sample-window*)
(00000442 10)
(00000443 9 10 2		'logfont)
(00000446 9 63 2		':ACCESSOR)
(00000449 9 9 2		'(get-logfont set-logfont))
(0000044C 9 67 2		':L-CONTEXT)
(0000044F 9 66 2		':AUTOLISP)
(00000452 53 5 76 2 1 32		add-desktop-option)
(00000458 10)
(00000459 9 61 3		'auto-restore-apex-and-size)
(0000045C 26 8 2		auto-restore-apex-and-size)
(0000045F 9 8 2		'auto-restore-apex-and-size)
(00000462 10)
(00000463 9 60 3		'judge-and-restore-apex-and-size)
(00000466 26 7 2		judge-and-restore-apex-and-size)
(00000469 9 7 2		'judge-and-restore-apex-and-size)
(0000046C 10)
(0000046D 9 59 3		'auto-scale-apex-and-size)
(00000470 26 6 2		auto-scale-apex-and-size)
(00000473 9 6 2		'auto-scale-apex-and-size)
(00000476 10)
(00000477 9 58 3		'judge-and-scale-apex-and-size)
(0000047A 26 5 2		judge-and-scale-apex-and-size)
(0000047D 9 5 2		'judge-and-scale-apex-and-size)
(00000480 10)
(00000481 9 57 3		'win-frame.apex-and-size-100)
(00000484 26 4 2		win-frame.apex-and-size-100)
(00000487 9 4 2		'win-frame.apex-and-size-100)
(0000048A 10)
(0000048B 9 3 2		'win-frame)
(0000048E 9 63 2		':ACCESSOR)
(00000491 9 2 2		'(win-frame.apex-and-size-100))
(00000494 9 67 2		':L-CONTEXT)
(00000497 9 66 2		':AUTOLISP)
(0000049A 53 5 76 2 1 32		add-desktop-option)
(000004A0 10)
(000004A1 9 13 2		'*editor-sample-window*)
(000004A4 9 67 2		':L-CONTEXT)
(000004A7 9 66 2		':AUTOLISP)
(000004AA 53 3 76 2 1 32		add-desktop-option)
(000004B0 10)
(000004B1 1		nil)
(000004B2 10)
(000004B3 9 56 3		'get-desktop-window-sample)
(000004B6 26 1 2		get-desktop-window-sample)
(000004B9 9 1 2		'get-desktop-window-sample)
(000004BC 10)
(000004BD 9 55 3		'update-attributes-by-model-window)
(000004C0 26 0 2		update-attributes-by-model-window)
(000004C3 9 0 2		'update-attributes-by-model-window)
(000004C6 10)
(000004C7 9 54 3		'_ass-sample&)
(000004CA 26 255 1		_ass-sample&)
(000004CD 9 255 1		'_ass-sample&)
(000004D0 10)
(000004D1 9 53 3		'_ass-sample/cntx)
(000004D4 26 254 1		_ass-sample/cntx)
(000004D7 9 254 1		'_ass-sample/cntx)
(000004DA 10)
(000004DB 9 52 3		'_ass-sample)
(000004DE 26 253 1		_ass-sample)
(000004E1 9 253 1		'_ass-sample)
(000004E4 10)
(000004E5 9 51 3		'!wa-set-prototype)
(000004E8 26 252 1		!wa-set-prototype)
(000004EB 9 252 1		'!wa-set-prototype)
(000004EE 10)
(000004EF 9 50 3		'!wa-curr-to-prototype)
(000004F2 26 251 1		!wa-curr-to-prototype)
(000004F5 9 251 1		'!wa-curr-to-prototype)
(000004F8 10)
(000004F9 9 49 3		'!wa-all-to-prototype)
(000004FC 26 250 1		!wa-all-to-prototype)
(000004FF 9 250 1		'!wa-all-to-prototype)
(00000502 28		[ret])
(00000503 20 0 0 0 0)
(00000508 1		nil)
(00000509 10)
(0000050A 9 249 1		'editor!)
(0000050D 81 1 105 2 1 0		provide)
(00000513 10)
(00000514 1		nil)
(00000515 10)
(00000516 12 48 3		'_psi-unw-fun)
(00000519 26 248 1		_psi-unw-fun)
(0000051C 9 248 1		'_psi-unw-fun)
(0000051F 10)
(00000520 12 47 3		'process-selection-istream)
(00000523 26 247 1		process-selection-istream)
(00000526 9 247 1		'process-selection-istream)
(00000529 10)
(0000052A 9 46 3		'eval-selection!)
(0000052D 26 246 1		eval-selection!)
(00000530 9 246 1		'eval-selection!)
(00000533 10)
(00000534 12 45 3		'load-buffer!)
(00000537 26 245 1		load-buffer!)
(0000053A 9 245 1		'load-buffer!)
(0000053D 10)
(0000053E 1		nil)
(0000053F 10)
(00000540 1		nil)
(00000541 27 244 1		%last-file-to-load-dir%)
(00000544 9 244 1		'%last-file-to-load-dir%)
(00000547 10)
(00000548 9 44 3		'filename-from-selection?)
(0000054B 26 243 1		filename-from-selection?)
(0000054E 9 243 1		'filename-from-selection?)
(00000551 10)
(00000552 9 43 3		'get-filename-to-load)
(00000555 26 242 1		get-filename-to-load)
(00000558 9 242 1		'get-filename-to-load)
(0000055B 10)
(0000055C 12 42 3		'load-file!)
(0000055F 26 241 1		load-file!)
(00000562 9 241 1		'load-file!)
(00000565 10)
(00000566 1		nil)
(00000567 10)
(00000568 9 41 3		'!?editor-revert)
(0000056B 26 240 1		!?editor-revert)
(0000056E 9 240 1		'!?editor-revert)
(00000571 10)
(00000572 9 40 3		'>@editor-revert)
(00000575 26 239 1		>@editor-revert)
(00000578 9 239 1		'>@editor-revert)
(0000057B 10)
(0000057C 9 39 3		'!editor-revert)
(0000057F 26 238 1		!editor-revert)
(00000582 9 238 1		'!editor-revert)
(00000585 10)
(00000586 50 0		0)
(00000588 27 237 1		*untitled-num*)
(0000058B 9 237 1		'*untitled-num*)
(0000058E 10)
(0000058F 9 38 3		'new-editor!)
(00000592 26 236 1		new-editor!)
(00000595 9 236 1		'new-editor!)
(00000598 10)
(00000599 1		nil)
(0000059A 10)
(0000059B 1		nil)
(0000059C 27 235 1		%last-editor-open-dir%)
(0000059F 9 235 1		'%last-editor-open-dir%)
(000005A2 10)
(000005A3 9 37 3		'open-editor!)
(000005A6 26 234 1		open-editor!)
(000005A9 9 234 1		'open-editor!)
(000005AC 10)
(000005AD 9 36 3		'fresh-file-editor)
(000005B0 26 233 1		fresh-file-editor)
(000005B3 9 233 1		'fresh-file-editor)
(000005B6 10)
(000005B7 9 35 3		'open-fresh-editor)
(000005BA 26 232 1		open-fresh-editor)
(000005BD 9 232 1		'open-fresh-editor)
(000005C0 10)
(000005C1 9 34 3		'!?save-all-editors)
(000005C4 26 231 1		!?save-all-editors)
(000005C7 9 231 1		'!?save-all-editors)
(000005CA 10)
(000005CB 9 33 3		'>@save-all-editors)
(000005CE 26 230 1		>@save-all-editors)
(000005D1 9 230 1		'>@save-all-editors)
(000005D4 10)
(000005D5 9 32 3		'save-all-editors!)
(000005D8 26 229 1		save-all-editors!)
(000005DB 9 229 1		'save-all-editors!)
(000005DE 10)
(000005DF 1		nil)
(000005E0 10)
(000005E1 9 31 3		'exit!)
(000005E4 26 228 1		exit!)
(000005E7 9 228 1		'exit!)
(000005EA 10)
(000005EB 1		nil)
(000005EC 10)
(000005ED 3 227 1		*end-session-hook*)
(000005F0 27 227 1		*end-session-hook*)
(000005F3 9 227 1		'*end-session-hook*)
(000005F6 10)
(000005F7 9 227 1		'*end-session-hook*)
(000005FA 15 0 0		JMP 000005FD)
(000005FD 9 30 3		'nil)
(00000600 53 2 226 1 1 32		hook-expand)
(00000606 10)
(00000607 50 4		4)
(00000609 26 225 1		MK_SHIFT)
(0000060C 9 225 1		'MK_SHIFT)
(0000060F 10)
(00000610 50 8		8)
(00000612 26 224 1		MK_CONTROL)
(00000615 9 224 1		'MK_CONTROL)
(00000618 10)
(00000619 9 29 3		'!vkeys-flags-info)
(0000061C 26 223 1		!vkeys-flags-info)
(0000061F 9 223 1		'!vkeys-flags-info)
(00000622 10)
(00000623 50 1		1)
(00000625 57 1 0		list)
(00000628 26 222 1		__tcmd-stor__)
(0000062B 9 222 1		'__tcmd-stor__)
(0000062E 10)
(0000062F 9 28 3		'vkeys-Shift-p)
(00000632 26 221 1		vkeys-Shift-p)
(00000635 9 221 1		'vkeys-Shift-p)
(00000638 10)
(00000639 9 27 3		'vkeys-Ctrl-p)
(0000063C 26 220 1		vkeys-Ctrl-p)
(0000063F 9 220 1		'vkeys-Ctrl-p)
(00000642 10)
(00000643 9 26 3		'expand-selection)
(00000646 26 219 1		expand-selection)
(00000649 9 219 1		'expand-selection)
(0000064C 10)
(0000064D 1		nil)
(0000064E 10)
(0000064F 1		nil)
(00000650 10)
(00000651 9 25 3		'left-button-dblclk!)
(00000654 26 218 1		left-button-dblclk!)
(00000657 9 218 1		'left-button-dblclk!)
(0000065A 10)
(0000065B 9 24 3		'!goto-bow)
(0000065E 26 217 1		!goto-bow)
(00000661 9 217 1		'!goto-bow)
(00000664 10)
(00000665 9 23 3		'!select-to-bow)
(00000668 26 216 1		!select-to-bow)
(0000066B 9 216 1		'!select-to-bow)
(0000066E 10)
(0000066F 9 22 3		'!goto-eow)
(00000672 26 215 1		!goto-eow)
(00000675 9 215 1		'!goto-eow)
(00000678 10)
(00000679 9 21 3		'!select-to-eow)
(0000067C 26 214 1		!select-to-eow)
(0000067F 9 214 1		'!select-to-eow)
(00000682 10)
(00000683 9 20 3		'!del-word-bw)
(00000686 26 213 1		!del-word-bw)
(00000689 9 213 1		'!del-word-bw)
(0000068C 10)
(0000068D 9 19 3		'!del-word-fw)
(00000690 26 212 1		!del-word-fw)
(00000693 9 212 1		'!del-word-fw)
(00000696 10)
(00000697 9 18 3		'kill-chars)
(0000069A 26 211 1		kill-chars)
(0000069D 9 211 1		'kill-chars)
(000006A0 10)
(000006A1 9 17 3		'!newline-and-indent)
(000006A4 26 210 1		!newline-and-indent)
(000006A7 9 210 1		'!newline-and-indent)
(000006AA 10)
(000006AB 9 16 3		'!drop-files)
(000006AE 26 209 1		!drop-files)
(000006B1 9 209 1		'!drop-files)
(000006B4 28		[ret])
(000006B5 20 22 0 0 0)
(000006BA 1		nil)
(000006BB 10)
(000006BC 9 208 1		'search!)
(000006BF 81 1 105 2 1 0		provide)
(000006C5 10)
(000006C6 9 207 1		"car")
(000006C9 27 206 1		*editor-find-what*)
(000006CC 9 206 1		'*editor-find-what*)
(000006CF 10)
(000006D0 9 205 1		"")
(000006D3 27 204 1		*editor-replace-with*)
(000006D6 9 204 1		'*editor-replace-with*)
(000006D9 10)
(000006DA 2		T)
(000006DB 27 203 1		*editor-forward-search*)
(000006DE 9 203 1		'*editor-forward-search*)
(000006E1 10)
(000006E2 1		nil)
(000006E3 27 202 1		*editor-match-whole-word*)
(000006E6 9 202 1		'*editor-match-whole-word*)
(000006E9 10)
(000006EA 1		nil)
(000006EB 27 201 1		*editor-match-case*)
(000006EE 9 201 1		'*editor-match-case*)
(000006F1 10)
(000006F2 3 206 1		*editor-find-what*)
(000006F5 57 1 0		list)
(000006F8 27 200 1		*editor-find-what-hist*)
(000006FB 9 200 1		'*editor-find-what-hist*)
(000006FE 10)
(000006FF 3 199 1		*editor-search-margins*)
(00000702 27 199 1		*editor-search-margins*)
(00000705 9 199 1		'*editor-search-margins*)
(00000708 10)
(00000709 50 64		64)
(0000070B 26 198 1		%SEARCH-SELECTION-SIZE%)
(0000070E 9 198 1		'%SEARCH-SELECTION-SIZE%)
(00000711 10)
(00000712 3 197 1		*editor-replace-to-hist*)
(00000715 27 197 1		*editor-replace-to-hist*)
(00000718 9 197 1		'*editor-replace-to-hist*)
(0000071B 10)
(0000071C 2		T)
(0000071D 27 196 1		*next-is-find*)
(00000720 9 196 1		'*next-is-find*)
(00000723 10)
(00000724 1		nil)
(00000725 27 195 1		*editor-mark-found*)
(00000728 9 195 1		'*editor-mark-found*)
(0000072B 10)
(0000072C 9 195 1		'*editor-mark-found*)
(0000072F 9 67 2		':L-CONTEXT)
(00000732 9 66 2		':AUTOLISP)
(00000735 53 3 76 2 1 32		add-desktop-option)
(0000073B 10)
(0000073C 50 15		15)
(0000073E 26 194 1		_%editor-history-limit%)
(00000741 9 194 1		'_%editor-history-limit%)
(00000744 10)
(00000745 1		nil)
(00000746 10)
(00000747 9 15 3		'_fine-stringp)
(0000074A 26 193 1		_fine-stringp)
(0000074D 9 193 1		'_fine-stringp)
(00000750 10)
(00000751 1		nil)
(00000752 10)
(00000753 1		nil)
(00000754 10)
(00000755 9 14 3		'editor-selection-match-p)
(00000758 26 192 1		editor-selection-match-p)
(0000075B 9 192 1		'editor-selection-match-p)
(0000075E 10)
(0000075F 1		nil)
(00000760 10)
(00000761 1		nil)
(00000762 10)
(00000763 9 13 3		'editor-search)
(00000766 26 191 1		editor-search)
(00000769 9 191 1		'editor-search)
(0000076C 10)
(0000076D 1		nil)
(0000076E 10)
(0000076F 9 12 3		'!editor-find-command)
(00000772 26 190 1		!editor-find-command)
(00000775 9 190 1		'!editor-find-command)
(00000778 10)
(00000779 9 11 3		'_editor-find2-command)
(0000077C 26 189 1		_editor-find2-command)
(0000077F 9 189 1		'_editor-find2-command)
(00000782 10)
(00000783 1		nil)
(00000784 10)
(00000785 1		nil)
(00000786 10)
(00000787 3 188 1		*lb-find-next*)
(0000078A 14 35 0		T->JMP 000007B0)
(0000078D 51 150 0 12 0		786582)
(00000792 9 206 1		'*editor-find-what*)
(00000795 9 187 1		"VLMSG.DLL")
(00000798 51 78 92 0 0		23630)
(0000079D 81 2 186 1 1 0		string-resource)
(000007A3 1		nil)
(000007A4 50 15		15)
(000007A6 9 200 1		'*editor-find-what-hist*)
(000007A9 2		T)
(000007AA 53 7 185 1 1 32		accessed-drop-down-list-box)
(000007B0 27 188 1		*lb-find-next*)
(000007B3 9 188 1		'*lb-find-next*)
(000007B6 10)
(000007B7 3 188 1		*lb-find-next*)
(000007BA 3 184 1		*LBS_WITH-STRING*)
(000007BD 81 2 183 1 1 0		dialog-item._msw-style<-)
(000007C3 10)
(000007C4 3 188 1		*lb-find-next*)
(000007C7 2		T)
(000007C8 81 2 182 1 1 0		dialog-item.has-pix-size<-)
(000007CE 10)
(000007CF 3 188 1		*lb-find-next*)
(000007D2 2		T)
(000007D3 81 2 181 1 1 0		dialog-item.has-pix-pos<-)
(000007D9 10)
(000007DA 3 180 1		*editor-find-mode*)
(000007DD 27 180 1		*editor-find-mode*)
(000007E0 9 180 1		'*editor-find-mode*)
(000007E3 10)
(000007E4 9 179 1		'((*editor-find-dialog-items* !editor-find-command *ed-find-size* !editor-use-selection) (*editor-find-dialog-items* !editor-find-command *ed-find-size* !editor-drop-selection) (*editor-find-in-project-items* !editor-grep-project *ed-grep-project-size* !editor-init-grep-project) (*editor-find-in-files-items* !editor-grep-files *ed-grep-size* !editor-init-grep-files)))
(000007E7 27 178 1		*editor-find-modes*)
(000007EA 9 178 1		'*editor-find-modes*)
(000007ED 10)
(000007EE 9 177 1		'(0 . 0))
(000007F1 27 176 1		*ed-find-size*)
(000007F4 9 176 1		'*ed-find-size*)
(000007F7 10)
(000007F8 9 175 1		'(0.0 0))
(000007FB 27 174 1		*ed-replace-size*)
(000007FE 9 174 1		'*ed-replace-size*)
(00000801 10)
(00000802 1		nil)
(00000803 27 173 1		*ed-grep-project-size*)
(00000806 9 173 1		'*ed-grep-project-size*)
(00000809 10)
(0000080A 1		nil)
(0000080B 27 172 1		*ed-grep-size*)
(0000080E 9 172 1		'*ed-grep-size*)
(00000811 10)
(00000812 3 188 1		*lb-find-next*)
(00000815 53 1 171 1 1 32		sync-up)
(0000081B 10)
(0000081C 51 90 0 12 0		786522)
(00000821 9 202 1		'*editor-match-whole-word*)
(00000824 1		nil)
(00000825 9 187 1		"VLMSG.DLL")
(00000828 51 88 92 0 0		23640)
(0000082D 81 2 186 1 1 0		string-resource)
(00000833 9 187 1		"VLMSG.DLL")
(00000836 51 98 92 0 0		23650)
(0000083B 81 2 186 1 1 0		string-resource)
(00000841 53 5 170 1 1 32		accessed-check-box)
(00000847 8 0		UnVar0)
(00000849 51 90 0 12 0		786522)
(0000084E 9 201 1		'*editor-match-case*)
(00000851 1		nil)
(00000852 9 187 1		"VLMSG.DLL")
(00000855 51 108 92 0 0		23660)
(0000085A 81 2 186 1 1 0		string-resource)
(00000860 9 187 1		"VLMSG.DLL")
(00000863 51 118 92 0 0		23670)
(00000868 81 2 186 1 1 0		string-resource)
(0000086E 53 5 170 1 1 32		accessed-check-box)
(00000874 8 1		UnVar1)
(00000876 51 32 0 12 0		786464)
(0000087B 9 203 1		'*editor-forward-search*)
(0000087E 1		nil)
(0000087F 9 169 1		'identity)
(00000882 9 187 1		"VLMSG.DLL")
(00000885 51 128 92 0 0		23680)
(0000088A 81 2 186 1 1 0		string-resource)
(00000890 1		nil)
(00000891 9 187 1		"VLMSG.DLL")
(00000894 51 138 92 0 0		23690)
(00000899 81 2 186 1 1 0		string-resource)
(0000089F 53 7 168 1 1 32		accessed-radio-button)
(000008A5 8 2		UnVar2)
(000008A7 51 32 0 12 0		786464)
(000008AC 9 203 1		'*editor-forward-search*)
(000008AF 2		T)
(000008B0 9 169 1		'identity)
(000008B3 9 187 1		"VLMSG.DLL")
(000008B6 51 148 92 0 0		23700)
(000008BB 81 2 186 1 1 0		string-resource)
(000008C1 1		nil)
(000008C2 9 187 1		"VLMSG.DLL")
(000008C5 51 158 92 0 0		23710)
(000008CA 81 2 186 1 1 0		string-resource)
(000008D0 53 7 168 1 1 32		accessed-radio-button)
(000008D6 8 3		UnVar3)
(000008D8 51 90 0 12 0		786522)
(000008DD 9 195 1		'*editor-mark-found*)
(000008E0 1		nil)
(000008E1 9 187 1		"VLMSG.DLL")
(000008E4 51 168 92 0 0		23720)
(000008E9 81 2 186 1 1 0		string-resource)
(000008EF 9 187 1		"VLMSG.DLL")
(000008F2 51 178 92 0 0		23730)
(000008F7 81 2 186 1 1 0		string-resource)
(000008FD 53 5 170 1 1 32		accessed-check-box)
(00000903 8 4		UnVar4)
(00000905 51 50 0 14 0		917554)
(0000090A 9 187 1		"VLMSG.DLL")
(0000090D 51 188 92 0 0		23740)
(00000912 81 2 186 1 1 0		string-resource)
(00000918 15 0 0		JMP 0000091B)
(0000091B 9 10 3		'nil)
(0000091E 9 187 1		"VLMSG.DLL")
(00000921 51 208 92 0 0		23760)
(00000926 81 2 186 1 1 0		string-resource)
(0000092C 53 4 167 1 1 32		push-button)
(00000932 8 5		UnVar5)
(00000934 51 50 0 14 0		917554)
(00000939 9 187 1		"VLMSG.DLL")
(0000093C 51 228 82 0 0		21220)
(00000941 81 2 186 1 1 0		string-resource)
(00000947 15 0 0		JMP 0000094A)
(0000094A 9 9 3		'nil)
(0000094D 9 187 1		"VLMSG.DLL")
(00000950 51 218 92 0 0		23770)
(00000955 81 2 186 1 1 0		string-resource)
(0000095B 53 4 167 1 1 32		push-button)
(00000961 8 6		UnVar6)
(00000963 51 14 0 14 0		917518)
(00000968 9 166 1		"...")
(0000096B 9 8 3		'!grep-choose-source-directory)
(0000096E 53 3 167 1 1 32		push-button)
(00000974 8 7		UnVar7)
(00000976 51 90 0 12 0		786522)
(0000097B 9 165 1		'*grep-subdirs*)
(0000097E 1		nil)
(0000097F 9 187 1		"VLMSG.DLL")
(00000982 51 228 92 0 0		23780)
(00000987 81 2 186 1 1 0		string-resource)
(0000098D 9 187 1		"VLMSG.DLL")
(00000990 51 238 92 0 0		23790)
(00000995 81 2 186 1 1 0		string-resource)
(0000099B 53 5 170 1 1 32		accessed-check-box)
(000009A1 8 8		UnVar8)
(000009A3 9 164 1		':FIND-WHAT)
(000009A6 51 128 0 12 0		786560)
(000009AB 9 206 1		'*editor-find-what*)
(000009AE 9 187 1		"VLMSG.DLL")
(000009B1 51 248 92 0 0		23800)
(000009B6 81 2 186 1 1 0		string-resource)
(000009BC 1		nil)
(000009BD 50 9		9)
(000009BF 9 200 1		'*editor-find-what-hist*)
(000009C2 2		T)
(000009C3 53 7 185 1 1 32		accessed-drop-down-list-box)
(000009C9 9 163 1		':REPLACE-TO)
(000009CC 51 128 0 12 0		786560)
(000009D1 9 204 1		'*editor-replace-with*)
(000009D4 9 187 1		"VLMSG.DLL")
(000009D7 51 248 92 0 0		23800)
(000009DC 81 2 186 1 1 0		string-resource)
(000009E2 1		nil)
(000009E3 50 9		9)
(000009E5 9 197 1		'*editor-replace-to-hist*)
(000009E8 2		T)
(000009E9 53 7 185 1 1 32		accessed-drop-down-list-box)
(000009EF 9 162 1		':EDITOR-FIND-PUSH-BUTTON)
(000009F2 51 50 0 14 0		917554)
(000009F7 9 187 1		"VLMSG.DLL")
(000009FA 51 2 93 0 0		23810)
(000009FF 81 2 186 1 1 0		string-resource)
(00000A05 9 161 1		'_editor-find-command)
(00000A08 9 187 1		"VLMSG.DLL")
(00000A0B 51 12 93 0 0		23820)
(00000A10 81 2 186 1 1 0		string-resource)
(00000A16 53 4 167 1 1 32		push-button)
(00000A1C 9 160 1		':EDITOR-REPLACE-PUSH-BUTTON)
(00000A1F 51 50 0 14 0		917554)
(00000A24 9 187 1		"VLMSG.DLL")
(00000A27 51 196 64 0 0		16580)
(00000A2C 81 2 186 1 1 0		string-resource)
(00000A32 9 7 3		'_editor-replace-command)
(00000A35 9 187 1		"VLMSG.DLL")
(00000A38 51 102 88 0 0		22630)
(00000A3D 81 2 186 1 1 0		string-resource)
(00000A43 53 4 167 1 1 32		push-button)
(00000A49 9 159 1		':EDITOR-REPLACE-ALL-PUSH-BUTTON)
(00000A4C 51 50 0 14 0		917554)
(00000A51 9 187 1		"VLMSG.DLL")
(00000A54 51 22 93 0 0		23830)
(00000A59 81 2 186 1 1 0		string-resource)
(00000A5F 9 6 3		'_editor-replace-all-command)
(00000A62 9 187 1		"VLMSG.DLL")
(00000A65 51 32 93 0 0		23840)
(00000A6A 81 2 186 1 1 0		string-resource)
(00000A70 53 4 167 1 1 32		push-button)
(00000A76 9 158 1		':CHOOSE-FILES)
(00000A79 51 128 0 12 0		786560)
(00000A7E 9 157 1		'*editor-filelist*)
(00000A81 9 187 1		"VLMSG.DLL")
(00000A84 51 42 93 0 0		23850)
(00000A89 81 2 186 1 1 0		string-resource)
(00000A8F 1		nil)
(00000A90 1		nil)
(00000A91 9 156 1		'*editor-filelist-hist*)
(00000A94 2		T)
(00000A95 53 7 185 1 1 32		accessed-drop-down-list-box)
(00000A9B 9 155 1		':choose-project-lbox)
(00000A9E 51 128 0 12 0		786560)
(00000AA3 53 1 154 1 1 32		drop-down-list-box)
(00000AA9 9 153 1		':sel-box)
(00000AAC 51 70 0 12 0		786502)
(00000AB1 9 180 1		'*editor-find-mode*)
(00000AB4 3 178 1		*editor-find-modes*)
(00000AB7 40		car)
(00000AB8 9 5 3		'_tune-find-command)
(00000ABB 9 187 1		"VLMSG.DLL")
(00000ABE 51 52 93 0 0		23860)
(00000AC3 81 2 186 1 1 0		string-resource)
(00000AC9 53 5 168 1 1 32		accessed-radio-button)
(00000ACF 51 70 0 12 0		786502)
(00000AD4 9 180 1		'*editor-find-mode*)
(00000AD7 3 178 1		*editor-find-modes*)
(00000ADA 41		cdr)
(00000ADB 40		car)
(00000ADC 9 5 3		'_tune-find-command)
(00000ADF 9 187 1		"VLMSG.DLL")
(00000AE2 51 62 93 0 0		23870)
(00000AE7 81 2 186 1 1 0		string-resource)
(00000AED 53 5 168 1 1 32		accessed-radio-button)
(00000AF3 51 70 0 12 0		786502)
(00000AF8 9 180 1		'*editor-find-mode*)
(00000AFB 3 178 1		*editor-find-modes*)
(00000AFE 41		cdr)
(00000AFF 41		cdr)
(00000B00 40		car)
(00000B01 9 5 3		'_tune-find-command)
(00000B04 9 187 1		"VLMSG.DLL")
(00000B07 51 72 93 0 0		23880)
(00000B0C 81 2 186 1 1 0		string-resource)
(00000B12 53 5 168 1 1 32		accessed-radio-button)
(00000B18 51 70 0 12 0		786502)
(00000B1D 9 180 1		'*editor-find-mode*)
(00000B20 3 178 1		*editor-find-modes*)
(00000B23 41		cdr)
(00000B24 41		cdr)
(00000B25 41		cdr)
(00000B26 40		car)
(00000B27 9 5 3		'_tune-find-command)
(00000B2A 9 187 1		"VLMSG.DLL")
(00000B2D 51 54 86 0 0		22070)
(00000B32 81 2 186 1 1 0		string-resource)
(00000B38 53 5 168 1 1 32		accessed-radio-button)
(00000B3E 57 4 0		list)
(00000B41 9 152 1		':sel-box-replace)
(00000B44 51 70 0 12 0		786502)
(00000B49 9 180 1		'*editor-find-mode*)
(00000B4C 3 178 1		*editor-find-modes*)
(00000B4F 40		car)
(00000B50 9 4 3		'_tune-replace-command)
(00000B53 9 187 1		"VLMSG.DLL")
(00000B56 51 52 93 0 0		23860)
(00000B5B 81 2 186 1 1 0		string-resource)
(00000B61 53 5 168 1 1 32		accessed-radio-button)
(00000B67 51 70 0 12 0		786502)
(00000B6C 9 180 1		'*editor-find-mode*)
(00000B6F 3 178 1		*editor-find-modes*)
(00000B72 41		cdr)
(00000B73 40		car)
(00000B74 9 4 3		'_tune-replace-command)
(00000B77 9 187 1		"VLMSG.DLL")
(00000B7A 51 62 93 0 0		23870)
(00000B7F 81 2 186 1 1 0		string-resource)
(00000B85 53 5 168 1 1 32		accessed-radio-button)
(00000B8B 57 2 0		list)
(00000B8E 57 18 0		list)
(00000B91 8 9		UnVar9)
(00000B93 5 9		UnVar9)
(00000B95 8 10		UnVar10)
(00000B97 5 10		UnVar10)
(00000B99 9 164 1		':FIND-WHAT)
(00000B9C 1		nil)
(00000B9D 81 3 151 1 1 0		getf)
(00000BA3 8 11		UnVar11)
(00000BA5 5 10		UnVar10)
(00000BA7 9 163 1		':REPLACE-TO)
(00000BAA 1		nil)
(00000BAB 81 3 151 1 1 0		getf)
(00000BB1 8 12		UnVar12)
(00000BB3 5 10		UnVar10)
(00000BB5 9 162 1		':EDITOR-FIND-PUSH-BUTTON)
(00000BB8 1		nil)
(00000BB9 81 3 151 1 1 0		getf)
(00000BBF 8 13		UnVar13)
(00000BC1 5 10		UnVar10)
(00000BC3 9 160 1		':EDITOR-REPLACE-PUSH-BUTTON)
(00000BC6 1		nil)
(00000BC7 81 3 151 1 1 0		getf)
(00000BCD 8 14		UnVar14)
(00000BCF 5 10		UnVar10)
(00000BD1 9 159 1		':EDITOR-REPLACE-ALL-PUSH-BUTTON)
(00000BD4 1		nil)
(00000BD5 81 3 151 1 1 0		getf)
(00000BDB 8 15		UnVar15)
(00000BDD 5 10		UnVar10)
(00000BDF 9 150 1		':EDITOR-CANCEL-PUSH-BUTTON)
(00000BE2 1		nil)
(00000BE3 81 3 151 1 1 0		getf)
(00000BE9 8 16		UnVar16)
(00000BEB 5 10		UnVar10)
(00000BED 9 158 1		':CHOOSE-FILES)
(00000BF0 1		nil)
(00000BF1 81 3 151 1 1 0		getf)
(00000BF7 8 17		UnVar17)
(00000BF9 5 10		UnVar10)
(00000BFB 9 155 1		':choose-project-lbox)
(00000BFE 1		nil)
(00000BFF 81 3 151 1 1 0		getf)
(00000C05 8 18		UnVar18)
(00000C07 5 10		UnVar10)
(00000C09 9 153 1		':sel-box)
(00000C0C 1		nil)
(00000C0D 81 3 151 1 1 0		getf)
(00000C13 8 19		UnVar19)
(00000C15 5 10		UnVar10)
(00000C17 9 152 1		':sel-box-replace)
(00000C1A 1		nil)
(00000C1B 81 3 151 1 1 0		getf)
(00000C21 8 20		UnVar20)
(00000C23 9 149 1		':H)
(00000C26 50 5		5)
(00000C28 9 148 1		':V)
(00000C2B 50 5		5)
(00000C2D 9 149 1		':H)
(00000C30 9 148 1		':V)
(00000C33 50 2		2)
(00000C35 51 52 0 12 0		786484)
(00000C3A 9 187 1		"VLMSG.DLL")
(00000C3D 51 82 93 0 0		23890)
(00000C42 81 2 186 1 1 0		string-resource)
(00000C48 9 147 1		':LEFT)
(00000C4B 53 3 146 1 1 32		static-text)
(00000C51 57 3 0		list)
(00000C54 50 3		3)
(00000C56 5 11		UnVar11)
(00000C58 57 4 0		list)
(00000C5B 50 5		5)
(00000C5D 9 149 1		':H)
(00000C60 9 145 1		':GROUP)
(00000C63 9 187 1		"VLMSG.DLL")
(00000C66 51 120 90 0 0		23160)
(00000C6B 81 2 186 1 1 0		string-resource)
(00000C71 9 149 1		':H)
(00000C74 50 2		2)
(00000C76 9 148 1		':V)
(00000C79 5 19		UnVar19)
(00000C7B 50 1		1)
(00000C7D 57 1 0		list)
(00000C80 81 2 144 1 1 0		append)
(00000C86 42		cons)
(00000C87 50 2		2)
(00000C89 57 4 0		list)
(00000C8C 57 3 0		list)
(00000C8F 50 5		5)
(00000C91 9 148 1		':V)
(00000C94 9 145 1		':GROUP)
(00000C97 9 187 1		"VLMSG.DLL")
(00000C9A 51 92 93 0 0		23900)
(00000C9F 81 2 186 1 1 0		string-resource)
(00000CA5 9 148 1		':V)
(00000CA8 50 255		-1)
(00000CAA 9 149 1		':H)
(00000CAD 50 8		8)
(00000CAF 5 3		UnVar3)
(00000CB1 50 8		8)
(00000CB3 5 2		UnVar2)
(00000CB5 50 8		8)
(00000CB7 57 6 0		list)
(00000CBA 57 3 0		list)
(00000CBD 57 3 0		list)
(00000CC0 50 3		3)
(00000CC2 5 0		UnVar0)
(00000CC4 5 1		UnVar1)
(00000CC6 5 4		UnVar4)
(00000CC8 50 3		3)
(00000CCA 57 7 0		list)
(00000CCD 57 4 0		list)
(00000CD0 50 5		5)
(00000CD2 57 6 0		list)
(00000CD5 50 5		5)
(00000CD7 9 148 1		':V)
(00000CDA 50 5		5)
(00000CDC 5 13		UnVar13)
(00000CDE 50 3		3)
(00000CE0 5 6		UnVar6)
(00000CE2 50 6		6)
(00000CE4 50 3		3)
(00000CE6 57 7 0		list)
(00000CE9 50 5		5)
(00000CEB 57 6 0		list)
(00000CEE 50 0		0)
(00000CF0 3 176 1		*ed-find-size*)
(00000CF3 53 3 143 1 1 32		di-fmt-pos-alist)
(00000CF9 81 1 142 1 1 0		nreverse)
(00000CFF 26 141 1		*editor-find-dialog-items*)
(00000D02 9 141 1		'*editor-find-dialog-items*)
(00000D05 10)
(00000D06 9 140 1		"vldlg.dll")
(00000D09 50 107		107)
(00000D0B 81 2 139 1 1 0		dialog-size-from-res)
(00000D11 8 21		UnVar21)
(00000D13 5 21		UnVar21)
(00000D15 61 21 0		nil->JMP 00000D2D)
(00000D18 5 21		UnVar21)
(00000D1A 81 1 138 1 1 0		ipoint-h)
(00000D20 5 21		UnVar21)
(00000D22 81 1 137 1 1 0		ipoint-v)
(00000D28 42		cons)
(00000D29 11)
(00000D2A 6 176 1		*ed-find-size*)
(00000D2D 10)
(00000D2E 9 149 1		':H)
(00000D31 50 5		5)
(00000D33 9 148 1		':V)
(00000D36 50 5		5)
(00000D38 9 149 1		':H)
(00000D3B 9 148 1		':V)
(00000D3E 50 2		2)
(00000D40 51 52 0 12 0		786484)
(00000D45 9 187 1		"VLMSG.DLL")
(00000D48 51 82 93 0 0		23890)
(00000D4D 81 2 186 1 1 0		string-resource)
(00000D53 9 147 1		':LEFT)
(00000D56 53 3 146 1 1 32		static-text)
(00000D5C 50 3		3)
(00000D5E 51 52 0 12 0		786484)
(00000D63 9 187 1		"VLMSG.DLL")
(00000D66 51 102 93 0 0		23910)
(00000D6B 81 2 186 1 1 0		string-resource)
(00000D71 9 147 1		':LEFT)
(00000D74 53 3 146 1 1 32		static-text)
(00000D7A 57 5 0		list)
(00000D7D 50 1		1)
(00000D7F 9 148 1		':V)
(00000D82 5 11		UnVar11)
(00000D84 50 3		3)
(00000D86 5 12		UnVar12)
(00000D88 50 3		3)
(00000D8A 57 5 0		list)
(00000D8D 57 4 0		list)
(00000D90 9 149 1		':H)
(00000D93 9 145 1		':GROUP)
(00000D96 9 187 1		"VLMSG.DLL")
(00000D99 51 120 90 0 0		23160)
(00000D9E 81 2 186 1 1 0		string-resource)
(00000DA4 9 149 1		':H)
(00000DA7 50 2		2)
(00000DA9 9 148 1		':V)
(00000DAC 5 20		UnVar20)
(00000DAE 40		car)
(00000DAF 5 20		UnVar20)
(00000DB1 41		cdr)
(00000DB2 40		car)
(00000DB3 50 1		1)
(00000DB5 57 4 0		list)
(00000DB8 50 2		2)
(00000DBA 57 4 0		list)
(00000DBD 57 3 0		list)
(00000DC0 50 5		5)
(00000DC2 9 148 1		':V)
(00000DC5 9 145 1		':GROUP)
(00000DC8 9 187 1		"VLMSG.DLL")
(00000DCB 51 92 93 0 0		23900)
(00000DD0 81 2 186 1 1 0		string-resource)
(00000DD6 9 148 1		':V)
(00000DD9 50 255		-1)
(00000DDB 9 149 1		':H)
(00000DDE 50 8		8)
(00000DE0 5 3		UnVar3)
(00000DE2 50 8		8)
(00000DE4 5 2		UnVar2)
(00000DE6 50 8		8)
(00000DE8 57 6 0		list)
(00000DEB 57 3 0		list)
(00000DEE 57 3 0		list)
(00000DF1 50 3		3)
(00000DF3 5 0		UnVar0)
(00000DF5 5 1		UnVar1)
(00000DF7 50 3		3)
(00000DF9 57 6 0		list)
(00000DFC 50 5		5)
(00000DFE 57 5 0		list)
(00000E01 57 4 0		list)
(00000E04 50 5		5)
(00000E06 9 148 1		':V)
(00000E09 50 5		5)
(00000E0B 5 13		UnVar13)
(00000E0D 50 3		3)
(00000E0F 5 14		UnVar14)
(00000E11 50 3		3)
(00000E13 5 15		UnVar15)
(00000E15 50 3		3)
(00000E17 5 6		UnVar6)
(00000E19 50 5		5)
(00000E1B 57 10 0		list)
(00000E1E 50 5		5)
(00000E20 57 6 0		list)
(00000E23 50 0		0)
(00000E25 3 174 1		*ed-replace-size*)
(00000E28 53 3 143 1 1 32		di-fmt-pos-alist)
(00000E2E 81 1 142 1 1 0		nreverse)
(00000E34 26 136 1		*editor-replace-dialog-items*)
(00000E37 9 136 1		'*editor-replace-dialog-items*)
(00000E3A 10)
(00000E3B 3 176 1		*ed-find-size*)
(00000E3E 40		car)
(00000E3F 3 176 1		*ed-find-size*)
(00000E42 41		cdr)
(00000E43 42		cons)
(00000E44 11)
(00000E45 6 173 1		*ed-grep-project-size*)
(00000E48 10)
(00000E49 9 148 1		':V)
(00000E4C 9 149 1		':H)
(00000E4F 9 148 1		':V)
(00000E52 50 2		2)
(00000E54 51 52 0 12 0		786484)
(00000E59 9 187 1		"VLMSG.DLL")
(00000E5C 51 112 93 0 0		23920)
(00000E61 81 2 186 1 1 0		string-resource)
(00000E67 9 147 1		':LEFT)
(00000E6A 53 3 146 1 1 32		static-text)
(00000E70 57 3 0		list)
(00000E73 50 1		1)
(00000E75 5 18		UnVar18)
(00000E77 50 4		4)
(00000E79 57 5 0		list)
(00000E7C 50 5		5)
(00000E7E 57 3 0		list)
(00000E81 50 4		4)
(00000E83 3 176 1		*ed-find-size*)
(00000E86 41		cdr)
(00000E87 81 2 135 1 1 0		make-ipoint)
(00000E8D 3 173 1		*ed-grep-project-size*)
(00000E90 53 3 143 1 1 32		di-fmt-pos-alist)
(00000E96 3 141 1		*editor-find-dialog-items*)
(00000E99 81 2 134 1 1 0		revappend)
(00000E9F 26 133 1		*editor-find-in-project-items*)
(00000EA2 9 133 1		'*editor-find-in-project-items*)
(00000EA5 10)
(00000EA6 3 173 1		*ed-grep-project-size*)
(00000EA9 3 173 1		*ed-grep-project-size*)
(00000EAC 40		car)
(00000EAD 3 176 1		*ed-find-size*)
(00000EB0 40		car)
(00000EB1 81 2 132 1 1 0		MAX)
(00000EB7 81 2 131 1 1 0		setcar)
(00000EBD 10)
(00000EBE 3 176 1		*ed-find-size*)
(00000EC1 40		car)
(00000EC2 3 176 1		*ed-find-size*)
(00000EC5 41		cdr)
(00000EC6 42		cons)
(00000EC7 11)
(00000EC8 6 172 1		*ed-grep-size*)
(00000ECB 10)
(00000ECC 9 130 1		':VC)
(00000ECF 50 2		2)
(00000ED1 9 149 1		':H)
(00000ED4 9 148 1		':V)
(00000ED7 50 2		2)
(00000ED9 51 52 0 12 0		786484)
(00000EDE 9 187 1		"VLMSG.DLL")
(00000EE1 51 224 76 0 0		19680)
(00000EE6 81 2 186 1 1 0		string-resource)
(00000EEC 9 147 1		':LEFT)
(00000EEF 53 3 146 1 1 32		static-text)
(00000EF5 57 3 0		list)
(00000EF8 50 1		1)
(00000EFA 9 148 1		':V)
(00000EFD 5 17		UnVar17)
(00000EFF 50 1		1)
(00000F01 5 8		UnVar8)
(00000F03 57 4 0		list)
(00000F06 50 5		5)
(00000F08 5 7		UnVar7)
(00000F0A 50 5		5)
(00000F0C 57 7 0		list)
(00000F0F 50 5		5)
(00000F11 57 4 0		list)
(00000F14 50 5		5)
(00000F16 3 176 1		*ed-find-size*)
(00000F19 41		cdr)
(00000F1A 81 2 135 1 1 0		make-ipoint)
(00000F20 3 172 1		*ed-grep-size*)
(00000F23 53 3 143 1 1 32		di-fmt-pos-alist)
(00000F29 3 141 1		*editor-find-dialog-items*)
(00000F2C 81 2 134 1 1 0		revappend)
(00000F32 26 129 1		*editor-find-in-files-items*)
(00000F35 9 129 1		'*editor-find-in-files-items*)
(00000F38 10)
(00000F39 3 172 1		*ed-grep-size*)
(00000F3C 3 172 1		*ed-grep-size*)
(00000F3F 40		car)
(00000F40 3 176 1		*ed-find-size*)
(00000F43 40		car)
(00000F44 81 2 132 1 1 0		MAX)
(00000F4A 81 2 131 1 1 0		setcar)
(00000F50 10)
(00000F51 5 11		UnVar11)
(00000F53 51 128 0 60 0		3932288)
(00000F58 9 128 1		'size)
(00000F5B 81 3 127 1 1 0		slot-value<-)
(00000F61 10)
(00000F62 5 12		UnVar12)
(00000F64 51 128 0 60 0		3932288)
(00000F69 9 128 1		'size)
(00000F6C 81 3 127 1 1 0		slot-value<-)
(00000F72 10)
(00000F73 5 18		UnVar18)
(00000F75 51 128 0 44 0		2883712)
(00000F7A 9 128 1		'size)
(00000F7D 81 3 127 1 1 0		slot-value<-)
(00000F83 10)
(00000F84 5 17		UnVar17)
(00000F86 51 128 0 44 0		2883712)
(00000F8B 9 128 1		'size)
(00000F8E 81 3 127 1 1 0		slot-value<-)
(00000F94 10)
(00000F95 1		nil)
(00000F96 3 176 1		*ed-find-size*)
(00000F99 40		car)
(00000F9A 3 176 1		*ed-find-size*)
(00000F9D 41		cdr)
(00000F9E 81 2 135 1 1 0		make-ipoint)
(00000FA4 9 187 1		"VLMSG.DLL")
(00000FA7 51 92 88 0 0		22620)
(00000FAC 81 2 186 1 1 0		string-resource)
(00000FB2 3 141 1		*editor-find-dialog-items*)
(00000FB5 9 126 1		':DEFAULT-PUSH-BUTTON)
(00000FB8 5 13		UnVar13)
(00000FBA 9 125 1		':LABELS)
(00000FBD 5 9		UnVar9)
(00000FBF 9 124 1		':FONT)
(00000FC2 3 123 1		*inspector-font*)
(00000FC5 9 122 1		':PITCH)
(00000FC8 3 121 1		*inspector-pitch*)
(00000FCB 53 12 120 1 1 32		dialog-with-labels)
(00000FD1 26 119 1		*editor-find-dialog*)
(00000FD4 9 119 1		'*editor-find-dialog*)
(00000FD7 10)
(00000FD8 3 119 1		*editor-find-dialog*)
(00000FDB 50 16		16)
(00000FDD 81 2 118 1 1 0		dialog._border-style<-)
(00000FE3 10)
(00000FE4 1		nil)
(00000FE5 3 174 1		*ed-replace-size*)
(00000FE8 40		car)
(00000FE9 3 174 1		*ed-replace-size*)
(00000FEC 41		cdr)
(00000FED 81 2 135 1 1 0		make-ipoint)
(00000FF3 9 187 1		"VLMSG.DLL")
(00000FF6 51 102 88 0 0		22630)
(00000FFB 81 2 186 1 1 0		string-resource)
(00001001 3 136 1		*editor-replace-dialog-items*)
(00001004 9 126 1		':DEFAULT-PUSH-BUTTON)
(00001007 5 13		UnVar13)
(00001009 9 125 1		':LABELS)
(0000100C 5 9		UnVar9)
(0000100E 9 124 1		':FONT)
(00001011 3 123 1		*inspector-font*)
(00001014 9 122 1		':PITCH)
(00001017 3 121 1		*inspector-pitch*)
(0000101A 53 12 120 1 1 32		dialog-with-labels)
(00001020 26 117 1		*editor-replace-dialog*)
(00001023 9 117 1		'*editor-replace-dialog*)
(00001026 10)
(00001027 3 117 1		*editor-replace-dialog*)
(0000102A 50 16		16)
(0000102C 81 2 118 1 1 0		dialog._border-style<-)
(00001032 10)
(00001033 9 3 3		'swap-selection)
(00001036 26 116 1		swap-selection)
(00001039 9 116 1		'swap-selection)
(0000103C 10)
(0000103D 9 2 3		'next-find/replace!)
(00001040 26 115 1		next-find/replace!)
(00001043 9 115 1		'next-find/replace!)
(00001046 10)
(00001047 9 1 3		'find!)
(0000104A 26 114 1		find!)
(0000104D 9 114 1		'find!)
(00001050 10)
(00001051 9 0 3		'!editor-selection-p)
(00001054 26 113 1		!editor-selection-p)
(00001057 9 113 1		'!editor-selection-p)
(0000105A 10)
(0000105B 9 255 2		'!editor-use-selection)
(0000105E 26 112 1		!editor-use-selection)
(00001061 9 112 1		'!editor-use-selection)
(00001064 10)
(00001065 9 254 2		'!editor-drop-selection)
(00001068 26 111 1		!editor-drop-selection)
(0000106B 9 111 1		'!editor-drop-selection)
(0000106E 10)
(0000106F 9 5 3		'_tune-find-command)
(00001072 26 110 1		_tune-find-command)
(00001075 9 110 1		'_tune-find-command)
(00001078 10)
(00001079 9 253 2		'_set-find-mode)
(0000107C 26 109 1		_set-find-mode)
(0000107F 9 109 1		'_set-find-mode)
(00001082 10)
(00001083 9 252 2		'_switch-to-replace)
(00001086 26 108 1		_switch-to-replace)
(00001089 9 108 1		'_switch-to-replace)
(0000108C 10)
(0000108D 9 4 3		'_tune-replace-command)
(00001090 26 107 1		_tune-replace-command)
(00001093 9 107 1		'_tune-replace-command)
(00001096 10)
(00001097 9 251 2		'_set-replace-mode)
(0000109A 26 106 1		_set-replace-mode)
(0000109D 9 106 1		'_set-replace-mode)
(000010A0 10)
(000010A1 9 250 2		'update-find-hist)
(000010A4 26 105 1		update-find-hist)
(000010A7 9 105 1		'update-find-hist)
(000010AA 10)
(000010AB 1		nil)
(000010AC 10)
(000010AD 9 249 2		'!?find)
(000010B0 26 104 1		!?find)
(000010B3 9 104 1		'!?find)
(000010B6 10)
(000010B7 9 248 2		'>@find)
(000010BA 26 103 1		>@find)
(000010BD 9 103 1		'>@find)
(000010C0 10)
(000010C1 9 247 2		'!?replace)
(000010C4 26 102 1		!?replace)
(000010C7 9 102 1		'!?replace)
(000010CA 10)
(000010CB 1		nil)
(000010CC 10)
(000010CD 1		nil)
(000010CE 10)
(000010CF 9 246 2		'>@replace)
(000010D2 26 101 1		>@replace)
(000010D5 9 101 1		'>@replace)
(000010D8 10)
(000010D9 9 245 2		'replace!)
(000010DC 26 100 1		replace!)
(000010DF 9 100 1		'replace!)
(000010E2 10)
(000010E3 9 244 2		'!?next-find/replace)
(000010E6 26 99 1		!?next-find/replace)
(000010E9 9 99 1		'!?next-find/replace)
(000010EC 10)
(000010ED 9 243 2		'>@next-find/replace)
(000010F0 26 98 1		>@next-find/replace)
(000010F3 9 98 1		'>@next-find/replace)
(000010F6 10)
(000010F7 1		nil)
(000010F8 10)
(000010F9 1		nil)
(000010FA 10)
(000010FB 1		nil)
(000010FC 10)
(000010FD 1		nil)
(000010FE 10)
(000010FF 9 242 2		'replace-all!)
(00001102 26 97 1		replace-all!)
(00001105 9 97 1		'replace-all!)
(00001108 10)
(00001109 9 241 2		'_replace-selection)
(0000110C 26 96 1		_replace-selection)
(0000110F 9 96 1		'_replace-selection)
(00001112 10)
(00001113 9 240 2		'!find-via-ribbon)
(00001116 26 95 1		!find-via-ribbon)
(00001119 9 95 1		'!find-via-ribbon)
(0000111C 10)
(0000111D 9 239 2		'!goto-line)
(00001120 26 94 1		!goto-line)
(00001123 9 94 1		'!goto-line)
(00001126 10)
(00001127 1		nil)
(00001128 10)
(00001129 9 238 2		'!cursor-info)
(0000112C 26 93 1		!cursor-info)
(0000112F 9 93 1		'!cursor-info)
(00001132 10)
(00001133 9 237 2		'!find-fast)
(00001136 26 92 1		!find-fast)
(00001139 9 92 1		'!find-fast)
(0000113C 28		[ret])
(0000113D 20 0 0 0 0)
(00001142 1		nil)
(00001143 10)
(00001144 1		nil)
(00001145 10)
(00001146 9 91 1		"\\/")
(00001149 3 90 1		*exe-dir*)
(0000114C 81 2 89 1 1 0		string-right-trim)
(00001152 9 88 1		"/$vld$.dcl")
(00001155 81 2 92 2 1 0		concat)
(0000115B 27 87 1		*dcl-tmp-file*)
(0000115E 9 87 1		'*dcl-tmp-file*)
(00001161 10)
(00001162 3 86 1		*dcl-dialog-name-history*)
(00001165 27 86 1		*dcl-dialog-name-history*)
(00001168 9 86 1		'*dcl-dialog-name-history*)
(0000116B 10)
(0000116C 3 85 1		*dcl-dialog-name-last*)
(0000116F 27 85 1		*dcl-dialog-name-last*)
(00001172 9 85 1		'*dcl-dialog-name-last*)
(00001175 10)
(00001176 9 84 1		"\003\003\003((lambda(/ id)(setq id(LOAD_DIALOG ~s))~\n(cond((>= id 0)(if(NEW_DIALOG ~s id \"(done_dialog)\")~\n(START_DIALOG))(UNLOAD_DIALOG id))))) ")
(00001179 26 83 1		*dcl-preview-fmt*)
(0000117C 9 83 1		'*dcl-preview-fmt*)
(0000117F 10)
(00001180 1		nil)
(00001181 10)
(00001182 9 236 2		'!?preview-dcl-dialog)
(00001185 26 82 1		!?preview-dcl-dialog)
(00001188 9 82 1		'!?preview-dcl-dialog)
(0000118B 10)
(0000118C 9 235 2		'!preview-dcl-dialog)
(0000118F 26 81 1		!preview-dcl-dialog)
(00001192 9 81 1		'!preview-dcl-dialog)
(00001195 10)
(00001196 12 234 2		'_do-preview-dcl-dialog)
(00001199 26 80 1		_do-preview-dcl-dialog)
(0000119C 9 80 1		'_do-preview-dcl-dialog)
(0000119F 10)
(000011A0 9 233 2		'next-sym/spec/paren)
(000011A3 26 79 1		next-sym/spec/paren)
(000011A6 9 79 1		'next-sym/spec/paren)
(000011A9 10)
(000011AA 1		nil)
(000011AB 28		[ret])
(000011AC 20 0 0 0 0)
(000011B1 1		nil)
(000011B2 10)
(000011B3 1		nil)
(000011B4 10)
(000011B5 1		nil)
(000011B6 10)
(000011B7 3 78 1		*grep-output*)
(000011BA 14 20 0		T->JMP 000011D1)
(000011BD 9 187 1		"VLMSG.DLL")
(000011C0 51 14 86 0 0		22030)
(000011C5 81 2 186 1 1 0		string-resource)
(000011CB 53 1 77 1 1 32		outwin)
(000011D1 26 78 1		*grep-output*)
(000011D4 9 78 1		'*grep-output*)
(000011D7 10)
(000011D8 3 156 1		*editor-filelist-hist*)
(000011DB 27 156 1		*editor-filelist-hist*)
(000011DE 9 156 1		'*editor-filelist-hist*)
(000011E1 10)
(000011E2 1		nil)
(000011E3 10)
(000011E4 1		nil)
(000011E5 10)
(000011E6 1		nil)
(000011E7 10)
(000011E8 9 232 2		'grep-filelist-fn)
(000011EB 26 76 1		grep-filelist-fn)
(000011EE 9 76 1		'grep-filelist-fn)
(000011F1 10)
(000011F2 12 231 2		'grep-filelist)
(000011F5 26 75 1		grep-filelist)
(000011F8 9 75 1		'grep-filelist)
(000011FB 10)
(000011FC 9 230 2		'grep-message)
(000011FF 26 74 1		grep-message)
(00001202 9 74 1		'grep-message)
(00001205 10)
(00001206 1		nil)
(00001207 10)
(00001208 3 165 1		*grep-subdirs*)
(0000120B 27 165 1		*grep-subdirs*)
(0000120E 9 165 1		'*grep-subdirs*)
(00001211 10)
(00001212 1		nil)
(00001213 10)
(00001214 12 229 2		'_do-grep-flist)
(00001217 26 73 1		_do-grep-flist)
(0000121A 9 73 1		'_do-grep-flist)
(0000121D 10)
(0000121E 9 8 3		'!grep-choose-source-directory)
(00001221 26 72 1		!grep-choose-source-directory)
(00001224 9 72 1		'!grep-choose-source-directory)
(00001227 10)
(00001228 9 228 2		'!editor-init-grep-files)
(0000122B 26 71 1		!editor-init-grep-files)
(0000122E 9 71 1		'!editor-init-grep-files)
(00001231 10)
(00001232 9 227 2		'!editor-grep-files)
(00001235 26 70 1		!editor-grep-files)
(00001238 9 70 1		'!editor-grep-files)
(0000123B 10)
(0000123C 9 69 1		"Dummy")
(0000123F 9 169 1		'identity)
(00001242 53 2 68 1 1 32		menu-item)
(00001248 26 67 1		@find-in-files)
(0000124B 9 67 1		'@find-in-files)
(0000124E 28		[ret])
(0000124F 20 0 0 0 0)
(00001254 1		nil)
(00001255 10)
(00001256 1		nil)
(00001257 10)
(00001258 1		nil)
(00001259 10)
(0000125A 1		nil)
(0000125B 10)
(0000125C 1		nil)
(0000125D 10)
(0000125E 50 32		32)
(00001260 26 66 1		*mark-ring-length*)
(00001263 9 66 1		'*mark-ring-length*)
(00001266 10)
(00001267 12 226 2		'!mark-ring-add)
(0000126A 26 65 1		!mark-ring-add)
(0000126D 9 65 1		'!mark-ring-add)
(00001270 10)
(00001271 9 225 2		'!mark-ring-prev)
(00001274 26 64 1		!mark-ring-prev)
(00001277 9 64 1		'!mark-ring-prev)
(0000127A 10)
(0000127B 9 224 2		'!mark-ring-next)
(0000127E 26 63 1		!mark-ring-next)
(00001281 9 63 1		'!mark-ring-next)
(00001284 10)
(00001285 9 223 2		'!mark-ring-clear)
(00001288 26 62 1		!mark-ring-clear)
(0000128B 9 62 1		'!mark-ring-clear)
(0000128E 10)
(0000128F 9 222 2		'!mark-ring-select-to-prev)
(00001292 26 61 1		!mark-ring-select-to-prev)
(00001295 9 61 1		'!mark-ring-select-to-prev)
(00001298 10)
(00001299 9 221 2		'!mark-ring-select-to-next)
(0000129C 26 60 1		!mark-ring-select-to-next)
(0000129F 9 60 1		'!mark-ring-select-to-next)
(000012A2 10)
(000012A3 9 220 2		'!mark-ring-toggle)
(000012A6 26 59 1		!mark-ring-toggle)
(000012A9 9 59 1		'!mark-ring-toggle)
(000012AC 28		[ret])
(000012AD 20 0 0 0 0)
(000012B2 1		nil)
(000012B3 10)
(000012B4 1		nil)
(000012B5 10)
(000012B6 9 219 2		'!?debug-step)
(000012B9 26 58 1		!?debug-step)
(000012BC 9 58 1		'!?debug-step)
(000012BF 10)
(000012C0 1		nil)
(000012C1 10)
(000012C2 9 218 2		'sdb-step-in!)
(000012C5 26 57 1		sdb-step-in!)
(000012C8 9 57 1		'sdb-step-in!)
(000012CB 10)
(000012CC 9 217 2		'sdb-step!)
(000012CF 26 56 1		sdb-step!)
(000012D2 9 56 1		'sdb-step!)
(000012D5 10)
(000012D6 9 216 2		'sdb-ret!)
(000012D9 26 55 1		sdb-ret!)
(000012DC 9 55 1		'sdb-ret!)
(000012DF 10)
(000012E0 1		nil)
(000012E1 28		[ret])
(000012E2 20 0 0 0 0)
(000012E7 1		nil)
(000012E8 10)
(000012E9 9 54 1		'((* . 65539) (+ . 65537) (- . 65538) (/ . 65540) (/= . 65542) (1+ . 65554) (1- . 65555) (< . 65543) (<= . 65544) (= . 65541) (> . 65545) (>= . 65552) (car . 65604) (caaaar . 65604) (caaadr . 65604) (caaar . 65604) (caadar . 65604) (caaddr . 65604) (caadr . 65604) (caar . 65604) (cadaar . 65604) (cadadr . 65604) (cadar . 65604) (caddar . 65604) (cadddr . 65604) (caddr . 65604) (cadr . 65604) (cdaaar . 65604) (cdaadr . 65604) (cdaar . 65604) (cdadar . 65604) (cdaddr . 65604) (cdadr . 65604) (cdar . 65604) (cddaar . 65604) (cddadr . 65604) (cddar . 65604) (cdddar . 65604) (cddddr . 65604) (cdddr . 65604) (cddr . 65604) (cdr . 65604) (DIMX_TILE . 65632) (DIMY_TILE . 65632) (~ . 65553)))
(000012EC 26 53 1		*al-hids-alist*)
(000012EF 9 53 1		'*al-hids-alist*)
(000012F2 28		[ret])
(000012F3 20 0 0 0 0)
(000012F8 1		nil)
(000012F9 10)
(000012FA 1		nil)
(000012FB 10)
(000012FC 81 0 52 1 1 0		in-ads-check)
(00001302 13 12 0		nil->JMP 00001311)
(00001305 9 51 1		"lpp-lisp.chm")
(00001308 81 1 50 1 1 0		as:findfile)
(0000130E 15 9 0		JMP 0000131A)
(00001311 9 51 1		"lpp-lisp.chm")
(00001314 81 1 49 1 1 0		find-file)
(0000131A 27 48 1		*lpp-help-file*)
(0000131D 9 48 1		'*lpp-help-file*)
(00001320 10)
(00001321 81 0 52 1 1 0		in-ads-check)
(00001327 13 12 0		nil->JMP 00001336)
(0000132A 9 47 1		"acad_dev191.chm")
(0000132D 81 1 50 1 1 0		as:findfile)
(00001333 15 9 0		JMP 0000133F)
(00001336 9 47 1		"acad_dev191.chm")
(00001339 81 1 49 1 1 0		find-file)
(0000133F 27 46 1		*vl-help-file*)
(00001342 9 46 1		'*vl-help-file*)
(00001345 10)
(00001346 9 215 2		'help-on-help!)
(00001349 26 45 1		help-on-help!)
(0000134C 9 45 1		'help-on-help!)
(0000134F 10)
(00001350 1		nil)
(00001351 10)
(00001352 9 214 2		'help-contents!)
(00001355 26 44 1		help-contents!)
(00001358 9 44 1		'help-contents!)
(0000135B 10)
(0000135C 9 213 2		'!help-tutorial)
(0000135F 26 43 1		!help-tutorial)
(00001362 9 43 1		'!help-tutorial)
(00001365 10)
(00001366 9 212 2		'help-search!)
(00001369 26 42 1		help-search!)
(0000136C 9 42 1		'help-search!)
(0000136F 10)
(00001370 9 211 2		'help-lisp!)
(00001373 26 41 1		help-lisp!)
(00001376 9 41 1		'help-lisp!)
(00001379 10)
(0000137A 9 210 2		'lisp-help-on-key)
(0000137D 26 40 1		lisp-help-on-key)
(00001380 9 40 1		'lisp-help-on-key)
(00001383 10)
(00001384 1		nil)
(00001385 10)
(00001386 1		nil)
(00001387 10)
(00001388 1		nil)
(00001389 10)
(0000138A 1		nil)
(0000138B 10)
(0000138C 1		nil)
(0000138D 10)
(0000138E 1		nil)
(0000138F 10)
(00001390 1		nil)
(00001391 10)
(00001392 9 39 1		"MS Sans Serif Bold")
(00001395 26 38 1		*about-font*)
(00001398 9 38 1		'*about-font*)
(0000139B 10)
(0000139C 50 8		8)
(0000139E 26 37 1		*about-pitch*)
(000013A1 9 37 1		'*about-pitch*)
(000013A4 10)
(000013A5 1		nil)
(000013A6 10)
(000013A7 1		nil)
(000013A8 10)
(000013A9 1		nil)
(000013AA 10)
(000013AB 1		nil)
(000013AC 10)
(000013AD 9 209 2		'about-lx!)
(000013B0 26 36 1		about-lx!)
(000013B3 9 36 1		'about-lx!)
(000013B6 10)
(000013B7 9 208 2		'about!)
(000013BA 26 35 1		about!)
(000013BD 9 35 1		'about!)
(000013C0 28		[ret])
(000013C1 20 0 0 0 0)
(000013C6 1		nil)
(000013C7 10)
(000013C8 1		nil)
(000013C9 10)
(000013CA 50 32		32)
(000013CC 27 34 1		*history-maxlen*)
(000013CF 9 34 1		'*history-maxlen*)
(000013D2 10)
(000013D3 3 33 1		*console-history*)
(000013D6 27 33 1		*console-history*)
(000013D9 9 33 1		'*console-history*)
(000013DC 10)
(000013DD 1		nil)
(000013DE 27 32 1		*console-history-last-shown*)
(000013E1 9 32 1		'*console-history-last-shown*)
(000013E4 10)
(000013E5 1		nil)
(000013E6 27 31 1		*console-history-last-tag*)
(000013E9 9 31 1		'*console-history-last-tag*)
(000013EC 10)
(000013ED 1		nil)
(000013EE 10)
(000013EF 1		nil)
(000013F0 10)
(000013F1 1		nil)
(000013F2 10)
(000013F3 1		nil)
(000013F4 10)
(000013F5 9 207 2		'history-add)
(000013F8 26 30 1		history-add)
(000013FB 9 30 1		'history-add)
(000013FE 10)
(000013FF 1		nil)
(00001400 10)
(00001401 1		nil)
(00001402 10)
(00001403 9 206 2		'!history-up)
(00001406 26 29 1		!history-up)
(00001409 9 29 1		'!history-up)
(0000140C 10)
(0000140D 9 205 2		'!history-down)
(00001410 26 28 1		!history-down)
(00001413 9 28 1		'!history-down)
(00001416 28		[ret])
(00001417 20 0 0 0 0)
(0000141C 1		nil)
(0000141D 10)
(0000141E 1		nil)
(0000141F 10)
(00001420 2		T)
(00001421 27 27 1		*dax-nocase*)
(00001424 9 27 1		'*dax-nocase*)
(00001427 10)
(00001428 1		nil)
(00001429 27 26 1		*dax-back*)
(0000142C 9 26 1		'*dax-back*)
(0000142F 10)
(00001430 1		nil)
(00001431 27 25 1		*dax-tag*)
(00001434 9 25 1		'*dax-tag*)
(00001437 10)
(00001438 50 0		0)
(0000143A 27 24 1		*dax-tbeg*)
(0000143D 9 24 1		'*dax-tbeg*)
(00001440 10)
(00001441 50 0		0)
(00001443 27 23 1		*dax-tick*)
(00001446 9 23 1		'*dax-tick*)
(00001449 10)
(0000144A 1		nil)
(0000144B 27 22 1		*dax-xstr*)
(0000144E 9 22 1		'*dax-xstr*)
(00001451 10)
(00001452 50 255		-1)
(00001454 27 21 1		*dax-xend*)
(00001457 9 21 1		'*dax-xend*)
(0000145A 10)
(0000145B 1		nil)
(0000145C 27 20 1		*dax-xtbl*)
(0000145F 9 20 1		'*dax-xtbl*)
(00001462 10)
(00001463 50 0		0)
(00001465 27 19 1		*dax-beg-pos*)
(00001468 9 19 1		'*dax-beg-pos*)
(0000146B 10)
(0000146C 1		nil)
(0000146D 27 18 1		*dax-end-mark*)
(00001470 9 18 1		'*dax-end-mark*)
(00001473 10)
(00001474 1		nil)
(00001475 27 17 1		*dax-prompt*)
(00001478 9 17 1		'*dax-prompt*)
(0000147B 10)
(0000147C 9 204 2		'!dabbrev-expand)
(0000147F 26 16 1		!dabbrev-expand)
(00001482 9 16 1		'!dabbrev-expand)
(00001485 10)
(00001486 1		nil)
(00001487 10)
(00001488 1		nil)
(00001489 10)
(0000148A 1		nil)
(0000148B 10)
(0000148C 1		nil)
(0000148D 10)
(0000148E 1		nil)
(0000148F 28		[ret])
(00001490 20 0 0 0 0)
(00001495 1		nil)
(00001496 10)
(00001497 1		nil)
(00001498 10)
(00001499 9 203 2		'!?al-check)
(0000149C 26 15 1		!?al-check)
(0000149F 9 15 1		'!?al-check)
(000014A2 10)
(000014A3 1		nil)
(000014A4 10)
(000014A5 9 187 1		"VLMSG.DLL")
(000014A8 51 68 82 0 0		21060)
(000014AD 81 2 186 1 1 0		string-resource)
(000014B3 53 1 77 1 1 32		outwin)
(000014B9 27 14 1		*build-window*)
(000014BC 9 14 1		'*build-window*)
(000014BF 10)
(000014C0 12 202 2		'al-check-ed)
(000014C3 26 13 1		al-check-ed)
(000014C6 9 13 1		'al-check-ed)
(000014C9 10)
(000014CA 9 201 2		'!al-check-selection)
(000014CD 26 12 1		!al-check-selection)
(000014D0 9 12 1		'!al-check-selection)
(000014D3 10)
(000014D4 9 200 2		'!al-check-buffer)
(000014D7 26 11 1		!al-check-buffer)
(000014DA 9 11 1		'!al-check-buffer)
(000014DD 10)
(000014DE 12 199 2		'!al-check-file)
(000014E1 26 10 1		!al-check-file)
(000014E4 9 10 1		'!al-check-file)
(000014E7 28		[ret])
(000014E8 20 0 0 0 0)
(000014ED 1		nil)
(000014EE 10)
(000014EF 1		nil)
(000014F0 10)
(000014F1 1		nil)
(000014F2 10)
(000014F3 9 198 2		'mdiwins->list)
(000014F6 26 9 1		mdiwins->list)
(000014F9 9 9 1		'mdiwins->list)
(000014FC 10)
(000014FD 1		nil)
(000014FE 10)
(000014FF 9 197 2		'window-1!)
(00001502 26 8 1		window-1!)
(00001505 9 8 1		'window-1!)
(00001508 10)
(00001509 9 196 2		'window-2!)
(0000150C 26 7 1		window-2!)
(0000150F 9 7 1		'window-2!)
(00001512 10)
(00001513 9 195 2		'window-3!)
(00001516 26 6 1		window-3!)
(00001519 9 6 1		'window-3!)
(0000151C 10)
(0000151D 9 194 2		'window-4!)
(00001520 26 5 1		window-4!)
(00001523 9 5 1		'window-4!)
(00001526 10)
(00001527 9 193 2		'window-5!)
(0000152A 26 4 1		window-5!)
(0000152D 9 4 1		'window-5!)
(00001530 10)
(00001531 9 192 2		'window-6!)
(00001534 26 3 1		window-6!)
(00001537 9 3 1		'window-6!)
(0000153A 10)
(0000153B 9 191 2		'window-7!)
(0000153E 26 2 1		window-7!)
(00001541 9 2 1		'window-7!)
(00001544 10)
(00001545 9 190 2		'window-8!)
(00001548 26 1 1		window-8!)
(0000154B 9 1 1		'window-8!)
(0000154E 10)
(0000154F 9 189 2		'window-9!)
(00001552 26 0 1		window-9!)
(00001555 9 0 1		'window-9!)
(00001558 10)
(00001559 12 188 2		'make-mm-cmd)
(0000155C 26 255 0		make-mm-cmd)
(0000155F 9 255 0		'make-mm-cmd)
(00001562 10)
(00001563 1		nil)
(00001564 10)
(00001565 9 187 2		'window-list!)
(00001568 26 254 0		window-list!)
(0000156B 9 254 0		'window-list!)
(0000156E 10)
(0000156F 9 186 2		'window-iconize-all!)
(00001572 26 253 0		window-iconize-all!)
(00001575 9 253 0		'window-iconize-all!)
(00001578 10)
(00001579 1		nil)
(0000157A 10)
(0000157B 9 185 2		'show-vlisp-windows)
(0000157E 26 252 0		show-vlisp-windows)
(00001581 9 252 0		'show-vlisp-windows)
(00001584 10)
(00001585 9 184 2		'hide-vlisp-windows)
(00001588 26 251 0		hide-vlisp-windows)
(0000158B 9 251 0		'hide-vlisp-windows)
(0000158E 28		[ret])
(0000158F 20 0 0 0 0)
(00001594 1		nil)
(00001595 10)
(00001596 1		nil)
(00001597 10)
(00001598 9 183 2		'is-pref-:LEX)
(0000159B 26 250 0		is-pref-:LEX)
(0000159E 9 250 0		'is-pref-:LEX)
(000015A1 10)
(000015A2 9 182 2		'twin.color-id-list)
(000015A5 26 249 0		twin.color-id-list)
(000015A8 9 249 0		'twin.color-id-list)
(000015AB 10)
(000015AC 9 248 0		':WINDOW-TEXT)
(000015AF 53 1 247 0 1 32		twin-color-name->id)
(000015B5 26 246 0		*WT-ci*)
(000015B8 9 246 0		'*WT-ci*)
(000015BB 10)
(000015BC 9 181 2		'_small-positive)
(000015BF 26 245 0		_small-positive)
(000015C2 9 245 0		'_small-positive)
(000015C5 10)
(000015C6 9 180 2		'_update-winattr-dlg)
(000015C9 26 244 0		_update-winattr-dlg)
(000015CC 9 244 0		'_update-winattr-dlg)
(000015CF 10)
(000015D0 12 179 2		'!window-attr)
(000015D3 26 243 0		!window-attr)
(000015D6 9 243 0		'!window-attr)
(000015D9 10)
(000015DA 1		nil)
(000015DB 10)
(000015DC 1		nil)
(000015DD 10)
(000015DE 1		nil)
(000015DF 10)
(000015E0 1		nil)
(000015E1 10)
(000015E2 1		nil)
(000015E3 10)
(000015E4 1		nil)
(000015E5 10)
(000015E6 1		nil)
(000015E7 10)
(000015E8 9 178 2		'!editor-coloring)
(000015EB 26 242 0		!editor-coloring)
(000015EE 9 242 0		'!editor-coloring)
(000015F1 10)
(000015F2 9 177 2		'set-color-dialog)
(000015F5 26 241 0		set-color-dialog)
(000015F8 9 241 0		'set-color-dialog)
(000015FB 10)
(000015FC 9 176 2		'>@editor-coloring)
(000015FF 26 240 0		>@editor-coloring)
(00001602 9 240 0		'>@editor-coloring)
(00001605 10)
(00001606 9 175 2		'!edit-font)
(00001609 26 239 0		!edit-font)
(0000160C 9 239 0		'!edit-font)
(0000160F 28		[ret])
(00001610 21 2 0 0 0)
(00001615 1		nil)
(00001616 10)
(00001617 1		nil)
(00001618 10)
(00001619 1		nil)
(0000161A 10)
(0000161B 51 150 0 9 0		589974)
(00001620 27 238 0		*dio-acb-sz*)
(00001623 9 238 0		'*dio-acb-sz*)
(00001626 10)
(00001627 1		nil)
(00001628 10)
(00001629 9 174 2		'dio-acb)
(0000162C 26 237 0		dio-acb)
(0000162F 9 237 0		'dio-acb)
(00001632 10)
(00001633 1		nil)
(00001634 10)
(00001635 1		nil)
(00001636 10)
(00001637 1		nil)
(00001638 10)
(00001639 50 0		0)
(0000163B 8 0		UnVar0)
(0000163D 50 0		0)
(0000163F 8 1		UnVar1)
(00001641 12 173 2		'general-options!)
(00001644 26 236 0		general-options!)
(00001647 9 236 0		'general-options!)
(0000164A 28		[ret])
(0000164B 20 0 0 0 0)
(00001650 1		nil)
(00001651 10)
(00001652 1		nil)
(00001653 10)
(00001654 9 235 0		"VLRES.DLL")
(00001657 26 234 0		*lppbtn*)
(0000165A 9 234 0		'*lppbtn*)
(0000165D 10)
(0000165E 50 21		21)
(00001660 26 233 0		*btn-wid*)
(00001663 9 233 0		'*btn-wid*)
(00001666 10)
(00001667 50 19		19)
(00001669 26 232 0		*btn-ht*)
(0000166C 9 232 0		'*btn-ht*)
(0000166F 10)
(00001670 50 16		16)
(00001672 26 231 0		*btn-wid16*)
(00001675 9 231 0		'*btn-wid16*)
(00001678 10)
(00001679 50 16		16)
(0000167B 26 230 0		*btn-ht16*)
(0000167E 9 230 0		'*btn-ht16*)
(00001681 10)
(00001682 3 231 0		*btn-wid16*)
(00001685 3 230 0		*btn-ht16*)
(00001688 81 2 135 1 1 0		make-ipoint)
(0000168E 26 229 0		*btn-dim16*)
(00001691 9 229 0		'*btn-dim16*)
(00001694 10)
(00001695 3 233 0		*btn-wid*)
(00001698 3 232 0		*btn-ht*)
(0000169B 81 2 135 1 1 0		make-ipoint)
(000016A1 26 228 0		*btn-dim*)
(000016A4 9 228 0		'*btn-dim*)
(000016A7 10)
(000016A8 2		T)
(000016A9 26 227 0		%bmp_style%)
(000016AC 9 227 0		'%bmp_style%)
(000016AF 10)
(000016B0 9 235 0		"VLRES.DLL")
(000016B3 9 226 0		"bitmap1")
(000016B6 81 2 225 0 1 0		bitmap-resource)
(000016BC 27 224 0		*carp-res0*)
(000016BF 9 224 0		'*carp-res0*)
(000016C2 10)
(000016C3 9 235 0		"VLRES.DLL")
(000016C6 9 223 0		"bitmap3")
(000016C9 81 2 225 0 1 0		bitmap-resource)
(000016CF 27 222 0		*carp-res16*)
(000016D2 9 222 0		'*carp-res16*)
(000016D5 10)
(000016D6 9 172 2		'clip-bmp-pos)
(000016D9 26 221 0		clip-bmp-pos)
(000016DC 9 221 0		'clip-bmp-pos)
(000016DF 10)
(000016E0 9 171 2		'clip-bmp-pos16)
(000016E3 26 220 0		clip-bmp-pos16)
(000016E6 9 220 0		'clip-bmp-pos16)
(000016E9 10)
(000016EA 3 222 0		*carp-res16*)
(000016ED 50 10		10)
(000016EF 50 2		2)
(000016F1 53 2 220 0 1 32		clip-bmp-pos16)
(000016F7 3 229 0		*btn-dim16*)
(000016FA 9 245 1		'load-buffer!)
(000016FD 9 187 1		"VLMSG.DLL")
(00001700 51 252 48 0 0		12540)
(00001705 81 2 186 1 1 0		string-resource)
(0000170B 9 187 1		"VLMSG.DLL")
(0000170E 51 8 87 0 0		22280)
(00001713 81 2 186 1 1 0		string-resource)
(00001719 53 6 219 0 1 32		bmp-push-button1)
(0000171F 27 218 0		*btn-load-buffer*)
(00001722 9 218 0		'*btn-load-buffer*)
(00001725 10)
(00001726 3 222 0		*carp-res16*)
(00001729 50 10		10)
(0000172B 50 3		3)
(0000172D 53 2 220 0 1 32		clip-bmp-pos16)
(00001733 3 229 0		*btn-dim16*)
(00001736 9 46 3		'eval-selection!)
(00001739 9 187 1		"VLMSG.DLL")
(0000173C 51 18 87 0 0		22290)
(00001741 81 2 186 1 1 0		string-resource)
(00001747 9 187 1		"VLMSG.DLL")
(0000174A 51 28 87 0 0		22300)
(0000174F 81 2 186 1 1 0		string-resource)
(00001755 53 6 219 0 1 32		bmp-push-button1)
(0000175B 27 217 0		*btn-load-select*)
(0000175E 9 217 0		'*btn-load-select*)
(00001761 10)
(00001762 3 222 0		*carp-res16*)
(00001765 50 4		4)
(00001767 50 3		3)
(00001769 53 2 220 0 1 32		clip-bmp-pos16)
(0000176F 3 229 0		*btn-dim16*)
(00001772 9 201 2		'!al-check-selection)
(00001775 9 187 1		"VLMSG.DLL")
(00001778 51 56 49 0 0		12600)
(0000177D 81 2 186 1 1 0		string-resource)
(00001783 9 187 1		"VLMSG.DLL")
(00001786 51 38 87 0 0		22310)
(0000178B 81 2 186 1 1 0		string-resource)
(00001791 53 6 219 0 1 32		bmp-push-button1)
(00001797 27 216 0		*btn-check-select*)
(0000179A 9 216 0		'*btn-check-select*)
(0000179D 10)
(0000179E 3 222 0		*carp-res16*)
(000017A1 50 4		4)
(000017A3 50 4		4)
(000017A5 53 2 220 0 1 32		clip-bmp-pos16)
(000017AB 3 229 0		*btn-dim16*)
(000017AE 9 200 2		'!al-check-buffer)
(000017B1 9 187 1		"VLMSG.DLL")
(000017B4 51 76 49 0 0		12620)
(000017B9 81 2 186 1 1 0		string-resource)
(000017BF 9 187 1		"VLMSG.DLL")
(000017C2 51 48 87 0 0		22320)
(000017C7 81 2 186 1 1 0		string-resource)
(000017CD 53 6 219 0 1 32		bmp-push-button1)
(000017D3 27 215 0		*btn-check-buffer*)
(000017D6 9 215 0		'*btn-check-buffer*)
(000017D9 10)
(000017DA 3 222 0		*carp-res16*)
(000017DD 50 11		11)
(000017DF 50 1		1)
(000017E1 53 2 220 0 1 32		clip-bmp-pos16)
(000017E7 3 229 0		*btn-dim16*)
(000017EA 9 214 0		'ppf!)
(000017ED 9 187 1		"VLMSG.DLL")
(000017F0 51 96 49 0 0		12640)
(000017F5 81 2 186 1 1 0		string-resource)
(000017FB 9 187 1		"VLMSG.DLL")
(000017FE 51 58 87 0 0		22330)
(00001803 81 2 186 1 1 0		string-resource)
(00001809 53 6 219 0 1 32		bmp-push-button1)
(0000180F 27 213 0		*btn-format-select*)
(00001812 9 213 0		'*btn-format-select*)
(00001815 10)
(00001816 3 222 0		*carp-res16*)
(00001819 50 11		11)
(0000181B 50 0		0)
(0000181D 53 2 220 0 1 32		clip-bmp-pos16)
(00001823 3 229 0		*btn-dim16*)
(00001826 9 212 0		'ppf-buffer!)
(00001829 9 187 1		"VLMSG.DLL")
(0000182C 51 116 49 0 0		12660)
(00001831 81 2 186 1 1 0		string-resource)
(00001837 9 187 1		"VLMSG.DLL")
(0000183A 51 68 87 0 0		22340)
(0000183F 81 2 186 1 1 0		string-resource)
(00001845 53 6 219 0 1 32		bmp-push-button1)
(0000184B 27 211 0		*btn-format-buffer*)
(0000184E 9 211 0		'*btn-format-buffer*)
(00001851 10)
(00001852 3 224 0		*carp-res0*)
(00001855 50 0		0)
(00001857 50 0		0)
(00001859 81 2 135 1 1 0		make-ipoint)
(0000185F 50 16		16)
(00001861 50 16		16)
(00001863 81 2 135 1 1 0		make-ipoint)
(00001869 81 3 210 0 1 0		bitmap-resource.clip)
(0000186F 27 209 0		*empty-sel*)
(00001872 9 209 0		'*empty-sel*)
(00001875 10)
(00001876 3 222 0		*carp-res16*)
(00001879 50 7		7)
(0000187B 50 0		0)
(0000187D 53 2 220 0 1 32		clip-bmp-pos16)
(00001883 3 229 0		*btn-dim16*)
(00001886 9 208 0		'debug-continue!)
(00001889 9 187 1		"VLMSG.DLL")
(0000188C 51 240 50 0 0		13040)
(00001891 81 2 186 1 1 0		string-resource)
(00001897 9 187 1		"VLMSG.DLL")
(0000189A 51 78 87 0 0		22350)
(0000189F 81 2 186 1 1 0		string-resource)
(000018A5 53 6 219 0 1 32		bmp-push-button1)
(000018AB 27 207 0		*hhand-btn*)
(000018AE 9 207 0		'*hhand-btn*)
(000018B1 10)
(000018B2 3 222 0		*carp-res16*)
(000018B5 50 4		4)
(000018B7 50 2		2)
(000018B9 53 2 220 0 1 32		clip-bmp-pos16)
(000018BF 3 229 0		*btn-dim16*)
(000018C2 9 206 0		'debug-quit!)
(000018C5 9 187 1		"VLMSG.DLL")
(000018C8 51 24 51 0 0		13080)
(000018CD 81 2 186 1 1 0		string-resource)
(000018D3 9 187 1		"VLMSG.DLL")
(000018D6 51 88 87 0 0		22360)
(000018DB 81 2 186 1 1 0		string-resource)
(000018E1 53 6 219 0 1 32		bmp-push-button1)
(000018E7 27 205 0		*quit-btn*)
(000018EA 9 205 0		'*quit-btn*)
(000018ED 10)
(000018EE 3 222 0		*carp-res16*)
(000018F1 50 7		7)
(000018F3 50 4		4)
(000018F5 53 2 220 0 1 32		clip-bmp-pos16)
(000018FB 3 229 0		*btn-dim16*)
(000018FE 9 204 0		'debug-reset!)
(00001901 9 187 1		"VLMSG.DLL")
(00001904 51 4 51 0 0		13060)
(00001909 81 2 186 1 1 0		string-resource)
(0000190F 9 187 1		"VLMSG.DLL")
(00001912 51 98 87 0 0		22370)
(00001917 81 2 186 1 1 0		string-resource)
(0000191D 53 6 219 0 1 32		bmp-push-button1)
(00001923 27 203 0		*reset-btn*)
(00001926 9 203 0		'*reset-btn*)
(00001929 10)
(0000192A 3 222 0		*carp-res16*)
(0000192D 50 0		0)
(0000192F 50 2		2)
(00001931 53 2 220 0 1 32		clip-bmp-pos16)
(00001937 3 229 0		*btn-dim16*)
(0000193A 9 202 0		'Inspect-item!)
(0000193D 9 187 1		"VLMSG.DLL")
(00001940 51 244 46 0 0		12020)
(00001945 81 2 186 1 1 0		string-resource)
(0000194B 9 187 1		"VLMSG.DLL")
(0000194E 51 216 64 0 0		16600)
(00001953 81 2 186 1 1 0		string-resource)
(00001959 53 6 219 0 1 32		bmp-push-button1)
(0000195F 27 201 0		*bino-btn*)
(00001962 9 201 0		'*bino-btn*)
(00001965 10)
(00001966 3 222 0		*carp-res16*)
(00001969 50 1		1)
(0000196B 50 2		2)
(0000196D 53 2 220 0 1 32		clip-bmp-pos16)
(00001973 3 229 0		*btn-dim16*)
(00001976 9 200 0		'add-item-to-watch-window!)
(00001979 9 187 1		"VLMSG.DLL")
(0000197C 51 144 51 0 0		13200)
(00001981 81 2 186 1 1 0		string-resource)
(00001987 9 187 1		"VLMSG.DLL")
(0000198A 51 108 87 0 0		22380)
(0000198F 81 2 186 1 1 0		string-resource)
(00001995 53 6 219 0 1 32		bmp-push-button1)
(0000199B 27 199 0		*btn-watch*)
(0000199E 9 199 0		'*btn-watch*)
(000019A1 10)
(000019A2 3 222 0		*carp-res16*)
(000019A5 50 1		1)
(000019A7 50 4		4)
(000019A9 53 2 220 0 1 32		clip-bmp-pos16)
(000019AF 3 229 0		*btn-dim16*)
(000019B2 9 198 0		'new-watch-window!)
(000019B5 9 187 1		"VLMSG.DLL")
(000019B8 51 68 47 0 0		12100)
(000019BD 81 2 186 1 1 0		string-resource)
(000019C3 9 187 1		"VLMSG.DLL")
(000019C6 51 118 87 0 0		22390)
(000019CB 81 2 186 1 1 0		string-resource)
(000019D1 53 6 219 0 1 32		bmp-push-button1)
(000019D7 27 197 0		*btn-view-watch*)
(000019DA 9 197 0		'*btn-view-watch*)
(000019DD 10)
(000019DE 3 222 0		*carp-res16*)
(000019E1 50 9		9)
(000019E3 50 1		1)
(000019E5 53 2 220 0 1 32		clip-bmp-pos16)
(000019EB 3 229 0		*btn-dim16*)
(000019EE 9 196 0		'!console-show-up)
(000019F1 9 187 1		"VLMSG.DLL")
(000019F4 51 148 47 0 0		12180)
(000019F9 81 2 186 1 1 0		string-resource)
(000019FF 9 187 1		"VLMSG.DLL")
(00001A02 51 16 74 0 0		18960)
(00001A07 81 2 186 1 1 0		string-resource)
(00001A0D 53 6 219 0 1 32		bmp-push-button1)
(00001A13 27 195 0		*btn-console*)
(00001A16 9 195 0		'*btn-console*)
(00001A19 10)
(00001A1A 3 222 0		*carp-res16*)
(00001A1D 50 6		6)
(00001A1F 50 2		2)
(00001A21 53 2 220 0 1 32		clip-bmp-pos16)
(00001A27 3 229 0		*btn-dim16*)
(00001A2A 9 194 0		'symbol-service!)
(00001A2D 9 187 1		"VLMSG.DLL")
(00001A30 51 138 87 0 0		22410)
(00001A35 81 2 186 1 1 0		string-resource)
(00001A3B 9 187 1		"VLMSG.DLL")
(00001A3E 51 148 87 0 0		22420)
(00001A43 81 2 186 1 1 0		string-resource)
(00001A49 53 6 219 0 1 32		bmp-push-button1)
(00001A4F 27 193 0		*btn-ss*)
(00001A52 9 193 0		'*btn-ss*)
(00001A55 10)
(00001A56 3 222 0		*carp-res16*)
(00001A59 50 7		7)
(00001A5B 50 2		2)
(00001A5D 53 2 220 0 1 32		clip-bmp-pos16)
(00001A63 3 229 0		*btn-dim16*)
(00001A66 9 217 2		'sdb-step!)
(00001A69 9 187 1		"VLMSG.DLL")
(00001A6C 51 44 51 0 0		13100)
(00001A71 81 2 186 1 1 0		string-resource)
(00001A77 9 187 1		"VLMSG.DLL")
(00001A7A 51 158 87 0 0		22430)
(00001A7F 81 2 186 1 1 0		string-resource)
(00001A85 53 6 219 0 1 32		bmp-push-button1)
(00001A8B 27 192 0		*step-btn*)
(00001A8E 9 192 0		'*step-btn*)
(00001A91 10)
(00001A92 3 222 0		*carp-res16*)
(00001A95 50 7		7)
(00001A97 50 3		3)
(00001A99 53 2 220 0 1 32		clip-bmp-pos16)
(00001A9F 3 229 0		*btn-dim16*)
(00001AA2 9 218 2		'sdb-step-in!)
(00001AA5 9 187 1		"VLMSG.DLL")
(00001AA8 51 64 51 0 0		13120)
(00001AAD 81 2 186 1 1 0		string-resource)
(00001AB3 9 187 1		"VLMSG.DLL")
(00001AB6 51 168 87 0 0		22440)
(00001ABB 81 2 186 1 1 0		string-resource)
(00001AC1 53 6 219 0 1 32		bmp-push-button1)
(00001AC7 27 191 0		*stepin-btn*)
(00001ACA 9 191 0		'*stepin-btn*)
(00001ACD 10)
(00001ACE 3 222 0		*carp-res16*)
(00001AD1 50 1		1)
(00001AD3 50 0		0)
(00001AD5 53 2 220 0 1 32		clip-bmp-pos16)
(00001ADB 3 229 0		*btn-dim16*)
(00001ADE 9 216 2		'sdb-ret!)
(00001AE1 9 187 1		"VLMSG.DLL")
(00001AE4 51 84 51 0 0		13140)
(00001AE9 81 2 186 1 1 0		string-resource)
(00001AEF 9 187 1		"VLMSG.DLL")
(00001AF2 51 178 87 0 0		22450)
(00001AF7 81 2 186 1 1 0		string-resource)
(00001AFD 53 6 219 0 1 32		bmp-push-button1)
(00001B03 27 190 0		*ret-btn*)
(00001B06 9 190 0		'*ret-btn*)
(00001B09 10)
(00001B0A 3 222 0		*carp-res16*)
(00001B0D 50 1		1)
(00001B0F 50 1		1)
(00001B11 53 2 220 0 1 32		clip-bmp-pos16)
(00001B17 3 229 0		*btn-dim16*)
(00001B1A 9 189 0		'!show-break-cause-source)
(00001B1D 9 187 1		"VLMSG.DLL")
(00001B20 51 188 87 0 0		22460)
(00001B25 81 2 186 1 1 0		string-resource)
(00001B2B 9 187 1		"VLMSG.DLL")
(00001B2E 51 198 87 0 0		22470)
(00001B33 81 2 186 1 1 0		string-resource)
(00001B39 53 6 219 0 1 32		bmp-push-button1)
(00001B3F 27 188 0		*here-btn*)
(00001B42 9 188 0		'*here-btn*)
(00001B45 10)
(00001B46 3 222 0		*carp-res16*)
(00001B49 50 6		6)
(00001B4B 50 4		4)
(00001B4D 53 2 220 0 1 32		clip-bmp-pos16)
(00001B53 3 229 0		*btn-dim16*)
(00001B56 9 187 0		'!sdb-bpt-toggle)
(00001B59 9 187 1		"VLMSG.DLL")
(00001B5C 51 174 51 0 0		13230)
(00001B61 81 2 186 1 1 0		string-resource)
(00001B67 9 187 1		"VLMSG.DLL")
(00001B6A 51 208 87 0 0		22480)
(00001B6F 81 2 186 1 1 0		string-resource)
(00001B75 53 6 219 0 1 32		bmp-push-button1)
(00001B7B 27 186 0		*setbpt-btn*)
(00001B7E 9 186 0		'*setbpt-btn*)
(00001B81 10)
(00001B82 3 222 0		*carp-res16*)
(00001B85 50 10		10)
(00001B87 50 0		0)
(00001B89 53 2 220 0 1 32		clip-bmp-pos16)
(00001B8F 50 16		16)
(00001B91 50 16		16)
(00001B93 81 2 135 1 1 0		make-ipoint)
(00001B99 81 3 210 0 1 0		bitmap-resource.clip)
(00001B9F 27 185 0		*isbefore*)
(00001BA2 9 185 0		'*isbefore*)
(00001BA5 10)
(00001BA6 3 222 0		*carp-res16*)
(00001BA9 50 10		10)
(00001BAB 50 1		1)
(00001BAD 53 2 220 0 1 32		clip-bmp-pos16)
(00001BB3 50 16		16)
(00001BB5 50 16		16)
(00001BB7 81 2 135 1 1 0		make-ipoint)
(00001BBD 81 3 210 0 1 0		bitmap-resource.clip)
(00001BC3 27 184 0		*isafter*)
(00001BC6 9 184 0		'*isafter*)
(00001BC9 10)
(00001BCA 3 222 0		*carp-res16*)
(00001BCD 50 10		10)
(00001BCF 50 4		4)
(00001BD1 53 2 220 0 1 32		clip-bmp-pos16)
(00001BD7 50 16		16)
(00001BD9 50 16		16)
(00001BDB 81 2 135 1 1 0		make-ipoint)
(00001BE1 81 3 210 0 1 0		bitmap-resource.clip)
(00001BE7 27 183 0		*isinside*)
(00001BEA 9 183 0		'*isinside*)
(00001BED 10)
(00001BEE 50 16		16)
(00001BF0 53 1 182 0 1 32		auto-scale-x)
(00001BF6 50 16		16)
(00001BF8 53 1 181 0 1 32		auto-scale-y)
(00001BFE 81 2 135 1 1 0		make-ipoint)
(00001C04 9 205 1		"")
(00001C07 1		nil)
(00001C08 3 209 0		*empty-sel*)
(00001C0B 57 1 0		list)
(00001C0E 9 187 1		"VLMSG.DLL")
(00001C11 51 218 87 0 0		22490)
(00001C16 81 2 186 1 1 0		string-resource)
(00001C1C 42		cons)
(00001C1D 3 185 0		*isbefore*)
(00001C20 57 1 0		list)
(00001C23 9 187 1		"VLMSG.DLL")
(00001C26 51 228 87 0 0		22500)
(00001C2B 81 2 186 1 1 0		string-resource)
(00001C31 42		cons)
(00001C32 3 183 0		*isinside*)
(00001C35 57 1 0		list)
(00001C38 9 187 1		"VLMSG.DLL")
(00001C3B 51 238 87 0 0		22510)
(00001C40 81 2 186 1 1 0		string-resource)
(00001C46 42		cons)
(00001C47 3 184 0		*isafter*)
(00001C4A 57 1 0		list)
(00001C4D 9 187 1		"VLMSG.DLL")
(00001C50 51 248 87 0 0		22520)
(00001C55 81 2 186 1 1 0		string-resource)
(00001C5B 42		cons)
(00001C5C 57 4 0		list)
(00001C5F 53 4 180 0 1 32		bitmap-push-button)
(00001C65 27 179 0		*bpt-status*)
(00001C68 9 179 0		'*bpt-status*)
(00001C6B 10)
(00001C6C 1		nil)
(00001C6D 10)
(00001C6E 9 170 2		'source-pos-status)
(00001C71 26 178 0		source-pos-status)
(00001C74 9 178 0		'source-pos-status)
(00001C77 10)
(00001C78 3 179 0		*bpt-status*)
(00001C7B 1		nil)
(00001C7C 81 2 177 0 1 0		bitmap-push-button.enabled<-)
(00001C82 10)
(00001C83 9 176 0		':UNKNOWN)
(00001C86 53 1 178 0 1 32		source-pos-status)
(00001C8C 10)
(00001C8D 1		nil)
(00001C8E 10)
(00001C8F 3 222 0		*carp-res16*)
(00001C92 50 8		8)
(00001C94 50 2		2)
(00001C96 53 2 220 0 1 32		clip-bmp-pos16)
(00001C9C 3 229 0		*btn-dim16*)
(00001C9F 9 220 2		'!mark-ring-toggle)
(00001CA2 9 187 1		"VLMSG.DLL")
(00001CA5 51 12 88 0 0		22540)
(00001CAA 81 2 186 1 1 0		string-resource)
(00001CB0 9 187 1		"VLMSG.DLL")
(00001CB3 51 22 88 0 0		22550)
(00001CB8 81 2 186 1 1 0		string-resource)
(00001CBE 53 6 219 0 1 32		bmp-push-button1)
(00001CC4 27 175 0		*pum-btn*)
(00001CC7 9 175 0		'*pum-btn*)
(00001CCA 10)
(00001CCB 3 222 0		*carp-res16*)
(00001CCE 50 8		8)
(00001CD0 50 3		3)
(00001CD2 53 2 220 0 1 32		clip-bmp-pos16)
(00001CD8 3 229 0		*btn-dim16*)
(00001CDB 9 225 2		'!mark-ring-prev)
(00001CDE 9 187 1		"VLMSG.DLL")
(00001CE1 51 128 42 0 0		10880)
(00001CE6 81 2 186 1 1 0		string-resource)
(00001CEC 9 187 1		"VLMSG.DLL")
(00001CEF 51 32 88 0 0		22560)
(00001CF4 81 2 186 1 1 0		string-resource)
(00001CFA 53 6 219 0 1 32		bmp-push-button1)
(00001D00 27 174 0		*pom-btn*)
(00001D03 9 174 0		'*pom-btn*)
(00001D06 10)
(00001D07 3 222 0		*carp-res16*)
(00001D0A 50 8		8)
(00001D0C 50 4		4)
(00001D0E 53 2 220 0 1 32		clip-bmp-pos16)
(00001D14 3 229 0		*btn-dim16*)
(00001D17 9 224 2		'!mark-ring-next)
(00001D1A 9 187 1		"VLMSG.DLL")
(00001D1D 51 108 42 0 0		10860)
(00001D22 81 2 186 1 1 0		string-resource)
(00001D28 9 187 1		"VLMSG.DLL")
(00001D2B 51 42 88 0 0		22570)
(00001D30 81 2 186 1 1 0		string-resource)
(00001D36 53 6 219 0 1 32		bmp-push-button1)
(00001D3C 27 173 0		*swmp-btn*)
(00001D3F 9 173 0		'*swmp-btn*)
(00001D42 10)
(00001D43 3 222 0		*carp-res16*)
(00001D46 50 9		9)
(00001D48 50 0		0)
(00001D4A 53 2 220 0 1 32		clip-bmp-pos16)
(00001D50 3 229 0		*btn-dim16*)
(00001D53 9 223 2		'!mark-ring-clear)
(00001D56 9 187 1		"VLMSG.DLL")
(00001D59 51 148 42 0 0		10900)
(00001D5E 81 2 186 1 1 0		string-resource)
(00001D64 9 187 1		"VLMSG.DLL")
(00001D67 51 148 42 0 0		10900)
(00001D6C 81 2 186 1 1 0		string-resource)
(00001D72 53 6 219 0 1 32		bmp-push-button1)
(00001D78 27 172 0		*btn-cle-book*)
(00001D7B 9 172 0		'*btn-cle-book*)
(00001D7E 10)
(00001D7F 3 222 0		*carp-res16*)
(00001D82 50 9		9)
(00001D84 50 2		2)
(00001D86 53 2 220 0 1 32		clip-bmp-pos16)
(00001D8C 3 229 0		*btn-dim16*)
(00001D8F 9 171 0		'!twin-print)
(00001D92 9 187 1		"VLMSG.DLL")
(00001D95 51 24 41 0 0		10520)
(00001D9A 81 2 186 1 1 0		string-resource)
(00001DA0 9 187 1		"VLMSG.DLL")
(00001DA3 51 52 88 0 0		22580)
(00001DA8 81 2 186 1 1 0		string-resource)
(00001DAE 53 6 219 0 1 32		bmp-push-button1)
(00001DB4 27 170 0		*btn-print*)
(00001DB7 9 170 0		'*btn-print*)
(00001DBA 10)
(00001DBB 3 222 0		*carp-res16*)
(00001DBE 50 8		8)
(00001DC0 50 0		0)
(00001DC2 53 2 220 0 1 32		clip-bmp-pos16)
(00001DC8 3 229 0		*btn-dim16*)
(00001DCB 15 0 0		JMP 00001DCE)
(00001DCE 9 169 2		'nil)
(00001DD1 9 187 1		"VLMSG.DLL")
(00001DD4 51 62 88 0 0		22590)
(00001DD9 81 2 186 1 1 0		string-resource)
(00001DDF 9 187 1		"VLMSG.DLL")
(00001DE2 51 72 88 0 0		22600)
(00001DE7 81 2 186 1 1 0		string-resource)
(00001DED 53 6 219 0 1 32		bmp-push-button1)
(00001DF3 27 169 0		*btn-undo*)
(00001DF6 9 169 0		'*btn-undo*)
(00001DF9 10)
(00001DFA 3 222 0		*carp-res16*)
(00001DFD 50 8		8)
(00001DFF 50 1		1)
(00001E01 53 2 220 0 1 32		clip-bmp-pos16)
(00001E07 3 229 0		*btn-dim16*)
(00001E0A 15 0 0		JMP 00001E0D)
(00001E0D 9 168 2		'nil)
(00001E10 9 187 1		"VLMSG.DLL")
(00001E13 51 36 44 0 0		11300)
(00001E18 81 2 186 1 1 0		string-resource)
(00001E1E 9 187 1		"VLMSG.DLL")
(00001E21 51 82 88 0 0		22610)
(00001E26 81 2 186 1 1 0		string-resource)
(00001E2C 53 6 219 0 1 32		bmp-push-button1)
(00001E32 27 168 0		*btn-redo*)
(00001E35 9 168 0		'*btn-redo*)
(00001E38 10)
(00001E39 3 222 0		*carp-res16*)
(00001E3C 50 0		0)
(00001E3E 50 0		0)
(00001E40 53 2 220 0 1 32		clip-bmp-pos16)
(00001E46 3 229 0		*btn-dim16*)
(00001E49 9 1 3		'find!)
(00001E4C 9 187 1		"VLMSG.DLL")
(00001E4F 51 244 41 0 0		10740)
(00001E54 81 2 186 1 1 0		string-resource)
(00001E5A 9 187 1		"VLMSG.DLL")
(00001E5D 51 92 88 0 0		22620)
(00001E62 81 2 186 1 1 0		string-resource)
(00001E68 53 6 219 0 1 32		bmp-push-button1)
(00001E6E 27 167 0		*glasses-btn*)
(00001E71 9 167 0		'*glasses-btn*)
(00001E74 10)
(00001E75 3 222 0		*carp-res16*)
(00001E78 50 3		3)
(00001E7A 50 4		4)
(00001E7C 53 2 220 0 1 32		clip-bmp-pos16)
(00001E82 3 229 0		*btn-dim16*)
(00001E85 9 245 2		'replace!)
(00001E88 9 187 1		"VLMSG.DLL")
(00001E8B 51 8 42 0 0		10760)
(00001E90 81 2 186 1 1 0		string-resource)
(00001E96 9 187 1		"VLMSG.DLL")
(00001E99 51 102 88 0 0		22630)
(00001E9E 81 2 186 1 1 0		string-resource)
(00001EA4 53 6 219 0 1 32		bmp-push-button1)
(00001EAA 27 166 0		*btn-replace*)
(00001EAD 9 166 0		'*btn-replace*)
(00001EB0 10)
(00001EB1 3 222 0		*carp-res16*)
(00001EB4 50 5		5)
(00001EB6 50 3		3)
(00001EB8 53 2 220 0 1 32		clip-bmp-pos16)
(00001EBE 3 229 0		*btn-dim16*)
(00001EC1 9 240 2		'!find-via-ribbon)
(00001EC4 9 187 1		"VLMSG.DLL")
(00001EC7 51 112 88 0 0		22640)
(00001ECC 81 2 186 1 1 0		string-resource)
(00001ED2 9 187 1		"VLMSG.DLL")
(00001ED5 51 122 88 0 0		22650)
(00001EDA 81 2 186 1 1 0		string-resource)
(00001EE0 53 6 219 0 1 32		bmp-push-button1)
(00001EE6 27 165 0		*glassnext-btn*)
(00001EE9 9 165 0		'*glassnext-btn*)
(00001EEC 10)
(00001EED 3 222 0		*carp-res16*)
(00001EF0 50 5		5)
(00001EF2 50 3		3)
(00001EF4 53 2 220 0 1 32		clip-bmp-pos16)
(00001EFA 3 229 0		*btn-dim16*)
(00001EFD 9 2 3		'next-find/replace!)
(00001F00 9 187 1		"VLMSG.DLL")
(00001F03 51 132 88 0 0		22660)
(00001F08 81 2 186 1 1 0		string-resource)
(00001F0E 9 187 1		"VLMSG.DLL")
(00001F11 51 132 88 0 0		22660)
(00001F16 81 2 186 1 1 0		string-resource)
(00001F1C 53 6 219 0 1 32		bmp-push-button1)
(00001F22 27 164 0		*glassnext1-btn*)
(00001F25 9 164 0		'*glassnext1-btn*)
(00001F28 10)
(00001F29 3 222 0		*carp-res16*)
(00001F2C 50 0		0)
(00001F2E 50 1		1)
(00001F30 53 2 220 0 1 32		clip-bmp-pos16)
(00001F36 3 229 0		*btn-dim16*)
(00001F39 15 0 0		JMP 00001F3C)
(00001F3C 9 167 2		'nil)
(00001F3F 9 187 1		"VLMSG.DLL")
(00001F42 51 88 47 0 0		12120)
(00001F47 81 2 186 1 1 0		string-resource)
(00001F4D 9 187 1		"VLMSG.DLL")
(00001F50 51 142 88 0 0		22670)
(00001F55 81 2 186 1 1 0		string-resource)
(00001F5B 53 6 219 0 1 32		bmp-push-button1)
(00001F61 27 163 0		*apropos-btn*)
(00001F64 9 163 0		'*apropos-btn*)
(00001F67 10)
(00001F68 3 222 0		*carp-res16*)
(00001F6B 50 3		3)
(00001F6D 50 3		3)
(00001F6F 53 2 220 0 1 32		clip-bmp-pos16)
(00001F75 3 229 0		*btn-dim16*)
(00001F78 15 0 0		JMP 00001F7B)
(00001F7B 9 166 2		'nil)
(00001F7E 9 187 1		"VLMSG.DLL")
(00001F81 51 28 47 0 0		12060)
(00001F86 81 2 186 1 1 0		string-resource)
(00001F8C 9 187 1		"VLMSG.DLL")
(00001F8F 51 252 73 0 0		18940)
(00001F94 81 2 186 1 1 0		string-resource)
(00001F9A 53 6 219 0 1 32		bmp-push-button1)
(00001FA0 27 162 0		*btn-backtrace*)
(00001FA3 9 162 0		'*btn-backtrace*)
(00001FA6 10)
(00001FA7 3 222 0		*carp-res16*)
(00001FAA 50 3		3)
(00001FAC 50 2		2)
(00001FAE 53 2 220 0 1 32		clip-bmp-pos16)
(00001FB4 3 229 0		*btn-dim16*)
(00001FB7 9 187 2		'window-list!)
(00001FBA 9 187 1		"VLMSG.DLL")
(00001FBD 51 152 88 0 0		22680)
(00001FC2 81 2 186 1 1 0		string-resource)
(00001FC8 9 187 1		"VLMSG.DLL")
(00001FCB 51 162 88 0 0		22690)
(00001FD0 81 2 186 1 1 0		string-resource)
(00001FD6 53 6 219 0 1 32		bmp-push-button1)
(00001FDC 27 161 0		*btn-windows*)
(00001FDF 9 161 0		'*btn-windows*)
(00001FE2 10)
(00001FE3 3 222 0		*carp-res16*)
(00001FE6 50 5		5)
(00001FE8 50 2		2)
(00001FEA 53 2 220 0 1 32		clip-bmp-pos16)
(00001FF0 3 229 0		*btn-dim16*)
(00001FF3 9 165 2		'!editor-comment-block)
(00001FF6 9 187 1		"VLMSG.DLL")
(00001FF9 51 100 45 0 0		11620)
(00001FFE 81 2 186 1 1 0		string-resource)
(00002004 9 187 1		"VLMSG.DLL")
(00002007 51 172 88 0 0		22700)
(0000200C 81 2 186 1 1 0		string-resource)
(00002012 53 6 219 0 1 32		bmp-push-button1)
(00002018 27 160 0		*btn-comment-block*)
(0000201B 9 160 0		'*btn-comment-block*)
(0000201E 10)
(0000201F 3 222 0		*carp-res16*)
(00002022 50 5		5)
(00002024 50 4		4)
(00002026 53 2 220 0 1 32		clip-bmp-pos16)
(0000202C 3 229 0		*btn-dim16*)
(0000202F 9 164 2		'!editor-uncomment-block)
(00002032 9 187 1		"VLMSG.DLL")
(00002035 51 120 45 0 0		11640)
(0000203A 81 2 186 1 1 0		string-resource)
(00002040 9 187 1		"VLMSG.DLL")
(00002043 51 182 88 0 0		22710)
(00002048 81 2 186 1 1 0		string-resource)
(0000204E 53 6 219 0 1 32		bmp-push-button1)
(00002054 27 159 0		*btn-uncomment-block*)
(00002057 9 159 0		'*btn-uncomment-block*)
(0000205A 10)
(0000205B 3 222 0		*carp-res16*)
(0000205E 50 4		4)
(00002060 50 1		1)
(00002062 53 2 220 0 1 32		clip-bmp-pos16)
(00002068 3 229 0		*btn-dim16*)
(0000206B 15 0 0		JMP 0000206E)
(0000206E 9 163 2		'nil)
(00002071 9 187 1		"VLMSG.DLL")
(00002074 51 192 88 0 0		22720)
(00002079 81 2 186 1 1 0		string-resource)
(0000207F 9 187 1		"VLMSG.DLL")
(00002082 51 202 88 0 0		22730)
(00002087 81 2 186 1 1 0		string-resource)
(0000208D 53 6 219 0 1 32		bmp-push-button1)
(00002093 27 158 0		*btn-help*)
(00002096 9 158 0		'*btn-help*)
(00002099 10)
(0000209A 3 222 0		*carp-res16*)
(0000209D 50 2		2)
(0000209F 50 1		1)
(000020A1 53 2 220 0 1 32		clip-bmp-pos16)
(000020A7 3 229 0		*btn-dim16*)
(000020AA 9 37 3		'open-editor!)
(000020AD 9 187 1		"VLMSG.DLL")
(000020B0 51 100 40 0 0		10340)
(000020B5 81 2 186 1 1 0		string-resource)
(000020BB 9 187 1		"VLMSG.DLL")
(000020BE 51 212 88 0 0		22740)
(000020C3 81 2 186 1 1 0		string-resource)
(000020C9 53 6 219 0 1 32		bmp-push-button1)
(000020CF 27 157 0		*btn-open*)
(000020D2 9 157 0		'*btn-open*)
(000020D5 10)
(000020D6 3 222 0		*carp-res16*)
(000020D9 50 2		2)
(000020DB 50 3		3)
(000020DD 53 2 220 0 1 32		clip-bmp-pos16)
(000020E3 3 229 0		*btn-dim16*)
(000020E6 15 0 0		JMP 000020E9)
(000020E9 9 162 2		'nil)
(000020EC 9 187 1		"VLMSG.DLL")
(000020EF 51 160 40 0 0		10400)
(000020F4 81 2 186 1 1 0		string-resource)
(000020FA 9 187 1		"VLMSG.DLL")
(000020FD 51 222 88 0 0		22750)
(00002102 81 2 186 1 1 0		string-resource)
(00002108 53 6 219 0 1 32		bmp-push-button1)
(0000210E 27 156 0		*btn-save*)
(00002111 9 156 0		'*btn-save*)
(00002114 10)
(00002115 3 222 0		*carp-res16*)
(00002118 50 2		2)
(0000211A 50 2		2)
(0000211C 53 2 220 0 1 32		clip-bmp-pos16)
(00002122 3 229 0		*btn-dim16*)
(00002125 9 38 3		'new-editor!)
(00002128 9 187 1		"VLMSG.DLL")
(0000212B 51 80 40 0 0		10320)
(00002130 81 2 186 1 1 0		string-resource)
(00002136 9 187 1		"VLMSG.DLL")
(00002139 51 232 88 0 0		22760)
(0000213E 81 2 186 1 1 0		string-resource)
(00002144 53 6 219 0 1 32		bmp-push-button1)
(0000214A 27 155 0		*btn-new*)
(0000214D 9 155 0		'*btn-new*)
(00002150 10)
(00002151 3 222 0		*carp-res16*)
(00002154 50 2		2)
(00002156 50 4		4)
(00002158 53 2 220 0 1 32		clip-bmp-pos16)
(0000215E 3 229 0		*btn-dim16*)
(00002161 15 0 0		JMP 00002164)
(00002164 9 161 2		'nil)
(00002167 9 187 1		"VLMSG.DLL")
(0000216A 51 56 44 0 0		11320)
(0000216F 81 2 186 1 1 0		string-resource)
(00002175 9 187 1		"VLMSG.DLL")
(00002178 51 242 88 0 0		22770)
(0000217D 81 2 186 1 1 0		string-resource)
(00002183 53 6 219 0 1 32		bmp-push-button1)
(00002189 27 154 0		*btn-cut*)
(0000218C 9 154 0		'*btn-cut*)
(0000218F 10)
(00002190 3 222 0		*carp-res16*)
(00002193 50 3		3)
(00002195 50 0		0)
(00002197 53 2 220 0 1 32		clip-bmp-pos16)
(0000219D 3 229 0		*btn-dim16*)
(000021A0 15 0 0		JMP 000021A3)
(000021A3 9 160 2		'nil)
(000021A6 9 187 1		"VLMSG.DLL")
(000021A9 51 76 44 0 0		11340)
(000021AE 81 2 186 1 1 0		string-resource)
(000021B4 9 187 1		"VLMSG.DLL")
(000021B7 51 252 88 0 0		22780)
(000021BC 81 2 186 1 1 0		string-resource)
(000021C2 53 6 219 0 1 32		bmp-push-button1)
(000021C8 27 153 0		*btn-copy*)
(000021CB 9 153 0		'*btn-copy*)
(000021CE 10)
(000021CF 3 222 0		*carp-res16*)
(000021D2 50 3		3)
(000021D4 50 1		1)
(000021D6 53 2 220 0 1 32		clip-bmp-pos16)
(000021DC 3 229 0		*btn-dim16*)
(000021DF 15 0 0		JMP 000021E2)
(000021E2 9 159 2		'nil)
(000021E5 9 187 1		"VLMSG.DLL")
(000021E8 51 96 44 0 0		11360)
(000021ED 81 2 186 1 1 0		string-resource)
(000021F3 9 187 1		"VLMSG.DLL")
(000021F6 51 6 89 0 0		22790)
(000021FB 81 2 186 1 1 0		string-resource)
(00002201 53 6 219 0 1 32		bmp-push-button1)
(00002207 27 152 0		*btn-paste*)
(0000220A 9 152 0		'*btn-paste*)
(0000220D 10)
(0000220E 3 222 0		*carp-res16*)
(00002211 50 6		6)
(00002213 50 3		3)
(00002215 53 2 220 0 1 32		clip-bmp-pos16)
(0000221B 3 229 0		*btn-dim16*)
(0000221E 15 0 0		JMP 00002221)
(00002221 9 158 2		'nil)
(00002224 9 187 1		"VLMSG.DLL")
(00002227 51 132 43 0 0		11140)
(0000222C 81 2 186 1 1 0		string-resource)
(00002232 9 187 1		"VLMSG.DLL")
(00002235 51 132 43 0 0		11140)
(0000223A 81 2 186 1 1 0		string-resource)
(00002240 53 6 219 0 1 32		bmp-push-button1)
(00002246 27 151 0		*ribb-acad!-pb*)
(00002249 9 151 0		'*ribb-acad!-pb*)
(0000224C 10)
(0000224D 3 222 0		*carp-res16*)
(00002250 50 2		2)
(00002252 50 0		0)
(00002254 53 2 220 0 1 32		clip-bmp-pos16)
(0000225A 3 229 0		*btn-dim16*)
(0000225D 9 150 0		'apropos-fast!)
(00002260 9 187 1		"VLMSG.DLL")
(00002263 51 16 89 0 0		22800)
(00002268 81 2 186 1 1 0		string-resource)
(0000226E 9 187 1		"VLMSG.DLL")
(00002271 51 26 89 0 0		22810)
(00002276 81 2 186 1 1 0		string-resource)
(0000227C 53 6 219 0 1 32		bmp-push-button1)
(00002282 27 149 0		*btn-complete*)
(00002285 9 149 0		'*btn-complete*)
(00002288 10)
(00002289 9 157 2		'sep-bmp-pb)
(0000228C 26 148 0		sep-bmp-pb)
(0000228F 9 148 0		'sep-bmp-pb)
(00002292 10)
(00002293 50 16		16)
(00002295 51 7 0 24 0		1572871)
(0000229A 53 2 148 0 1 32		sep-bmp-pb)
(000022A0 26 147 0		*btn-d-sep-v-tools*)
(000022A3 9 147 0		'*btn-d-sep-v-tools*)
(000022A6 10)
(000022A7 50 23		23)
(000022A9 51 2 0 24 0		1572866)
(000022AE 53 2 148 0 1 32		sep-bmp-pb)
(000022B4 26 146 0		*btn-s-sep-v-tools0*)
(000022B7 9 146 0		'*btn-s-sep-v-tools0*)
(000022BA 10)
(000022BB 50 23		23)
(000022BD 51 2 0 24 0		1572866)
(000022C2 53 2 148 0 1 32		sep-bmp-pb)
(000022C8 26 145 0		*btn-s-sep-v-tools1*)
(000022CB 9 145 0		'*btn-s-sep-v-tools1*)
(000022CE 10)
(000022CF 50 25		25)
(000022D1 51 24 0 7 0		458776)
(000022D6 53 2 148 0 1 32		sep-bmp-pb)
(000022DC 26 144 0		*btn-d-sep-h-tools*)
(000022DF 9 144 0		'*btn-d-sep-h-tools*)
(000022E2 10)
(000022E3 51 25 0 7 0		458777)
(000022E8 51 24 0 2 0		131096)
(000022ED 53 2 148 0 1 32		sep-bmp-pb)
(000022F3 26 143 0		*btn-s-sep-h-tools0*)
(000022F6 9 143 0		'*btn-s-sep-h-tools0*)
(000022F9 10)
(000022FA 51 25 0 7 0		458777)
(000022FF 51 24 0 2 0		131096)
(00002304 53 2 148 0 1 32		sep-bmp-pb)
(0000230A 26 142 0		*btn-s-sep-h-tools1*)
(0000230D 9 142 0		'*btn-s-sep-h-tools1*)
(00002310 10)
(00002311 50 16		16)
(00002313 51 7 0 24 0		1572871)
(00002318 53 2 148 0 1 32		sep-bmp-pb)
(0000231E 26 141 0		*btn-d-sep-v-std*)
(00002321 9 141 0		'*btn-d-sep-v-std*)
(00002324 10)
(00002325 50 23		23)
(00002327 51 2 0 24 0		1572866)
(0000232C 53 2 148 0 1 32		sep-bmp-pb)
(00002332 26 140 0		*btn-s-sep-v-std0*)
(00002335 9 140 0		'*btn-s-sep-v-std0*)
(00002338 10)
(00002339 50 23		23)
(0000233B 51 2 0 24 0		1572866)
(00002340 53 2 148 0 1 32		sep-bmp-pb)
(00002346 26 139 0		*btn-s-sep-v-std1*)
(00002349 9 139 0		'*btn-s-sep-v-std1*)
(0000234C 10)
(0000234D 50 23		23)
(0000234F 51 2 0 24 0		1572866)
(00002354 53 2 148 0 1 32		sep-bmp-pb)
(0000235A 26 138 0		*btn-s-sep-v-std2*)
(0000235D 9 138 0		'*btn-s-sep-v-std2*)
(00002360 10)
(00002361 50 25		25)
(00002363 51 24 0 7 0		458776)
(00002368 53 2 148 0 1 32		sep-bmp-pb)
(0000236E 26 137 0		*btn-d-sep-h-std*)
(00002371 9 137 0		'*btn-d-sep-h-std*)
(00002374 10)
(00002375 51 25 0 7 0		458777)
(0000237A 51 24 0 2 0		131096)
(0000237F 53 2 148 0 1 32		sep-bmp-pb)
(00002385 26 136 0		*btn-s-sep-h-std0*)
(00002388 9 136 0		'*btn-s-sep-h-std0*)
(0000238B 10)
(0000238C 51 25 0 7 0		458777)
(00002391 51 24 0 2 0		131096)
(00002396 53 2 148 0 1 32		sep-bmp-pb)
(0000239C 26 135 0		*btn-s-sep-h-std1*)
(0000239F 9 135 0		'*btn-s-sep-h-std1*)
(000023A2 10)
(000023A3 51 25 0 7 0		458777)
(000023A8 51 24 0 2 0		131096)
(000023AD 53 2 148 0 1 32		sep-bmp-pb)
(000023B3 26 134 0		*btn-s-sep-h-std2*)
(000023B6 9 134 0		'*btn-s-sep-h-std2*)
(000023B9 10)
(000023BA 50 16		16)
(000023BC 51 7 0 24 0		1572871)
(000023C1 53 2 148 0 1 32		sep-bmp-pb)
(000023C7 26 133 0		*btn-d-sep-v-sch*)
(000023CA 9 133 0		'*btn-d-sep-v-sch*)
(000023CD 10)
(000023CE 50 23		23)
(000023D0 51 2 0 24 0		1572866)
(000023D5 53 2 148 0 1 32		sep-bmp-pb)
(000023DB 26 132 0		*btn-s-sep-v-sch0*)
(000023DE 9 132 0		'*btn-s-sep-v-sch0*)
(000023E1 10)
(000023E2 50 25		25)
(000023E4 51 24 0 7 0		458776)
(000023E9 53 2 148 0 1 32		sep-bmp-pb)
(000023EF 26 131 0		*btn-d-sep-h-sch*)
(000023F2 9 131 0		'*btn-d-sep-h-sch*)
(000023F5 10)
(000023F6 51 25 0 7 0		458777)
(000023FB 51 24 0 2 0		131096)
(00002400 53 2 148 0 1 32		sep-bmp-pb)
(00002406 26 130 0		*btn-s-sep-h-sch0*)
(00002409 9 130 0		'*btn-s-sep-h-sch0*)
(0000240C 10)
(0000240D 50 16		16)
(0000240F 51 7 0 24 0		1572871)
(00002414 53 2 148 0 1 32		sep-bmp-pb)
(0000241A 26 129 0		*btn-d-sep-v-dbg*)
(0000241D 9 129 0		'*btn-d-sep-v-dbg*)
(00002420 10)
(00002421 50 23		23)
(00002423 51 2 0 24 0		1572866)
(00002428 53 2 148 0 1 32		sep-bmp-pb)
(0000242E 26 128 0		*btn-s-sep-v-dbg0*)
(00002431 9 128 0		'*btn-s-sep-v-dbg0*)
(00002434 10)
(00002435 50 23		23)
(00002437 51 2 0 24 0		1572866)
(0000243C 53 2 148 0 1 32		sep-bmp-pb)
(00002442 26 127 0		*btn-s-sep-v-dbg1*)
(00002445 9 127 0		'*btn-s-sep-v-dbg1*)
(00002448 10)
(00002449 50 23		23)
(0000244B 51 2 0 24 0		1572866)
(00002450 53 2 148 0 1 32		sep-bmp-pb)
(00002456 26 126 0		*btn-s-sep-v-dbg2*)
(00002459 9 126 0		'*btn-s-sep-v-dbg2*)
(0000245C 10)
(0000245D 50 25		25)
(0000245F 51 24 0 7 0		458776)
(00002464 53 2 148 0 1 32		sep-bmp-pb)
(0000246A 26 125 0		*btn-d-sep-h-dbg*)
(0000246D 9 125 0		'*btn-d-sep-h-dbg*)
(00002470 10)
(00002471 51 25 0 7 0		458777)
(00002476 51 24 0 2 0		131096)
(0000247B 53 2 148 0 1 32		sep-bmp-pb)
(00002481 26 124 0		*btn-s-sep-h-dbg0*)
(00002484 9 124 0		'*btn-s-sep-h-dbg0*)
(00002487 10)
(00002488 51 25 0 7 0		458777)
(0000248D 51 24 0 2 0		131096)
(00002492 53 2 148 0 1 32		sep-bmp-pb)
(00002498 26 123 0		*btn-s-sep-h-dbg1*)
(0000249B 9 123 0		'*btn-s-sep-h-dbg1*)
(0000249E 10)
(0000249F 51 25 0 7 0		458777)
(000024A4 51 24 0 2 0		131096)
(000024A9 53 2 148 0 1 32		sep-bmp-pb)
(000024AF 26 122 0		*btn-s-sep-h-dbg2*)
(000024B2 9 122 0		'*btn-s-sep-h-dbg2*)
(000024B5 10)
(000024B6 50 16		16)
(000024B8 51 7 0 24 0		1572871)
(000024BD 53 2 148 0 1 32		sep-bmp-pb)
(000024C3 26 121 0		*btn-d-sep-v-view*)
(000024C6 9 121 0		'*btn-d-sep-v-view*)
(000024C9 10)
(000024CA 50 23		23)
(000024CC 51 2 0 24 0		1572866)
(000024D1 53 2 148 0 1 32		sep-bmp-pb)
(000024D7 26 120 0		*btn-s-sep-v-view0*)
(000024DA 9 120 0		'*btn-s-sep-v-view0*)
(000024DD 10)
(000024DE 50 25		25)
(000024E0 51 24 0 7 0		458776)
(000024E5 53 2 148 0 1 32		sep-bmp-pb)
(000024EB 26 119 0		*btn-d-sep-h-view*)
(000024EE 9 119 0		'*btn-d-sep-h-view*)
(000024F1 10)
(000024F2 51 25 0 7 0		458777)
(000024F7 51 24 0 2 0		131096)
(000024FC 53 2 148 0 1 32		sep-bmp-pb)
(00002502 26 118 0		*btn-s-sep-h-view0*)
(00002505 9 118 0		'*btn-s-sep-h-view0*)
(00002508 28		[ret])
(00002509 20 0 0 0 0)
(0000250E 1		nil)
(0000250F 10)
(00002510 1		nil)
(00002511 10)
(00002512 1		nil)
(00002513 10)
(00002514 9 156 2		'!editor-insert-file)
(00002517 26 117 0		!editor-insert-file)
(0000251A 9 117 0		'!editor-insert-file)
(0000251D 10)
(0000251E 1		nil)
(0000251F 10)
(00002520 9 155 2		'!editor-write-block)
(00002523 26 116 0		!editor-write-block)
(00002526 9 116 0		'!editor-write-block)
(00002529 10)
(0000252A 1		nil)
(0000252B 10)
(0000252C 9 115 0		";;; ")
(0000252F 27 114 0		*last-indent-block-string*)
(00002532 9 114 0		'*last-indent-block-string*)
(00002535 10)
(00002536 9 154 2		'!editor-indent-block)
(00002539 26 113 0		!editor-indent-block)
(0000253C 9 113 0		'!editor-indent-block)
(0000253F 10)
(00002540 9 153 2		'!editor-unindent-block)
(00002543 26 112 0		!editor-unindent-block)
(00002546 9 112 0		'!editor-unindent-block)
(00002549 10)
(0000254A 9 152 2		'append-str-to-eols)
(0000254D 26 111 0		append-str-to-eols)
(00002550 9 111 0		'append-str-to-eols)
(00002553 10)
(00002554 9 110 0		" ;")
(00002557 27 109 0		*last-append-string-to-lines*)
(0000255A 9 109 0		'*last-append-string-to-lines*)
(0000255D 10)
(0000255E 9 151 2		'!editor-append-string-to-lines)
(00002561 26 108 0		!editor-append-string-to-lines)
(00002564 9 108 0		'!editor-append-string-to-lines)
(00002567 10)
(00002568 9 150 2		'tbuf-lines-list)
(0000256B 26 107 0		tbuf-lines-list)
(0000256E 9 107 0		'tbuf-lines-list)
(00002571 10)
(00002572 9 149 2		'!editor-sort-lines)
(00002575 26 106 0		!editor-sort-lines)
(00002578 9 106 0		'!editor-sort-lines)
(0000257B 10)
(0000257C 9 105 0		"\t")
(0000257F 27 104 0		*ed-indent-str*)
(00002582 9 104 0		'*ed-indent-str*)
(00002585 10)
(00002586 9 103 0		'((:AL . ";;;") (:LPP . ";;;") (:CPP . "//") (:DCL . "//") (:SQL . "//")))
(00002589 26 102 0		*xsi-comment-alist*)
(0000258C 9 102 0		'*xsi-comment-alist*)
(0000258F 10)
(00002590 9 148 2		'!?ed-comm-blk)
(00002593 26 101 0		!?ed-comm-blk)
(00002596 9 101 0		'!?ed-comm-blk)
(00002599 10)
(0000259A 9 165 2		'!editor-comment-block)
(0000259D 26 100 0		!editor-comment-block)
(000025A0 9 100 0		'!editor-comment-block)
(000025A3 10)
(000025A4 9 164 2		'!editor-uncomment-block)
(000025A7 26 99 0		!editor-uncomment-block)
(000025AA 9 99 0		'!editor-uncomment-block)
(000025AD 10)
(000025AE 9 147 2		'transform-selected-text)
(000025B1 26 98 0		transform-selected-text)
(000025B4 9 98 0		'transform-selected-text)
(000025B7 10)
(000025B8 1		nil)
(000025B9 10)
(000025BA 1		nil)
(000025BB 10)
(000025BC 9 146 2		'!ed-upcase)
(000025BF 26 97 0		!ed-upcase)
(000025C2 9 97 0		'!ed-upcase)
(000025C5 10)
(000025C6 9 145 2		'!ed-downcase)
(000025C9 26 96 0		!ed-downcase)
(000025CC 9 96 0		'!ed-downcase)
(000025CF 10)
(000025D0 9 144 2		'!ed-capitalize)
(000025D3 26 95 0		!ed-capitalize)
(000025D6 9 95 0		'!ed-capitalize)
(000025D9 10)
(000025DA 9 94 0		'("~@@d/~@@m/~@@y" "~V@d/~V@m/~@@y" "~@@m/~@@d/~@@y" "~V@m/~V@d/~@@y" "~V@d ~VVm, ~@@y" "~V@d-~@@@m-~@@y" "~@@d.~@@m.~@@y" "~V@d.~V@m.~@@y" "~V@d. ~VVm ~@@y"))
(000025DD 26 93 0		*vlisp-date-formats*)
(000025E0 9 93 0		'*vlisp-date-formats*)
(000025E3 10)
(000025E4 9 92 0		'("~@@h:~@@i:~@@s" "~@@h:~@@i" "~vh:~@@i:~@@s ~:h" "~vh:~@@i ~:h" "~@@h.~@@i.~@@s" "~@@h.~@@i"))
(000025E7 26 91 0		*vlisp-time-formats*)
(000025EA 9 91 0		'*vlisp-time-formats*)
(000025ED 10)
(000025EE 9 90 0		'*vlisp-date-format*)
(000025F1 9 67 2		':L-CONTEXT)
(000025F4 9 66 2		':AUTOLISP)
(000025F7 53 3 76 2 1 32		add-desktop-option)
(000025FD 10)
(000025FE 9 89 0		'*vlisp-time-format*)
(00002601 9 67 2		':L-CONTEXT)
(00002604 9 66 2		':AUTOLISP)
(00002607 53 3 76 2 1 32		add-desktop-option)
(0000260D 10)
(0000260E 12 143 2		'!choose-date-format)
(00002611 26 88 0		!choose-date-format)
(00002614 9 88 0		'!choose-date-format)
(00002617 10)
(00002618 1		nil)
(00002619 27 87 0		*editor-ctrl-x-menu-items*)
(0000261C 9 87 0		'*editor-ctrl-x-menu-items*)
(0000261F 10)
(00002620 9 142 2		'editor-ctrl-x!)
(00002623 26 86 0		editor-ctrl-x!)
(00002626 9 86 0		'editor-ctrl-x!)
(00002629 10)
(0000262A 9 141 2		'editor-add-ctrl-x-item)
(0000262D 26 85 0		editor-add-ctrl-x-item)
(00002630 9 85 0		'editor-add-ctrl-x-item)
(00002633 28		[ret])
(00002634 20 0 0 0 0)
(00002639 1		nil)
(0000263A 10)
(0000263B 1		nil)
(0000263C 10)
(0000263D 9 84 0		'*print-left-margin*)
(00002640 9 67 2		':L-CONTEXT)
(00002643 9 66 2		':AUTOLISP)
(00002646 53 3 76 2 1 32		add-desktop-option)
(0000264C 10)
(0000264D 9 83 0		'*print-right-margin*)
(00002650 9 67 2		':L-CONTEXT)
(00002653 9 66 2		':AUTOLISP)
(00002656 53 3 76 2 1 32		add-desktop-option)
(0000265C 10)
(0000265D 9 82 0		'*print-top-margin*)
(00002660 9 67 2		':L-CONTEXT)
(00002663 9 66 2		':AUTOLISP)
(00002666 53 3 76 2 1 32		add-desktop-option)
(0000266C 10)
(0000266D 9 81 0		'*print-bottom-margin*)
(00002670 9 67 2		':L-CONTEXT)
(00002673 9 66 2		':AUTOLISP)
(00002676 53 3 76 2 1 32		add-desktop-option)
(0000267C 10)
(0000267D 9 80 0		'*printer-header*)
(00002680 9 67 2		':L-CONTEXT)
(00002683 9 66 2		':AUTOLISP)
(00002686 53 3 76 2 1 32		add-desktop-option)
(0000268C 10)
(0000268D 9 79 0		'*printer-footer*)
(00002690 9 67 2		':L-CONTEXT)
(00002693 9 66 2		':AUTOLISP)
(00002696 53 3 76 2 1 32		add-desktop-option)
(0000269C 10)
(0000269D 9 78 0		'*print-inch-or-mm*)
(000026A0 9 67 2		':L-CONTEXT)
(000026A3 9 66 2		':AUTOLISP)
(000026A6 53 3 76 2 1 32		add-desktop-option)
(000026AC 10)
(000026AD 9 77 0		'*printer-font*)
(000026B0 9 67 2		':L-CONTEXT)
(000026B3 9 66 2		':AUTOLISP)
(000026B6 9 63 2		':ACCESSOR)
(000026B9 15 0 0		JMP 000026BC)
(000026BC 9 140 2		'nil)
(000026BF 15 0 0		JMP 000026C2)
(000026C2 9 139 2		'nil)
(000026C5 57 2 0		list)
(000026C8 53 5 76 2 1 32		add-desktop-option)
(000026CE 10)
(000026CF 9 84 0		'*print-left-margin*)
(000026D2 9 76 0		25.0)
(000026D5 53 2 69 2 1 32		delayed-desktop-restore)
(000026DB 10)
(000026DC 9 83 0		'*print-right-margin*)
(000026DF 9 75 0		15.0)
(000026E2 53 2 69 2 1 32		delayed-desktop-restore)
(000026E8 10)
(000026E9 9 82 0		'*print-top-margin*)
(000026EC 9 75 0		15.0)
(000026EF 53 2 69 2 1 32		delayed-desktop-restore)
(000026F5 10)
(000026F6 9 81 0		'*print-bottom-margin*)
(000026F9 9 75 0		15.0)
(000026FC 53 2 69 2 1 32		delayed-desktop-restore)
(00002702 10)
(00002703 9 74 0		'*print-header/footer-state*)
(00002706 50 3		3)
(00002708 53 2 69 2 1 32		delayed-desktop-restore)
(0000270E 10)
(0000270F 9 80 0		'*printer-header*)
(00002712 9 187 1		"VLMSG.DLL")
(00002715 51 46 89 0 0		22830)
(0000271A 81 2 186 1 1 0		string-resource)
(00002720 1		nil)
(00002721 9 187 1		"VLMSG.DLL")
(00002724 51 56 89 0 0		22840)
(00002729 81 2 186 1 1 0		string-resource)
(0000272F 9 73 0		"&d")
(00002732 57 4 0		list)
(00002735 53 2 69 2 1 32		delayed-desktop-restore)
(0000273B 10)
(0000273C 9 79 0		'*printer-footer*)
(0000273F 9 72 0		'("&r&p" nil nil "&p"))
(00002742 53 2 69 2 1 32		delayed-desktop-restore)
(00002748 10)
(00002749 9 78 0		'*print-inch-or-mm*)
(0000274C 9 71 0		':INCH)
(0000274F 53 2 69 2 1 32		delayed-desktop-restore)
(00002755 10)
(00002756 1		nil)
(00002757 10)
(00002758 1		nil)
(00002759 10)
(0000275A 9 70 0		25.4)
(0000275D 26 69 0		*mm-per-inch*)
(00002760 9 69 0		'*mm-per-inch*)
(00002763 10)
(00002764 50 1		1)
(00002766 9 70 0		25.4)
(00002769 81 2 68 0 1 0		/)
(0000276F 26 67 0		*inch-per-mm*)
(00002772 9 67 0		'*inch-per-mm*)
(00002775 10)
(00002776 1		nil)
(00002777 10)
(00002778 1		nil)
(00002779 10)
(0000277A 12 138 2		'_margin-value-item)
(0000277D 26 66 0		_margin-value-item)
(00002780 9 66 0		'_margin-value-item)
(00002783 10)
(00002784 1		nil)
(00002785 10)
(00002786 9 137 2		'_correct-margin)
(00002789 26 65 0		_correct-margin)
(0000278C 9 65 0		'_correct-margin)
(0000278F 10)
(00002790 9 136 2		'_verify-margins)
(00002793 26 64 0		_verify-margins)
(00002796 9 64 0		'_verify-margins)
(00002799 10)
(0000279A 9 135 2		'_setpage-ok)
(0000279D 26 63 0		_setpage-ok)
(000027A0 9 63 0		'_setpage-ok)
(000027A3 10)
(000027A4 9 134 2		'!printer-font-setup)
(000027A7 26 62 0		!printer-font-setup)
(000027AA 9 62 0		'!printer-font-setup)
(000027AD 10)
(000027AE 12 133 2		'!page-setup-dialog)
(000027B1 26 61 0		!page-setup-dialog)
(000027B4 9 61 0		'!page-setup-dialog)
(000027B7 10)
(000027B8 1		nil)
(000027B9 10)
(000027BA 1		nil)
(000027BB 10)
(000027BC 1		nil)
(000027BD 10)
(000027BE 1		nil)
(000027BF 10)
(000027C0 1		nil)
(000027C1 10)
(000027C2 9 132 2		'_print-header-hook)
(000027C5 26 60 0		_print-header-hook)
(000027C8 9 60 0		'_print-header-hook)
(000027CB 10)
(000027CC 9 131 2		'_print-footer-hook)
(000027CF 26 59 0		_print-footer-hook)
(000027D2 9 59 0		'_print-footer-hook)
(000027D5 10)
(000027D6 9 132 2		'_print-header-hook)
(000027D9 11)
(000027DA 6 58 0		*print-header-hook*)
(000027DD 10)
(000027DE 9 131 2		'_print-footer-hook)
(000027E1 11)
(000027E2 6 57 0		*print-footer-hook*)
(000027E5 10)
(000027E6 9 130 2		'*print-file-hook*)
(000027E9 26 56 0		*print-file-hook*)
(000027EC 9 56 0		'*print-file-hook*)
(000027EF 28		[ret])
(000027F0 20 0 0 0 0)
(000027F5 1		nil)
(000027F6 10)
(000027F7 1		nil)
(000027F8 10)
(000027F9 1		nil)
(000027FA 10)
(000027FB 1		nil)
(000027FC 10)
(000027FD 3 55 0		*edt-toolbar-dlg*)
(00002800 27 55 0		*edt-toolbar-dlg*)
(00002803 9 55 0		'*edt-toolbar-dlg*)
(00002806 10)
(00002807 3 54 0		*console-toolbar-dlg*)
(0000280A 27 54 0		*console-toolbar-dlg*)
(0000280D 9 54 0		'*console-toolbar-dlg*)
(00002810 10)
(00002811 3 53 0		*sdb-toolbar-dlg*)
(00002814 27 53 0		*sdb-toolbar-dlg*)
(00002817 9 53 0		'*sdb-toolbar-dlg*)
(0000281A 10)
(0000281B 3 224 0		*carp-res0*)
(0000281E 50 49		49)
(00002820 50 0		0)
(00002822 81 2 135 1 1 0		make-ipoint)
(00002828 50 10		10)
(0000282A 50 10		10)
(0000282C 81 2 135 1 1 0		make-ipoint)
(00002832 9 52 0		'destroy-host-spouse)
(00002835 9 187 1		"VLMSG.DLL")
(00002838 51 36 89 0 0		22820)
(0000283D 81 2 186 1 1 0		string-resource)
(00002843 53 5 219 0 1 32		bmp-push-button1)
(00002849 27 51 0		*close-dlg-bmp-pb*)
(0000284C 9 51 0		'*close-dlg-bmp-pb*)
(0000284F 10)
(00002850 3 51 0		*close-dlg-bmp-pb*)
(00002853 2		T)
(00002854 81 2 50 0 1 0		bmp-button.notflat)
(0000285A 10)
(0000285B 51 128 0 0 0		128)
(00002860 26 49 0		WS_EX_TOOLWINDOW)
(00002863 9 49 0		'WS_EX_TOOLWINDOW)
(00002866 10)
(00002867 50 8		8)
(00002869 50 16		16)
(0000286B 50 32		32)
(0000286D 50 64		64)
(0000286F 81 4 48 0 1 0		+)
(00002875 26 47 0		*TB_DLG-FL-BORDER*)
(00002878 9 47 0		'*TB_DLG-FL-BORDER*)
(0000287B 10)
(0000287C 50 8		8)
(0000287E 50 16		16)
(00002880 50 32		32)
(00002882 50 64		64)
(00002884 81 4 48 0 1 0		+)
(0000288A 26 47 0		*TB_DLG-FL-BORDER*)
(0000288D 9 47 0		'*TB_DLG-FL-BORDER*)
(00002890 10)
(00002891 51 0 0 0 4		67108864)
(00002896 26 46 0		WS_CLIPSIBLINGS)
(00002899 9 46 0		'WS_CLIPSIBLINGS)
(0000289C 10)
(0000289D 3 45 0		DS_LOCALEDIT)
(000028A0 3 44 0		DS_NOIDLEMSG)
(000028A3 3 43 0		WS_POPUP)
(000028A6 3 42 0		WS_VISIBLE)
(000028A9 81 4 41 0 1 0		logior)
(000028AF 26 40 0		*WS_TB-FLOAT-STYLE*)
(000028B2 9 40 0		'*WS_TB-FLOAT-STYLE*)
(000028B5 10)
(000028B6 50 1		1)
(000028B8 50 16		16)
(000028BA 50 32		32)
(000028BC 50 64		64)
(000028BE 81 4 48 0 1 0		+)
(000028C4 26 39 0		*TB_DLG-H-BORDER*)
(000028C7 9 39 0		'*TB_DLG-H-BORDER*)
(000028CA 10)
(000028CB 50 2		2)
(000028CD 50 16		16)
(000028CF 50 32		32)
(000028D1 50 64		64)
(000028D3 81 4 48 0 1 0		+)
(000028D9 26 38 0		*TB_DLG-V-BORDER*)
(000028DC 9 38 0		'*TB_DLG-V-BORDER*)
(000028DF 10)
(000028E0 3 37 0		WS_CHILD)
(000028E3 3 42 0		WS_VISIBLE)
(000028E6 51 0 0 0 4		67108864)
(000028EB 81 3 41 0 1 0		logior)
(000028F1 26 36 0		*WS_TB-RIBBON-STYLE*)
(000028F4 9 36 0		'*WS_TB-RIBBON-STYLE*)
(000028F7 10)
(000028F8 9 35 0		'toolbar-multydialog)
(000028FB 9 34 0		'(dialog))
(000028FE 3 33 0		*deftype-hook*)
(00002901 52 2 1		)
(00002904 10)
(00002905 9 35 0		'toolbar-multydialog)
(00002908 9 32 0		'(dialog-class toolbar-multydialog :BASE :MIXED-PAGE "Undocumented class" ((new-instance . toolbar-multydialog.new-instance)) nil ((caption . string) (apex . T) (size fixnum) (font . string) (pitch fixnum) (items . T) (parent . T) (default-push-button . T) (close-box-command . T) (states . T) (l-context . T) (register-symbol . T) (update-on-idle . T)) ((create-host-spouse dialog.create-host-spouse) (update-host-spouse dialog.update-host-spouse) (destroy-host-spouse dialog.destroy-host-spouse) (host-spouse-exists-p dialog.host-spouse-exists-p) (print-object . dialog.print-object) (accessed-verify . dialog.accessed-verify) (sync-up dialog.sync-up) (sync-down dialog.sync-down) (!dialog-size-hook . dialog.!dialog-size-hook) (bcolor . dialog.bcolor) (bcolor<- . dialog.bcolor<-) (!dialog-escape . dialog.!dialog-escape) (inspector-binary-slot-descriptions ("(host-spouse-exists-p) " nil host-spouse-exists-p) ("(_msw-style) " nil dialog._msw-style) ("(_border-style) " (fixnum) dialog._border-style dialog._border-style<-) ("(bcolor) " T dialog.bcolor dialog.bcolor<-)) (inspector-slot-printers apex ipoint-prin1-to-string size ipoint-prin1-to-string))))
(0000290B 53 2 31 0 1 32		find-class<-)
(00002911 10)
(00002912 1		nil)
(00002913 10)
(00002914 1		nil)
(00002915 10)
(00002916 1		nil)
(00002917 10)
(00002918 1		nil)
(00002919 10)
(0000291A 1		nil)
(0000291B 10)
(0000291C 1		nil)
(0000291D 10)
(0000291E 1		nil)
(0000291F 10)
(00002920 1		nil)
(00002921 10)
(00002922 1		nil)
(00002923 10)
(00002924 1		nil)
(00002925 10)
(00002926 1		nil)
(00002927 10)
(00002928 1		nil)
(00002929 10)
(0000292A 1		nil)
(0000292B 10)
(0000292C 1		nil)
(0000292D 10)
(0000292E 1		nil)
(0000292F 10)
(00002930 1		nil)
(00002931 10)
(00002932 1		nil)
(00002933 10)
(00002934 1		nil)
(00002935 10)
(00002936 1		nil)
(00002937 10)
(00002938 1		nil)
(00002939 10)
(0000293A 1		nil)
(0000293B 10)
(0000293C 1		nil)
(0000293D 10)
(0000293E 1		nil)
(0000293F 10)
(00002940 9 129 2		'!drag-dlg)
(00002943 26 30 0		!drag-dlg)
(00002946 9 30 0		'!drag-dlg)
(00002949 10)
(0000294A 1		nil)
(0000294B 10)
(0000294C 1		nil)
(0000294D 10)
(0000294E 1		nil)
(0000294F 10)
(00002950 9 29 0		'*toolbar-cfg*)
(00002953 9 63 2		':ACCESSOR)
(00002956 9 128 2		'desktop-save-toolbar)
(00002959 9 127 2		'desktop-restore-toolbar)
(0000295C 57 2 0		list)
(0000295F 9 67 2		':L-CONTEXT)
(00002962 9 66 2		':AUTOLISP)
(00002965 53 5 76 2 1 32		add-desktop-option)
(0000296B 28		[ret])
(0000296C 20 2 0 0 0)
(00002971 1		nil)
(00002972 10)
(00002973 1		nil)
(00002974 10)
(00002975 9 187 1		"VLMSG.DLL")
(00002978 51 100 90 0 0		23140)
(0000297D 81 2 186 1 1 0		string-resource)
(00002983 9 149 1		':H)
(00002986 50 3		3)
(00002988 9 148 1		':V)
(0000298B 9 147 0		'*btn-d-sep-v-tools*)
(0000298E 57 2 0		list)
(00002991 50 3		3)
(00002993 9 148 1		':V)
(00002996 50 3		3)
(00002998 9 218 0		'*btn-load-buffer*)
(0000299B 57 3 0		list)
(0000299E 50 3		3)
(000029A0 9 148 1		':V)
(000029A3 50 3		3)
(000029A5 9 217 0		'*btn-load-select*)
(000029A8 57 3 0		list)
(000029AB 50 3		3)
(000029AD 9 148 1		':V)
(000029B0 50 3		3)
(000029B2 9 215 0		'*btn-check-buffer*)
(000029B5 57 3 0		list)
(000029B8 50 3		3)
(000029BA 9 148 1		':V)
(000029BD 50 3		3)
(000029BF 9 216 0		'*btn-check-select*)
(000029C2 57 3 0		list)
(000029C5 50 3		3)
(000029C7 9 148 1		':V)
(000029CA 50 3		3)
(000029CC 9 211 0		'*btn-format-buffer*)
(000029CF 57 3 0		list)
(000029D2 50 3		3)
(000029D4 9 148 1		':V)
(000029D7 50 3		3)
(000029D9 9 213 0		'*btn-format-select*)
(000029DC 57 3 0		list)
(000029DF 50 3		3)
(000029E1 9 148 1		':V)
(000029E4 9 146 0		'*btn-s-sep-v-tools0*)
(000029E7 57 2 0		list)
(000029EA 50 3		3)
(000029EC 9 148 1		':V)
(000029EF 50 3		3)
(000029F1 9 160 0		'*btn-comment-block*)
(000029F4 57 3 0		list)
(000029F7 50 3		3)
(000029F9 9 148 1		':V)
(000029FC 50 3		3)
(000029FE 9 159 0		'*btn-uncomment-block*)
(00002A01 57 3 0		list)
(00002A04 50 3		3)
(00002A06 9 148 1		':V)
(00002A09 9 145 0		'*btn-s-sep-v-tools1*)
(00002A0C 57 2 0		list)
(00002A0F 50 3		3)
(00002A11 9 148 1		':V)
(00002A14 50 3		3)
(00002A16 9 158 0		'*btn-help*)
(00002A19 57 3 0		list)
(00002A1C 50 3		3)
(00002A1E 57 26 0		list)
(00002A21 9 148 1		':V)
(00002A24 50 3		3)
(00002A26 9 149 1		':H)
(00002A29 9 144 0		'*btn-d-sep-h-tools*)
(00002A2C 57 2 0		list)
(00002A2F 50 3		3)
(00002A31 9 149 1		':H)
(00002A34 50 3		3)
(00002A36 9 218 0		'*btn-load-buffer*)
(00002A39 57 3 0		list)
(00002A3C 50 3		3)
(00002A3E 9 149 1		':H)
(00002A41 50 3		3)
(00002A43 9 217 0		'*btn-load-select*)
(00002A46 57 3 0		list)
(00002A49 50 3		3)
(00002A4B 9 149 1		':H)
(00002A4E 50 3		3)
(00002A50 9 215 0		'*btn-check-buffer*)
(00002A53 57 3 0		list)
(00002A56 50 3		3)
(00002A58 9 149 1		':H)
(00002A5B 50 3		3)
(00002A5D 9 216 0		'*btn-check-select*)
(00002A60 57 3 0		list)
(00002A63 50 3		3)
(00002A65 9 149 1		':H)
(00002A68 50 3		3)
(00002A6A 9 211 0		'*btn-format-buffer*)
(00002A6D 57 3 0		list)
(00002A70 50 3		3)
(00002A72 9 149 1		':H)
(00002A75 50 3		3)
(00002A77 9 213 0		'*btn-format-select*)
(00002A7A 57 3 0		list)
(00002A7D 50 3		3)
(00002A7F 9 149 1		':H)
(00002A82 9 143 0		'*btn-s-sep-h-tools0*)
(00002A85 57 2 0		list)
(00002A88 50 3		3)
(00002A8A 9 149 1		':H)
(00002A8D 50 3		3)
(00002A8F 9 160 0		'*btn-comment-block*)
(00002A92 57 3 0		list)
(00002A95 50 3		3)
(00002A97 9 149 1		':H)
(00002A9A 50 3		3)
(00002A9C 9 159 0		'*btn-uncomment-block*)
(00002A9F 57 3 0		list)
(00002AA2 50 3		3)
(00002AA4 9 149 1		':H)
(00002AA7 9 142 0		'*btn-s-sep-h-tools1*)
(00002AAA 57 2 0		list)
(00002AAD 50 3		3)
(00002AAF 9 149 1		':H)
(00002AB2 50 3		3)
(00002AB4 9 158 0		'*btn-help*)
(00002AB7 57 3 0		list)
(00002ABA 50 3		3)
(00002ABC 57 26 0		list)
(00002ABF 9 28 0		':FL)
(00002AC2 9 149 1		':H)
(00002AC5 50 3		3)
(00002AC7 9 148 1		':V)
(00002ACA 50 2		2)
(00002ACC 9 147 0		'*btn-d-sep-v-tools*)
(00002ACF 50 2		2)
(00002AD1 57 4 0		list)
(00002AD4 50 3		3)
(00002AD6 9 148 1		':V)
(00002AD9 50 5		5)
(00002ADB 9 218 0		'*btn-load-buffer*)
(00002ADE 57 3 0		list)
(00002AE1 50 3		3)
(00002AE3 9 148 1		':V)
(00002AE6 50 5		5)
(00002AE8 9 217 0		'*btn-load-select*)
(00002AEB 57 3 0		list)
(00002AEE 50 3		3)
(00002AF0 9 148 1		':V)
(00002AF3 50 5		5)
(00002AF5 9 215 0		'*btn-check-buffer*)
(00002AF8 57 3 0		list)
(00002AFB 50 3		3)
(00002AFD 9 148 1		':V)
(00002B00 50 5		5)
(00002B02 9 216 0		'*btn-check-select*)
(00002B05 57 3 0		list)
(00002B08 50 3		3)
(00002B0A 9 148 1		':V)
(00002B0D 50 5		5)
(00002B0F 9 211 0		'*btn-format-buffer*)
(00002B12 57 3 0		list)
(00002B15 50 3		3)
(00002B17 9 148 1		':V)
(00002B1A 50 5		5)
(00002B1C 9 213 0		'*btn-format-select*)
(00002B1F 57 3 0		list)
(00002B22 50 3		3)
(00002B24 9 148 1		':V)
(00002B27 50 2		2)
(00002B29 9 146 0		'*btn-s-sep-v-tools0*)
(00002B2C 57 3 0		list)
(00002B2F 50 3		3)
(00002B31 9 148 1		':V)
(00002B34 50 5		5)
(00002B36 9 160 0		'*btn-comment-block*)
(00002B39 57 3 0		list)
(00002B3C 50 3		3)
(00002B3E 9 148 1		':V)
(00002B41 50 5		5)
(00002B43 9 159 0		'*btn-uncomment-block*)
(00002B46 57 3 0		list)
(00002B49 50 3		3)
(00002B4B 9 148 1		':V)
(00002B4E 50 2		2)
(00002B50 9 145 0		'*btn-s-sep-v-tools1*)
(00002B53 57 3 0		list)
(00002B56 50 3		3)
(00002B58 9 148 1		':V)
(00002B5B 50 5		5)
(00002B5D 9 158 0		'*btn-help*)
(00002B60 57 3 0		list)
(00002B63 50 3		3)
(00002B65 57 26 0		list)
(00002B68 57 2 0		list)
(00002B6B 57 4 0		list)
(00002B6E 27 27 0		*console-toolbar*)
(00002B71 9 27 0		'*console-toolbar*)
(00002B74 10)
(00002B75 9 187 1		"VLMSG.DLL")
(00002B78 51 110 90 0 0		23150)
(00002B7D 81 2 186 1 1 0		string-resource)
(00002B83 9 149 1		':H)
(00002B86 50 3		3)
(00002B88 9 148 1		':V)
(00002B8B 9 141 0		'*btn-d-sep-v-std*)
(00002B8E 57 2 0		list)
(00002B91 50 3		3)
(00002B93 9 148 1		':V)
(00002B96 50 3		3)
(00002B98 9 155 0		'*btn-new*)
(00002B9B 57 3 0		list)
(00002B9E 50 3		3)
(00002BA0 9 148 1		':V)
(00002BA3 50 3		3)
(00002BA5 9 157 0		'*btn-open*)
(00002BA8 57 3 0		list)
(00002BAB 50 3		3)
(00002BAD 9 148 1		':V)
(00002BB0 50 3		3)
(00002BB2 9 156 0		'*btn-save*)
(00002BB5 57 3 0		list)
(00002BB8 50 3		3)
(00002BBA 9 148 1		':V)
(00002BBD 50 3		3)
(00002BBF 9 170 0		'*btn-print*)
(00002BC2 57 3 0		list)
(00002BC5 50 3		3)
(00002BC7 9 148 1		':V)
(00002BCA 9 140 0		'*btn-s-sep-v-std0*)
(00002BCD 57 2 0		list)
(00002BD0 50 3		3)
(00002BD2 9 148 1		':V)
(00002BD5 50 3		3)
(00002BD7 9 154 0		'*btn-cut*)
(00002BDA 57 3 0		list)
(00002BDD 50 3		3)
(00002BDF 9 148 1		':V)
(00002BE2 50 3		3)
(00002BE4 9 153 0		'*btn-copy*)
(00002BE7 57 3 0		list)
(00002BEA 50 3		3)
(00002BEC 9 148 1		':V)
(00002BEF 50 3		3)
(00002BF1 9 152 0		'*btn-paste*)
(00002BF4 57 3 0		list)
(00002BF7 50 3		3)
(00002BF9 9 148 1		':V)
(00002BFC 9 139 0		'*btn-s-sep-v-std1*)
(00002BFF 57 2 0		list)
(00002C02 50 3		3)
(00002C04 9 148 1		':V)
(00002C07 50 3		3)
(00002C09 9 169 0		'*btn-undo*)
(00002C0C 57 3 0		list)
(00002C0F 50 3		3)
(00002C11 9 148 1		':V)
(00002C14 50 3		3)
(00002C16 9 168 0		'*btn-redo*)
(00002C19 57 3 0		list)
(00002C1C 50 3		3)
(00002C1E 9 148 1		':V)
(00002C21 9 138 0		'*btn-s-sep-v-std2*)
(00002C24 57 2 0		list)
(00002C27 50 3		3)
(00002C29 9 148 1		':V)
(00002C2C 50 3		3)
(00002C2E 9 149 0		'*btn-complete*)
(00002C31 57 3 0		list)
(00002C34 50 3		3)
(00002C36 57 30 0		list)
(00002C39 9 148 1		':V)
(00002C3C 50 3		3)
(00002C3E 9 149 1		':H)
(00002C41 9 137 0		'*btn-d-sep-h-std*)
(00002C44 57 2 0		list)
(00002C47 50 3		3)
(00002C49 9 149 1		':H)
(00002C4C 50 3		3)
(00002C4E 9 155 0		'*btn-new*)
(00002C51 57 3 0		list)
(00002C54 50 3		3)
(00002C56 9 149 1		':H)
(00002C59 50 3		3)
(00002C5B 9 157 0		'*btn-open*)
(00002C5E 57 3 0		list)
(00002C61 50 3		3)
(00002C63 9 149 1		':H)
(00002C66 50 3		3)
(00002C68 9 156 0		'*btn-save*)
(00002C6B 57 3 0		list)
(00002C6E 50 3		3)
(00002C70 9 149 1		':H)
(00002C73 50 3		3)
(00002C75 9 170 0		'*btn-print*)
(00002C78 57 3 0		list)
(00002C7B 50 3		3)
(00002C7D 9 149 1		':H)
(00002C80 9 136 0		'*btn-s-sep-h-std0*)
(00002C83 57 2 0		list)
(00002C86 50 3		3)
(00002C88 9 149 1		':H)
(00002C8B 50 3		3)
(00002C8D 9 154 0		'*btn-cut*)
(00002C90 57 3 0		list)
(00002C93 50 3		3)
(00002C95 9 149 1		':H)
(00002C98 50 3		3)
(00002C9A 9 153 0		'*btn-copy*)
(00002C9D 57 3 0		list)
(00002CA0 50 3		3)
(00002CA2 9 149 1		':H)
(00002CA5 50 3		3)
(00002CA7 9 152 0		'*btn-paste*)
(00002CAA 57 3 0		list)
(00002CAD 50 3		3)
(00002CAF 9 149 1		':H)
(00002CB2 9 135 0		'*btn-s-sep-h-std1*)
(00002CB5 57 2 0		list)
(00002CB8 50 3		3)
(00002CBA 9 149 1		':H)
(00002CBD 50 3		3)
(00002CBF 9 169 0		'*btn-undo*)
(00002CC2 57 3 0		list)
(00002CC5 50 3		3)
(00002CC7 9 149 1		':H)
(00002CCA 50 3		3)
(00002CCC 9 168 0		'*btn-redo*)
(00002CCF 57 3 0		list)
(00002CD2 50 3		3)
(00002CD4 9 149 1		':H)
(00002CD7 9 134 0		'*btn-s-sep-h-std2*)
(00002CDA 57 2 0		list)
(00002CDD 50 3		3)
(00002CDF 9 149 1		':H)
(00002CE2 50 3		3)
(00002CE4 9 149 0		'*btn-complete*)
(00002CE7 57 3 0		list)
(00002CEA 50 3		3)
(00002CEC 57 30 0		list)
(00002CEF 9 28 0		':FL)
(00002CF2 9 149 1		':H)
(00002CF5 50 3		3)
(00002CF7 9 148 1		':V)
(00002CFA 50 2		2)
(00002CFC 9 141 0		'*btn-d-sep-v-std*)
(00002CFF 50 2		2)
(00002D01 57 4 0		list)
(00002D04 50 3		3)
(00002D06 9 148 1		':V)
(00002D09 50 5		5)
(00002D0B 9 155 0		'*btn-new*)
(00002D0E 57 3 0		list)
(00002D11 50 3		3)
(00002D13 9 148 1		':V)
(00002D16 50 5		5)
(00002D18 9 157 0		'*btn-open*)
(00002D1B 57 3 0		list)
(00002D1E 50 3		3)
(00002D20 9 148 1		':V)
(00002D23 50 5		5)
(00002D25 9 156 0		'*btn-save*)
(00002D28 57 3 0		list)
(00002D2B 50 3		3)
(00002D2D 9 148 1		':V)
(00002D30 50 5		5)
(00002D32 9 170 0		'*btn-print*)
(00002D35 57 3 0		list)
(00002D38 50 3		3)
(00002D3A 9 148 1		':V)
(00002D3D 50 2		2)
(00002D3F 9 140 0		'*btn-s-sep-v-std0*)
(00002D42 57 3 0		list)
(00002D45 50 3		3)
(00002D47 9 148 1		':V)
(00002D4A 50 5		5)
(00002D4C 9 154 0		'*btn-cut*)
(00002D4F 57 3 0		list)
(00002D52 50 3		3)
(00002D54 9 148 1		':V)
(00002D57 50 5		5)
(00002D59 9 153 0		'*btn-copy*)
(00002D5C 57 3 0		list)
(00002D5F 50 3		3)
(00002D61 9 148 1		':V)
(00002D64 50 5		5)
(00002D66 9 152 0		'*btn-paste*)
(00002D69 57 3 0		list)
(00002D6C 50 3		3)
(00002D6E 9 148 1		':V)
(00002D71 50 2		2)
(00002D73 9 139 0		'*btn-s-sep-v-std1*)
(00002D76 57 3 0		list)
(00002D79 50 3		3)
(00002D7B 9 148 1		':V)
(00002D7E 50 5		5)
(00002D80 9 169 0		'*btn-undo*)
(00002D83 57 3 0		list)
(00002D86 50 3		3)
(00002D88 9 148 1		':V)
(00002D8B 50 5		5)
(00002D8D 9 168 0		'*btn-redo*)
(00002D90 57 3 0		list)
(00002D93 50 3		3)
(00002D95 9 148 1		':V)
(00002D98 50 2		2)
(00002D9A 9 138 0		'*btn-s-sep-v-std2*)
(00002D9D 57 3 0		list)
(00002DA0 50 3		3)
(00002DA2 9 148 1		':V)
(00002DA5 50 5		5)
(00002DA7 9 149 0		'*btn-complete*)
(00002DAA 57 3 0		list)
(00002DAD 50 3		3)
(00002DAF 57 30 0		list)
(00002DB2 57 2 0		list)
(00002DB5 57 4 0		list)
(00002DB8 27 26 0		*editor-toolbar*)
(00002DBB 9 26 0		'*editor-toolbar*)
(00002DBE 10)
(00002DBF 9 187 1		"VLMSG.DLL")
(00002DC2 51 120 90 0 0		23160)
(00002DC7 81 2 186 1 1 0		string-resource)
(00002DCD 9 149 1		':H)
(00002DD0 9 126 1		':DEFAULT-PUSH-BUTTON)
(00002DD3 9 165 0		'*glassnext-btn*)
(00002DD6 50 3		3)
(00002DD8 9 148 1		':V)
(00002DDB 9 133 0		'*btn-d-sep-v-sch*)
(00002DDE 57 2 0		list)
(00002DE1 50 3		3)
(00002DE3 9 148 1		':V)
(00002DE6 50 3		3)
(00002DE8 9 167 0		'*glasses-btn*)
(00002DEB 57 3 0		list)
(00002DEE 50 3		3)
(00002DF0 9 148 1		':V)
(00002DF3 50 3		3)
(00002DF5 9 166 0		'*btn-replace*)
(00002DF8 57 3 0		list)
(00002DFB 50 3		3)
(00002DFD 9 148 1		':V)
(00002E00 50 1		1)
(00002E02 9 188 1		'*lb-find-next*)
(00002E05 57 3 0		list)
(00002E08 50 3		3)
(00002E0A 9 148 1		':V)
(00002E0D 50 3		3)
(00002E0F 9 165 0		'*glassnext-btn*)
(00002E12 57 3 0		list)
(00002E15 50 3		3)
(00002E17 9 148 1		':V)
(00002E1A 9 132 0		'*btn-s-sep-v-sch0*)
(00002E1D 57 2 0		list)
(00002E20 50 3		3)
(00002E22 9 148 1		':V)
(00002E25 50 3		3)
(00002E27 9 175 0		'*pum-btn*)
(00002E2A 57 3 0		list)
(00002E2D 50 3		3)
(00002E2F 9 148 1		':V)
(00002E32 50 3		3)
(00002E34 9 173 0		'*swmp-btn*)
(00002E37 57 3 0		list)
(00002E3A 50 3		3)
(00002E3C 9 148 1		':V)
(00002E3F 50 3		3)
(00002E41 9 174 0		'*pom-btn*)
(00002E44 57 3 0		list)
(00002E47 50 3		3)
(00002E49 9 148 1		':V)
(00002E4C 50 3		3)
(00002E4E 9 172 0		'*btn-cle-book*)
(00002E51 57 3 0		list)
(00002E54 50 3		3)
(00002E56 57 24 0		list)
(00002E59 9 148 1		':V)
(00002E5C 50 3		3)
(00002E5E 9 148 1		':V)
(00002E61 9 131 0		'*btn-d-sep-h-sch*)
(00002E64 57 2 0		list)
(00002E67 50 3		3)
(00002E69 9 149 1		':H)
(00002E6C 50 3		3)
(00002E6E 9 167 0		'*glasses-btn*)
(00002E71 57 3 0		list)
(00002E74 50 3		3)
(00002E76 9 149 1		':H)
(00002E79 50 3		3)
(00002E7B 9 166 0		'*btn-replace*)
(00002E7E 57 3 0		list)
(00002E81 50 3		3)
(00002E83 9 149 1		':H)
(00002E86 50 3		3)
(00002E88 9 165 0		'*glassnext-btn*)
(00002E8B 57 3 0		list)
(00002E8E 50 3		3)
(00002E90 9 149 1		':H)
(00002E93 9 130 0		'*btn-s-sep-h-sch0*)
(00002E96 57 2 0		list)
(00002E99 50 3		3)
(00002E9B 9 149 1		':H)
(00002E9E 50 3		3)
(00002EA0 9 175 0		'*pum-btn*)
(00002EA3 57 3 0		list)
(00002EA6 50 3		3)
(00002EA8 9 149 1		':H)
(00002EAB 50 3		3)
(00002EAD 9 173 0		'*swmp-btn*)
(00002EB0 57 3 0		list)
(00002EB3 50 3		3)
(00002EB5 9 149 1		':H)
(00002EB8 50 3		3)
(00002EBA 9 174 0		'*pom-btn*)
(00002EBD 57 3 0		list)
(00002EC0 50 3		3)
(00002EC2 9 149 1		':H)
(00002EC5 50 3		3)
(00002EC7 9 172 0		'*btn-cle-book*)
(00002ECA 57 3 0		list)
(00002ECD 50 3		3)
(00002ECF 57 20 0		list)
(00002ED2 9 28 0		':FL)
(00002ED5 9 149 1		':H)
(00002ED8 50 3		3)
(00002EDA 9 148 1		':V)
(00002EDD 50 2		2)
(00002EDF 9 133 0		'*btn-d-sep-v-sch*)
(00002EE2 50 2		2)
(00002EE4 57 4 0		list)
(00002EE7 50 3		3)
(00002EE9 9 148 1		':V)
(00002EEC 50 5		5)
(00002EEE 9 167 0		'*glasses-btn*)
(00002EF1 57 3 0		list)
(00002EF4 50 3		3)
(00002EF6 9 148 1		':V)
(00002EF9 50 5		5)
(00002EFB 9 166 0		'*btn-replace*)
(00002EFE 57 3 0		list)
(00002F01 50 3		3)
(00002F03 9 148 1		':V)
(00002F06 50 5		5)
(00002F08 9 165 0		'*glassnext-btn*)
(00002F0B 57 3 0		list)
(00002F0E 50 3		3)
(00002F10 9 148 1		':V)
(00002F13 50 2		2)
(00002F15 9 132 0		'*btn-s-sep-v-sch0*)
(00002F18 57 3 0		list)
(00002F1B 50 3		3)
(00002F1D 9 148 1		':V)
(00002F20 50 5		5)
(00002F22 9 175 0		'*pum-btn*)
(00002F25 57 3 0		list)
(00002F28 50 3		3)
(00002F2A 9 148 1		':V)
(00002F2D 50 5		5)
(00002F2F 9 173 0		'*swmp-btn*)
(00002F32 57 3 0		list)
(00002F35 50 3		3)
(00002F37 9 148 1		':V)
(00002F3A 50 5		5)
(00002F3C 9 174 0		'*pom-btn*)
(00002F3F 57 3 0		list)
(00002F42 50 3		3)
(00002F44 9 148 1		':V)
(00002F47 50 5		5)
(00002F49 9 172 0		'*btn-cle-book*)
(00002F4C 57 3 0		list)
(00002F4F 50 3		3)
(00002F51 57 20 0		list)
(00002F54 57 2 0		list)
(00002F57 57 4 0		list)
(00002F5A 27 25 0		*find-toolbar*)
(00002F5D 9 25 0		'*find-toolbar*)
(00002F60 10)
(00002F61 9 187 1		"VLMSG.DLL")
(00002F64 51 130 90 0 0		23170)
(00002F69 81 2 186 1 1 0		string-resource)
(00002F6F 9 149 1		':H)
(00002F72 50 3		3)
(00002F74 9 148 1		':V)
(00002F77 9 121 0		'*btn-d-sep-v-view*)
(00002F7A 57 2 0		list)
(00002F7D 50 3		3)
(00002F7F 9 148 1		':V)
(00002F82 50 3		3)
(00002F84 9 151 0		'*ribb-acad!-pb*)
(00002F87 57 3 0		list)
(00002F8A 50 3		3)
(00002F8C 9 148 1		':V)
(00002F8F 50 3		3)
(00002F91 9 161 0		'*btn-windows*)
(00002F94 57 3 0		list)
(00002F97 50 3		3)
(00002F99 9 148 1		':V)
(00002F9C 9 120 0		'*btn-s-sep-v-view0*)
(00002F9F 57 2 0		list)
(00002FA2 50 3		3)
(00002FA4 9 148 1		':V)
(00002FA7 50 3		3)
(00002FA9 9 195 0		'*btn-console*)
(00002FAC 57 3 0		list)
(00002FAF 50 3		3)
(00002FB1 9 148 1		':V)
(00002FB4 50 3		3)
(00002FB6 9 201 0		'*bino-btn*)
(00002FB9 57 3 0		list)
(00002FBC 50 3		3)
(00002FBE 9 148 1		':V)
(00002FC1 50 3		3)
(00002FC3 9 162 0		'*btn-backtrace*)
(00002FC6 57 3 0		list)
(00002FC9 50 3		3)
(00002FCB 9 148 1		':V)
(00002FCE 50 3		3)
(00002FD0 9 193 0		'*btn-ss*)
(00002FD3 57 3 0		list)
(00002FD6 50 3		3)
(00002FD8 9 148 1		':V)
(00002FDB 50 3		3)
(00002FDD 9 163 0		'*apropos-btn*)
(00002FE0 57 3 0		list)
(00002FE3 50 3		3)
(00002FE5 9 148 1		':V)
(00002FE8 50 3		3)
(00002FEA 9 197 0		'*btn-view-watch*)
(00002FED 57 3 0		list)
(00002FF0 50 3		3)
(00002FF2 57 22 0		list)
(00002FF5 9 148 1		':V)
(00002FF8 50 3		3)
(00002FFA 9 149 1		':H)
(00002FFD 9 119 0		'*btn-d-sep-h-view*)
(00003000 57 2 0		list)
(00003003 50 3		3)
(00003005 9 149 1		':H)
(00003008 50 3		3)
(0000300A 9 151 0		'*ribb-acad!-pb*)
(0000300D 57 3 0		list)
(00003010 50 3		3)
(00003012 9 149 1		':H)
(00003015 50 3		3)
(00003017 9 161 0		'*btn-windows*)
(0000301A 57 3 0		list)
(0000301D 50 3		3)
(0000301F 9 149 1		':H)
(00003022 9 118 0		'*btn-s-sep-h-view0*)
(00003025 57 2 0		list)
(00003028 50 3		3)
(0000302A 9 149 1		':H)
(0000302D 50 3		3)
(0000302F 9 195 0		'*btn-console*)
(00003032 57 3 0		list)
(00003035 50 3		3)
(00003037 9 149 1		':H)
(0000303A 50 3		3)
(0000303C 9 201 0		'*bino-btn*)
(0000303F 57 3 0		list)
(00003042 50 3		3)
(00003044 9 149 1		':H)
(00003047 50 3		3)
(00003049 9 162 0		'*btn-backtrace*)
(0000304C 57 3 0		list)
(0000304F 50 3		3)
(00003051 9 149 1		':H)
(00003054 50 3		3)
(00003056 9 193 0		'*btn-ss*)
(00003059 57 3 0		list)
(0000305C 50 3		3)
(0000305E 9 149 1		':H)
(00003061 50 3		3)
(00003063 9 163 0		'*apropos-btn*)
(00003066 57 3 0		list)
(00003069 50 3		3)
(0000306B 9 149 1		':H)
(0000306E 50 3		3)
(00003070 9 197 0		'*btn-view-watch*)
(00003073 57 3 0		list)
(00003076 50 3		3)
(00003078 57 22 0		list)
(0000307B 9 28 0		':FL)
(0000307E 9 149 1		':H)
(00003081 50 3		3)
(00003083 9 148 1		':V)
(00003086 50 2		2)
(00003088 9 121 0		'*btn-d-sep-v-view*)
(0000308B 50 2		2)
(0000308D 57 4 0		list)
(00003090 50 3		3)
(00003092 9 148 1		':V)
(00003095 50 5		5)
(00003097 9 151 0		'*ribb-acad!-pb*)
(0000309A 57 3 0		list)
(0000309D 50 3		3)
(0000309F 9 148 1		':V)
(000030A2 50 5		5)
(000030A4 9 161 0		'*btn-windows*)
(000030A7 57 3 0		list)
(000030AA 50 3		3)
(000030AC 9 148 1		':V)
(000030AF 50 2		2)
(000030B1 9 120 0		'*btn-s-sep-v-view0*)
(000030B4 57 3 0		list)
(000030B7 50 3		3)
(000030B9 9 148 1		':V)
(000030BC 50 5		5)
(000030BE 9 195 0		'*btn-console*)
(000030C1 57 3 0		list)
(000030C4 50 3		3)
(000030C6 9 148 1		':V)
(000030C9 50 5		5)
(000030CB 9 201 0		'*bino-btn*)
(000030CE 57 3 0		list)
(000030D1 50 3		3)
(000030D3 9 148 1		':V)
(000030D6 50 5		5)
(000030D8 9 162 0		'*btn-backtrace*)
(000030DB 57 3 0		list)
(000030DE 50 3		3)
(000030E0 9 148 1		':V)
(000030E3 50 5		5)
(000030E5 9 193 0		'*btn-ss*)
(000030E8 57 3 0		list)
(000030EB 50 3		3)
(000030ED 9 148 1		':V)
(000030F0 50 5		5)
(000030F2 9 163 0		'*apropos-btn*)
(000030F5 57 3 0		list)
(000030F8 50 3		3)
(000030FA 9 148 1		':V)
(000030FD 50 5		5)
(000030FF 9 197 0		'*btn-view-watch*)
(00003102 57 3 0		list)
(00003105 50 3		3)
(00003107 57 22 0		list)
(0000310A 57 2 0		list)
(0000310D 57 4 0		list)
(00003110 27 24 0		*inspect-toolbar*)
(00003113 9 24 0		'*inspect-toolbar*)
(00003116 10)
(00003117 9 187 1		"VLMSG.DLL")
(0000311A 51 140 90 0 0		23180)
(0000311F 81 2 186 1 1 0		string-resource)
(00003125 9 149 1		':H)
(00003128 50 3		3)
(0000312A 9 148 1		':V)
(0000312D 9 129 0		'*btn-d-sep-v-dbg*)
(00003130 57 2 0		list)
(00003133 50 3		3)
(00003135 9 148 1		':V)
(00003138 50 3		3)
(0000313A 9 191 0		'*stepin-btn*)
(0000313D 57 3 0		list)
(00003140 50 3		3)
(00003142 9 148 1		':V)
(00003145 50 3		3)
(00003147 9 192 0		'*step-btn*)
(0000314A 57 3 0		list)
(0000314D 50 3		3)
(0000314F 9 148 1		':V)
(00003152 50 3		3)
(00003154 9 190 0		'*ret-btn*)
(00003157 57 3 0		list)
(0000315A 50 3		3)
(0000315C 9 148 1		':V)
(0000315F 9 128 0		'*btn-s-sep-v-dbg0*)
(00003162 57 2 0		list)
(00003165 50 3		3)
(00003167 9 148 1		':V)
(0000316A 50 3		3)
(0000316C 9 207 0		'*hhand-btn*)
(0000316F 57 3 0		list)
(00003172 50 3		3)
(00003174 9 148 1		':V)
(00003177 50 3		3)
(00003179 9 205 0		'*quit-btn*)
(0000317C 57 3 0		list)
(0000317F 50 3		3)
(00003181 9 148 1		':V)
(00003184 50 3		3)
(00003186 9 203 0		'*reset-btn*)
(00003189 57 3 0		list)
(0000318C 50 3		3)
(0000318E 9 148 1		':V)
(00003191 9 127 0		'*btn-s-sep-v-dbg1*)
(00003194 57 2 0		list)
(00003197 50 3		3)
(00003199 9 148 1		':V)
(0000319C 50 3		3)
(0000319E 9 186 0		'*setbpt-btn*)
(000031A1 57 3 0		list)
(000031A4 50 3		3)
(000031A6 9 148 1		':V)
(000031A9 50 3		3)
(000031AB 9 199 0		'*btn-watch*)
(000031AE 57 3 0		list)
(000031B1 50 3		3)
(000031B3 9 148 1		':V)
(000031B6 50 3		3)
(000031B8 9 188 0		'*here-btn*)
(000031BB 57 3 0		list)
(000031BE 50 3		3)
(000031C0 9 148 1		':V)
(000031C3 9 126 0		'*btn-s-sep-v-dbg2*)
(000031C6 57 2 0		list)
(000031C9 50 3		3)
(000031CB 9 148 1		':V)
(000031CE 50 3		3)
(000031D0 9 179 0		'*bpt-status*)
(000031D3 57 3 0		list)
(000031D6 50 3		3)
(000031D8 57 30 0		list)
(000031DB 9 148 1		':V)
(000031DE 50 3		3)
(000031E0 9 149 1		':H)
(000031E3 9 125 0		'*btn-d-sep-h-dbg*)
(000031E6 57 2 0		list)
(000031E9 50 3		3)
(000031EB 9 149 1		':H)
(000031EE 50 3		3)
(000031F0 9 191 0		'*stepin-btn*)
(000031F3 57 3 0		list)
(000031F6 50 3		3)
(000031F8 9 149 1		':H)
(000031FB 50 3		3)
(000031FD 9 192 0		'*step-btn*)
(00003200 57 3 0		list)
(00003203 50 3		3)
(00003205 9 149 1		':H)
(00003208 50 3		3)
(0000320A 9 190 0		'*ret-btn*)
(0000320D 57 3 0		list)
(00003210 50 3		3)
(00003212 9 149 1		':H)
(00003215 9 124 0		'*btn-s-sep-h-dbg0*)
(00003218 57 2 0		list)
(0000321B 50 3		3)
(0000321D 9 149 1		':H)
(00003220 50 3		3)
(00003222 9 207 0		'*hhand-btn*)
(00003225 57 3 0		list)
(00003228 50 3		3)
(0000322A 9 149 1		':H)
(0000322D 50 3		3)
(0000322F 9 205 0		'*quit-btn*)
(00003232 57 3 0		list)
(00003235 50 3		3)
(00003237 9 149 1		':H)
(0000323A 50 3		3)
(0000323C 9 203 0		'*reset-btn*)
(0000323F 57 3 0		list)
(00003242 50 3		3)
(00003244 9 149 1		':H)
(00003247 9 123 0		'*btn-s-sep-h-dbg1*)
(0000324A 57 2 0		list)
(0000324D 50 3		3)
(0000324F 9 149 1		':H)
(00003252 50 3		3)
(00003254 9 186 0		'*setbpt-btn*)
(00003257 57 3 0		list)
(0000325A 50 3		3)
(0000325C 9 149 1		':H)
(0000325F 50 3		3)
(00003261 9 199 0		'*btn-watch*)
(00003264 57 3 0		list)
(00003267 50 3		3)
(00003269 9 149 1		':H)
(0000326C 50 3		3)
(0000326E 9 188 0		'*here-btn*)
(00003271 57 3 0		list)
(00003274 50 3		3)
(00003276 9 149 1		':H)
(00003279 9 122 0		'*btn-s-sep-h-dbg2*)
(0000327C 57 2 0		list)
(0000327F 50 3		3)
(00003281 9 149 1		':H)
(00003284 50 3		3)
(00003286 9 179 0		'*bpt-status*)
(00003289 57 3 0		list)
(0000328C 50 3		3)
(0000328E 57 30 0		list)
(00003291 9 28 0		':FL)
(00003294 9 149 1		':H)
(00003297 50 3		3)
(00003299 9 148 1		':V)
(0000329C 50 2		2)
(0000329E 9 129 0		'*btn-d-sep-v-dbg*)
(000032A1 50 2		2)
(000032A3 57 4 0		list)
(000032A6 50 3		3)
(000032A8 9 148 1		':V)
(000032AB 50 5		5)
(000032AD 9 191 0		'*stepin-btn*)
(000032B0 57 3 0		list)
(000032B3 50 3		3)
(000032B5 9 148 1		':V)
(000032B8 50 5		5)
(000032BA 9 192 0		'*step-btn*)
(000032BD 57 3 0		list)
(000032C0 50 3		3)
(000032C2 9 148 1		':V)
(000032C5 50 5		5)
(000032C7 9 190 0		'*ret-btn*)
(000032CA 57 3 0		list)
(000032CD 50 3		3)
(000032CF 9 148 1		':V)
(000032D2 50 2		2)
(000032D4 9 128 0		'*btn-s-sep-v-dbg0*)
(000032D7 57 3 0		list)
(000032DA 50 3		3)
(000032DC 9 148 1		':V)
(000032DF 50 5		5)
(000032E1 9 207 0		'*hhand-btn*)
(000032E4 57 3 0		list)
(000032E7 50 3		3)
(000032E9 9 148 1		':V)
(000032EC 50 5		5)
(000032EE 9 205 0		'*quit-btn*)
(000032F1 57 3 0		list)
(000032F4 50 3		3)
(000032F6 9 148 1		':V)
(000032F9 50 5		5)
(000032FB 9 203 0		'*reset-btn*)
(000032FE 57 3 0		list)
(00003301 50 3		3)
(00003303 9 148 1		':V)
(00003306 50 2		2)
(00003308 9 127 0		'*btn-s-sep-v-dbg1*)
(0000330B 57 3 0		list)
(0000330E 50 3		3)
(00003310 9 148 1		':V)
(00003313 50 5		5)
(00003315 9 186 0		'*setbpt-btn*)
(00003318 57 3 0		list)
(0000331B 50 3		3)
(0000331D 9 148 1		':V)
(00003320 50 5		5)
(00003322 9 199 0		'*btn-watch*)
(00003325 57 3 0		list)
(00003328 50 3		3)
(0000332A 9 148 1		':V)
(0000332D 50 5		5)
(0000332F 9 188 0		'*here-btn*)
(00003332 57 3 0		list)
(00003335 50 3		3)
(00003337 9 148 1		':V)
(0000333A 50 2		2)
(0000333C 9 126 0		'*btn-s-sep-v-dbg2*)
(0000333F 57 3 0		list)
(00003342 50 3		3)
(00003344 9 148 1		':V)
(00003347 50 5		5)
(00003349 9 179 0		'*bpt-status*)
(0000334C 57 3 0		list)
(0000334F 50 3		3)
(00003351 57 30 0		list)
(00003354 57 2 0		list)
(00003357 57 4 0		list)
(0000335A 27 23 0		*debug-toolbar*)
(0000335D 9 23 0		'*debug-toolbar*)
(00003360 10)
(00003361 9 27 0		'*console-toolbar*)
(00003364 9 54 0		'*console-toolbar-dlg*)
(00003367 9 22 0		':VL)
(0000336A 9 126 2		'console-toolbar-update)
(0000336D 57 4 0		list)
(00003370 9 26 0		'*editor-toolbar*)
(00003373 9 55 0		'*edt-toolbar-dlg*)
(00003376 9 21 0		':HT)
(00003379 9 125 2		'edt-toolbar-update)
(0000337C 57 4 0		list)
(0000337F 9 25 0		'*find-toolbar*)
(00003382 9 20 0		'*find-toolbar-dlg*)
(00003385 9 21 0		':HT)
(00003388 9 124 2		'find-toolbar-update)
(0000338B 57 4 0		list)
(0000338E 9 24 0		'*inspect-toolbar*)
(00003391 9 19 0		'*inspect-toolbar-dlg*)
(00003394 9 21 0		':HT)
(00003397 9 123 2		'view-toolbar-update)
(0000339A 57 4 0		list)
(0000339D 9 23 0		'*debug-toolbar*)
(000033A0 9 53 0		'*sdb-toolbar-dlg*)
(000033A3 9 22 0		':VL)
(000033A6 9 122 2		'sdb-toolbar-update)
(000033A9 57 4 0		list)
(000033AC 57 5 0		list)
(000033AF 26 18 0		*toolbars-list*)
(000033B2 9 18 0		'*toolbars-list*)
(000033B5 10)
(000033B6 9 121 2		'update-toolbar)
(000033B9 26 17 0		update-toolbar)
(000033BC 9 17 0		'update-toolbar)
(000033BF 10)
(000033C0 9 125 2		'edt-toolbar-update)
(000033C3 26 16 0		edt-toolbar-update)
(000033C6 9 16 0		'edt-toolbar-update)
(000033C9 10)
(000033CA 9 124 2		'find-toolbar-update)
(000033CD 26 15 0		find-toolbar-update)
(000033D0 9 15 0		'find-toolbar-update)
(000033D3 10)
(000033D4 9 123 2		'view-toolbar-update)
(000033D7 26 14 0		view-toolbar-update)
(000033DA 9 14 0		'view-toolbar-update)
(000033DD 10)
(000033DE 9 126 2		'console-toolbar-update)
(000033E1 26 13 0		console-toolbar-update)
(000033E4 9 13 0		'console-toolbar-update)
(000033E7 10)
(000033E8 9 122 2		'sdb-toolbar-update)
(000033EB 26 12 0		sdb-toolbar-update)
(000033EE 9 12 0		'sdb-toolbar-update)
(000033F1 10)
(000033F2 9 120 2		'get-toolbar)
(000033F5 26 11 0		get-toolbar)
(000033F8 9 11 0		'get-toolbar)
(000033FB 10)
(000033FC 9 119 2		'set-toolbar)
(000033FF 26 10 0		set-toolbar)
(00003402 9 10 0		'set-toolbar)
(00003405 10)
(00003406 12 118 2		'instantiate-toolbar-check-box)
(00003409 26 9 0		instantiate-toolbar-check-box)
(0000340C 9 9 0		'instantiate-toolbar-check-box)
(0000340F 10)
(00003410 9 117 2		'remove-all-toolbars)
(00003413 26 8 0		remove-all-toolbars)
(00003416 9 8 0		'remove-all-toolbars)
(00003419 10)
(0000341A 9 116 2		'add-all-toolbars)
(0000341D 26 7 0		add-all-toolbars)
(00003420 9 7 0		'add-all-toolbars)
(00003423 10)
(00003424 9 115 2		'!toolbars)
(00003427 26 6 0		!toolbars)
(0000342A 9 6 0		'!toolbars)
(0000342D 10)
(0000342E 3 18 0		*toolbars-list*)
(00003431 8 0		UnVar0)
(00003433 100 1		UNVar1)
(00003435 15 55 0		JMP 0000346F)
(00003438 5 0		UnVar0)
(0000343A 40		car)
(0000343B 8 1		UnVar1)
(0000343D 5 0		UnVar0)
(0000343F 41		cdr)
(00003440 8 0		UnVar0)
(00003442 9 114 2		'register-toolbar-multidialog)
(00003445 5 1		UnVar1)
(00003447 83		apply)
(00003448 10)
(00003449 3 188 1		*lb-find-next*)
(0000344C 51 150 0 0 0		150)
(00003451 53 1 182 0 1 32		auto-scale-x)
(00003457 50 16		16)
(00003459 53 1 181 0 1 32		auto-scale-y)
(0000345F 81 2 135 1 1 0		make-ipoint)
(00003465 9 128 1		'size)
(00003468 81 3 127 1 1 0		slot-value<-)
(0000346E 10)
(0000346F 5 0		UnVar0)
(00003471 60 196 255		T->JMP 00003438)
(00003474 2		T)
(00003475 10)
(00003476 1		nil)
(00003477 10)
(00003478 9 113 2		'make-default-tool-bar)
(0000347B 26 5 0		make-default-tool-bar)
(0000347E 9 5 0		'make-default-tool-bar)
(00003481 28		[ret])
(00003482 20 0 0 0 0)
(00003487 1		nil)
(00003488 10)
(00003489 9 112 2		'do-one-srv-cmd)
(0000348C 26 4 0		do-one-srv-cmd)
(0000348F 9 4 0		'do-one-srv-cmd)
(00003492 10)
(00003493 1		nil)
(00003494 10)
(00003495 9 111 2		'do-dde-server-work)
(00003498 26 3 0		do-dde-server-work)
(0000349B 9 3 0		'do-dde-server-work)
(0000349E 10)
(0000349F 9 110 2		'*poke-hook*)
(000034A2 26 2 0		*poke-hook*)
(000034A5 9 2 0		'*poke-hook*)
(000034A8 10)
(000034A9 9 109 2		'*peek-hook*)
(000034AC 26 1 0		*peek-hook*)
(000034AF 9 1 0		'*peek-hook*)
(000034B2 22		ret)
