;;;==========SubFunction==========
;;;def nil 1
(00000001 20 4 0 0 1)
(00000006 9 255 0		'eval-when)
(00000009 9 254 0		'eval)
(0000000C 9 253 0		'load)
(0000000F 9 252 0		'compile)
(00000012 57 3 0		list)
(00000015 9 251 0		'defparameter)
(00000018 9 250 0		'*VLAReactor-Class-Vector*)
(0000001B 9 249 0		'vector)
(0000001E 5 0		UnVar0)
(00000020 8 1		UnVar1)
(00000022 100 2		UNVar2)
(00000024 15 19 0		JMP 0000003A)
(00000027 5 1		UnVar1)
(00000029 40		car)
(0000002A 81 1 248 0 1 0		kwote)
(00000030 5 2		UnVar2)
(00000032 42		cons)
(00000033 8 2		UnVar2)
(00000035 5 1		UnVar1)
(00000037 41		cdr)
(00000038 8 1		UnVar1)
(0000003A 5 1		UnVar1)
(0000003C 60 232 255		T->JMP 00000027)
(0000003F 5 2		UnVar2)
(00000041 81 1 247 0 1 0		nreverse)
(00000047 42		cons)
(00000048 57 3 0		list)
(0000004B 9 251 0		'defparameter)
(0000004E 9 246 0		'*VLAReactor-Class-Names-Vector*)
(00000051 9 249 0		'vector)
(00000054 5 0		UnVar0)
(00000056 8 1		UnVar1)
(00000058 100 2		UNVar2)
(0000005A 15 32 0		JMP 0000007D)
(0000005D 5 1		UnVar1)
(0000005F 40		car)
(00000060 8 3		UnVar3)
(00000062 9 245 0		":VLR-")
(00000065 5 3		UnVar3)
(00000067 81 2 244 0 1 0		concat)
(0000006D 81 1 243 0 1 0		intern)
(00000073 5 2		UnVar2)
(00000075 42		cons)
(00000076 8 2		UnVar2)
(00000078 5 1		UnVar1)
(0000007A 41		cdr)
(0000007B 8 1		UnVar1)
(0000007D 5 1		UnVar1)
(0000007F 60 219 255		T->JMP 0000005D)
(00000082 5 2		UnVar2)
(00000084 81 1 247 0 1 0		nreverse)
(0000008A 42		cons)
(0000008B 57 3 0		list)
(0000008E 9 251 0		'defparameter)
(00000091 9 242 0		'*VLAReactor-Class-Creators-Vector*)
(00000094 9 249 0		'vector)
(00000097 5 0		UnVar0)
(00000099 8 1		UnVar1)
(0000009B 100 2		UNVar2)
(0000009D 15 23 0		JMP 000000B7)
(000000A0 5 1		UnVar1)
(000000A2 40		car)
(000000A3 8 3		UnVar3)
(000000A5 9 241 0		'function)
(000000A8 5 3		UnVar3)
(000000AA 57 2 0		list)
(000000AD 5 2		UnVar2)
(000000AF 42		cons)
(000000B0 8 2		UnVar2)
(000000B2 5 1		UnVar1)
(000000B4 41		cdr)
(000000B5 8 1		UnVar1)
(000000B7 5 1		UnVar1)
(000000B9 60 228 255		T->JMP 000000A0)
(000000BC 5 2		UnVar2)
(000000BE 81 1 247 0 1 0		nreverse)
(000000C4 42		cons)
(000000C5 57 3 0		list)
(000000C8 57 5 0		list)
(000000CB 22		ret)
;;;def VLR-Reaction-Names 204
(000000CC 20 5 1 1 0)
(000000D1 100 1		UNVar1)
(000000D3 100 2		UNVar2)
(000000D5 5 0		UnVar0)
(000000D7 81 1 240 0 1 0		lpp-sym?)
(000000DD 3 246 0		*VLAReactor-Class-Names-Vector*)
(000000E0 81 2 239 0 1 0		vector-position)
(000000E6 11)
(000000E7 8 2		UnVar2)
(000000E9 60 34 0		T->JMP 0000010E)
(000000EC 5 0		UnVar0)
(000000EE 95 1 186 10 0 0		VL-Reactor-p)
(000000F4 60 23 0		T->JMP 0000010E)
(000000F7 9 238 0		"VLMSG.DLL")
(000000FA 51 120 110 0 0		28280)
(000000FF 81 2 237 0 1 0		string-resource)
(00000105 5 0		UnVar0)
(00000107 81 2 236 0 1 0		_bat-err)
(0000010D 10)
(0000010E 5 2		UnVar2)
(00000110 13 23 0		nil->JMP 0000012A)
(00000113 3 250 0		*VLAReactor-Class-Vector*)
(00000116 5 2		UnVar2)
(00000118 81 2 235 0 1 0		vector-elt)
(0000011E 9 234 0		'Notification-Names)
(00000121 81 2 233 0 1 0		find-class-slot-value)
(00000127 15 8 0		JMP 00000132)
(0000012A 5 0		UnVar0)
(0000012C 95 1 72 9 0 0		get-Notification-Names)
(00000132 8 1		UnVar1)
(00000134 5 1		UnVar1)
(00000136 63		nil->ret)
(00000137 5 1		UnVar1)
(00000139 81 1 232 0 1 0		vector->list)
(0000013F 8 3		UnVar3)
(00000141 100 4		UNVar4)
(00000143 15 19 0		JMP 00000159)
(00000146 5 3		UnVar3)
(00000148 40		car)
(00000149 81 1 231 0 1 0		al-sym?)
(0000014F 5 4		UnVar4)
(00000151 42		cons)
(00000152 8 4		UnVar4)
(00000154 5 3		UnVar3)
(00000156 41		cdr)
(00000157 8 3		UnVar3)
(00000159 5 3		UnVar3)
(0000015B 60 232 255		T->JMP 00000146)
(0000015E 5 4		UnVar4)
(00000160 81 1 247 0 1 0		nreverse)
(00000166 22		ret)
;;;def nil 359
(00000167 20 7 1 1 1)
(0000016C 81 0 230 0 1 0		gensym)
(00000172 8 2		UnVar2)
(00000174 5 0		UnVar0)
(00000176 40		car)
(00000177 8 3		UnVar3)
(00000179 5 0		UnVar0)
(0000017B 41		cdr)
(0000017C 40		car)
(0000017D 8 4		UnVar4)
(0000017F 5 0		UnVar0)
(00000181 41		cdr)
(00000182 41		cdr)
(00000183 40		car)
(00000184 8 5		UnVar5)
(00000186 5 0		UnVar0)
(00000188 41		cdr)
(00000189 41		cdr)
(0000018A 41		cdr)
(0000018B 61 6 0		nil->JMP 00000194)
(0000018E 5 0		UnVar0)
(00000190 41		cdr)
(00000191 41		cdr)
(00000192 41		cdr)
(00000193 40		car)
(00000194 8 6		UnVar6)
(00000196 9 229 0		'let)
(00000199 5 3		UnVar3)
(0000019B 50 0		0)
(0000019D 57 2 0		list)
(000001A0 5 4		UnVar4)
(000001A2 1		nil)
(000001A3 57 2 0		list)
(000001A6 5 2		UnVar2)
(000001A8 9 228 0		'vector-length)
(000001AB 5 5		UnVar5)
(000001AD 57 2 0		list)
(000001B0 57 2 0		list)
(000001B3 57 3 0		list)
(000001B6 9 227 0		'while)
(000001B9 9 226 0		'<&)
(000001BC 5 3		UnVar3)
(000001BE 5 2		UnVar2)
(000001C0 57 3 0		list)
(000001C3 9 225 0		'setq)
(000001C6 5 4		UnVar4)
(000001C8 9 235 0		'vector-elt)
(000001CB 5 5		UnVar5)
(000001CD 5 3		UnVar3)
(000001CF 57 3 0		list)
(000001D2 57 3 0		list)
(000001D5 5 1		UnVar1)
(000001D7 9 225 0		'setq)
(000001DA 5 3		UnVar3)
(000001DC 9 224 0		'1+)
(000001DF 5 3		UnVar3)
(000001E1 57 2 0		list)
(000001E4 57 3 0		list)
(000001E7 57 1 0		list)
(000001EA 81 2 223 0 1 0		append)
(000001F0 81 4 222 0 1 0		list*)
(000001F6 5 6		UnVar6)
(000001F8 57 4 0		list)
(000001FB 22		ret)
;;;def VLR-remove-all 508
(000001FC 20 6 0 0 1)
(00000201 100 1		UNVar1)
(00000203 100 2		UNVar2)
(00000205 9 30 1		'(582 VLR-reactors))
(00000208 5 0		UnVar0)
(0000020A 83		apply)
(0000020B 11)
(0000020C 8 1		UnVar1)
(0000020E 63		nil->ret)
(0000020F 5 1		UnVar1)
(00000211 8 3		UnVar3)
(00000213 100 4		UNVar4)
(00000215 15 38 0		JMP 0000023E)
(00000218 5 3		UnVar3)
(0000021A 40		car)
(0000021B 8 4		UnVar4)
(0000021D 5 3		UnVar3)
(0000021F 41		cdr)
(00000220 8 3		UnVar3)
(00000222 5 4		UnVar4)
(00000224 41		cdr)
(00000225 8 5		UnVar5)
(00000227 15 15 0		JMP 00000239)
(0000022A 5 5		UnVar5)
(0000022C 40		car)
(0000022D 95 1 163 16 0 0		VL-Reactor.remove)
(00000233 10)
(00000234 5 5		UnVar5)
(00000236 41		cdr)
(00000237 8 5		UnVar5)
(00000239 5 5		UnVar5)
(0000023B 60 236 255		T->JMP 0000022A)
(0000023E 5 3		UnVar3)
(00000240 60 213 255		T->JMP 00000218)
(00000243 5 1		UnVar1)
(00000245 22		ret)
;;;def VLR-reactors 582
(00000246 20 6 0 0 1)
(0000024B 100 1		UNVar1)
(0000024D 100 2		UNVar2)
(0000024F 100 3		UNVar3)
(00000251 95 0 62 22 0 0		VL-getRegistrationVector)
(00000257 11)
(00000258 8 1		UnVar1)
(0000025A 63		nil->ret)
(0000025B 5 0		UnVar0)
(0000025D 13 50 0		nil->JMP 00000292)
(00000260 5 0		UnVar0)
(00000262 8 4		UnVar4)
(00000264 100 5		UNVar5)
(00000266 15 33 0		JMP 0000028A)
(00000269 5 4		UnVar4)
(0000026B 40		car)
(0000026C 8 5		UnVar5)
(0000026E 5 4		UnVar4)
(00000270 41		cdr)
(00000271 8 4		UnVar4)
(00000273 5 5		UnVar5)
(00000275 5 1		UnVar1)
(00000277 95 2 154 2 0 0		func 0000029A)
(0000027D 11)
(0000027E 8 2		UnVar2)
(00000280 13 7 0		nil->JMP 0000028A)
(00000283 5 2		UnVar2)
(00000285 5 3		UnVar3)
(00000287 42		cons)
(00000288 8 3		UnVar3)
(0000028A 5 4		UnVar4)
(0000028C 60 218 255		T->JMP 00000269)
(0000028F 5 3		UnVar3)
(00000291 22		ret)
(00000292 5 1		UnVar1)
(00000294 97 1 245 2 0 0		offset 000002F5)
;;;def nil 666
(0000029A 20 4 2 2 0)
(0000029F 100 2		UNVar2)
(000002A1 100 3		UNVar3)
(000002A3 5 0		UnVar0)
(000002A5 81 1 240 0 1 0		lpp-sym?)
(000002AB 3 246 0		*VLAReactor-Class-Names-Vector*)
(000002AE 81 2 239 0 1 0		vector-position)
(000002B4 8 3		UnVar3)
(000002B6 5 3		UnVar3)
(000002B8 13 3 0		nil->JMP 000002BE)
(000002BB 15 23 0		JMP 000002D5)
(000002BE 9 238 0		"VLMSG.DLL")
(000002C1 51 130 110 0 0		28290)
(000002C6 81 2 237 0 1 0		string-resource)
(000002CC 5 0		UnVar0)
(000002CE 81 2 221 0 1 0		_msg-err)
(000002D4 10)
(000002D5 5 1		UnVar1)
(000002D7 5 3		UnVar3)
(000002D9 81 2 235 0 1 0		vector-elt)
(000002DF 8 2		UnVar2)
(000002E1 5 2		UnVar2)
(000002E3 63		nil->ret)
(000002E4 5 0		UnVar0)
(000002E6 81 1 231 0 1 0		al-sym?)
(000002EC 5 2		UnVar2)
(000002EE 42		cons)
(000002EF 22		ret)
;;;def nil 752
(000002F0 20 6 1 1 0)
(000002F5 100 1		UNVar1)
(000002F7 100 2		UNVar2)
(000002F9 50 0		0)
(000002FB 8 3		UnVar3)
(000002FD 100 4		UNVar4)
(000002FF 3 246 0		*VLAReactor-Class-Names-Vector*)
(00000302 81 1 228 0 1 0		vector-length)
(00000308 8 5		UnVar5)
(0000030A 15 50 0		JMP 0000033F)
(0000030D 3 246 0		*VLAReactor-Class-Names-Vector*)
(00000310 5 3		UnVar3)
(00000312 81 2 235 0 1 0		vector-elt)
(00000318 8 4		UnVar4)
(0000031A 5 0		UnVar0)
(0000031C 5 3		UnVar3)
(0000031E 81 2 235 0 1 0		vector-elt)
(00000324 11)
(00000325 8 1		UnVar1)
(00000327 13 16 0		nil->JMP 0000033A)
(0000032A 5 4		UnVar4)
(0000032C 81 1 231 0 1 0		al-sym?)
(00000332 5 1		UnVar1)
(00000334 42		cons)
(00000335 5 2		UnVar2)
(00000337 42		cons)
(00000338 8 2		UnVar2)
(0000033A 5 3		UnVar3)
(0000033C 79		1+)
(0000033D 8 3		UnVar3)
(0000033F 5 3		UnVar3)
(00000341 5 5		UnVar5)
(00000343 76		<)
(00000344 60 198 255		T->JMP 0000030D)
(00000347 5 2		UnVar2)
(00000349 22		ret)
;;;def VLR-beep-reaction 842
(0000034A 20 1 0 0 1)
(0000034F 81 0 220 0 1 0		message-beep)
(00000355 22		ret)
;;;def VLR-trace-reaction 854
(00000356 20 1 0 0 1)
(0000035B 3 219 0		*trace-output*)
(0000035E 81 1 218 0 1 0		fresh-line)
(00000364 10)
(00000365 9 238 0		"VLMSG.DLL")
(00000368 51 242 118 0 0		30450)
(0000036D 81 2 237 0 1 0		string-resource)
(00000373 3 217 0		*reaction-name*)
(00000376 81 1 216 0 1 0		princ-to-string)
(0000037C 5 0		UnVar0)
(0000037E 81 1 215 0 1 0		prin1-to-string)
(00000384 81 3 214 0 1 0		_win-format-message)
(0000038A 3 219 0		*trace-output*)
(0000038D 81 2 213 0 1 0		princ)
(00000393 10)
(00000394 3 219 0		*trace-output*)
(00000397 81 1 212 0 1 0		terpri)
(0000039D 10)
(0000039E 3 219 0		*trace-output*)
(000003A1 81 1 211 0 1 0		force-output)
(000003A7 10)
(000003A8 1		nil)
(000003A9 22		ret)
;;;def VLR-current-reaction-name 938
(000003AA 20 0 0 0 0)
(000003AF 3 217 0		*reaction-name*)
(000003B2 81 1 231 0 1 0		al-sym?)
(000003B8 22		ret)
;;;def VLR-types 953
(000003B9 20 2 0 0 0)
(000003BE 3 246 0		*VLAReactor-Class-Names-Vector*)
(000003C1 81 1 232 0 1 0		vector->list)
(000003C7 8 0		UnVar0)
(000003C9 100 1		UNVar1)
(000003CB 15 19 0		JMP 000003E1)
(000003CE 5 0		UnVar0)
(000003D0 40		car)
(000003D1 81 1 231 0 1 0		al-sym?)
(000003D7 5 1		UnVar1)
(000003D9 42		cons)
(000003DA 8 1		UnVar1)
(000003DC 5 0		UnVar0)
(000003DE 41		cdr)
(000003DF 8 0		UnVar0)
(000003E1 5 0		UnVar0)
(000003E3 60 232 255		T->JMP 000003CE)
(000003E6 5 1		UnVar1)
(000003E8 81 1 247 0 1 0		nreverse)
(000003EE 22		ret)
;;;def nil 1007
(000003EF 20 1 1 1 0)
(000003F4 9 210 0		'defun)
(000003F7 9 209 0		"VLR-")
(000003FA 5 0		UnVar0)
(000003FC 81 2 244 0 1 0		concat)
(00000402 81 1 243 0 1 0		intern)
(00000408 9 208 0		'&optional)
(0000040B 9 207 0		'data)
(0000040E 9 206 0		'fun-alist)
(00000411 9 205 0		'&aux)
(00000414 9 204 0		'reactor)
(00000417 57 5 0		list)
(0000041A 9 203 0		'VL-reactor-set-functions)
(0000041D 9 225 0		'setq)
(00000420 9 204 0		'reactor)
(00000423 5 0		UnVar0)
(00000425 9 202 0		':user-data)
(00000428 9 207 0		'data)
(0000042B 57 3 0		list)
(0000042E 57 3 0		list)
(00000431 9 206 0		'fun-alist)
(00000434 57 3 0		list)
(00000437 9 201 0		'add-reactor)
(0000043A 9 204 0		'reactor)
(0000043D 57 2 0		list)
(00000440 57 5 0		list)
(00000443 22		ret)
;;;def nil 1092
(00000444 20 1 1 1 0)
(00000449 9 210 0		'defun)
(0000044C 9 209 0		"VLR-")
(0000044F 5 0		UnVar0)
(00000451 81 2 244 0 1 0		concat)
(00000457 81 1 243 0 1 0		intern)
(0000045D 9 208 0		'&optional)
(00000460 9 200 0		'owners)
(00000463 9 207 0		'data)
(00000466 9 206 0		'fun-alist)
(00000469 9 205 0		'&aux)
(0000046C 9 204 0		'reactor)
(0000046F 57 6 0		list)
(00000472 9 225 0		'setq)
(00000475 9 204 0		'reactor)
(00000478 5 0		UnVar0)
(0000047A 9 202 0		':user-data)
(0000047D 9 207 0		'data)
(00000480 57 3 0		list)
(00000483 57 3 0		list)
(00000486 9 199 0		'dolist)
(00000489 9 198 0		'el)
(0000048C 9 200 0		'owners)
(0000048F 57 2 0		list)
(00000492 9 197 0		'VLR-Owner-Add)
(00000495 9 204 0		'reactor)
(00000498 9 198 0		'el)
(0000049B 57 3 0		list)
(0000049E 57 3 0		list)
(000004A1 9 201 0		'add-reactor)
(000004A4 9 204 0		'reactor)
(000004A7 57 2 0		list)
(000004AA 9 203 0		'VL-reactor-set-functions)
(000004AD 9 204 0		'reactor)
(000004B0 9 206 0		'fun-alist)
(000004B3 57 3 0		list)
(000004B6 9 204 0		'reactor)
(000004B9 57 8 0		list)
(000004BC 22		ret)
;;;def nil 1213
(000004BD 20 3 0 0 0)
(000004C2 9 255 0		'eval-when)
(000004C5 9 196 0		'(eval load))
(000004C8 3 250 0		*VLAReactor-Class-Vector*)
(000004CB 81 1 232 0 1 0		vector->list)
(000004D1 8 0		UnVar0)
(000004D3 100 1		UNVar1)
(000004D5 15 43 0		JMP 00000503)
(000004D8 5 0		UnVar0)
(000004DA 40		car)
(000004DB 8 2		UnVar2)
(000004DD 5 2		UnVar2)
(000004DF 9 195 0		'Object-Reactor)
(000004E2 38		=)
(000004E3 13 11 0		nil->JMP 000004F1)
(000004E6 9 194 0		'make-an-object-reactor)
(000004E9 5 2		UnVar2)
(000004EB 57 2 0		list)
(000004EE 15 8 0		JMP 000004F9)
(000004F1 9 193 0		'make-a-reactor)
(000004F4 5 2		UnVar2)
(000004F6 57 2 0		list)
(000004F9 5 1		UnVar1)
(000004FB 42		cons)
(000004FC 8 1		UnVar1)
(000004FE 5 0		UnVar0)
(00000500 41		cdr)
(00000501 8 0		UnVar0)
(00000503 5 0		UnVar0)
(00000505 60 208 255		T->JMP 000004D8)
(00000508 5 1		UnVar1)
(0000050A 81 1 247 0 1 0		nreverse)
(00000510 81 3 222 0 1 0		list*)
(00000516 22		ret)
;;;def VLR-Linker-Reactor 1303
(00000517 20 3 0 2 0)
(0000051C 100 2		UNVar2)
(0000051E 9 202 0		':user-data)
(00000521 5 0		UnVar0)
(00000523 95 2 54 31 0 0		Linker-Reactor)
(00000529 11)
(0000052A 8 2		UnVar2)
(0000052C 5 1		UnVar1)
(0000052E 95 2 17 8 0 0		VL-reactor-set-functions)
(00000534 10)
(00000535 5 2		UnVar2)
(00000537 97 1 121 9 0 0		offset 00000979)
;;;def VLR-Editor-Reactor 1341
(0000053D 20 3 0 2 0)
(00000542 100 2		UNVar2)
(00000544 9 202 0		':user-data)
(00000547 5 0		UnVar0)
(00000549 95 2 143 31 0 0		Editor-Reactor)
(0000054F 11)
(00000550 8 2		UnVar2)
(00000552 5 1		UnVar1)
(00000554 95 2 17 8 0 0		VL-reactor-set-functions)
(0000055A 10)
(0000055B 5 2		UnVar2)
(0000055D 97 1 121 9 0 0		offset 00000979)
;;;def VLR-AcDb-Reactor 1379
(00000563 20 3 0 2 0)
(00000568 100 2		UNVar2)
(0000056A 9 202 0		':user-data)
(0000056D 5 0		UnVar0)
(0000056F 95 2 232 31 0 0		AcDb-Reactor)
(00000575 11)
(00000576 8 2		UnVar2)
(00000578 5 1		UnVar1)
(0000057A 95 2 17 8 0 0		VL-reactor-set-functions)
(00000580 10)
(00000581 5 2		UnVar2)
(00000583 97 1 121 9 0 0		offset 00000979)
;;;def VLR-DocManager-Reactor 1417
(00000589 20 3 0 2 0)
(0000058E 100 2		UNVar2)
(00000590 9 202 0		':user-data)
(00000593 5 0		UnVar0)
(00000595 95 2 65 32 0 0		DocManager-Reactor)
(0000059B 11)
(0000059C 8 2		UnVar2)
(0000059E 5 1		UnVar1)
(000005A0 95 2 17 8 0 0		VL-reactor-set-functions)
(000005A6 10)
(000005A7 5 2		UnVar2)
(000005A9 97 1 121 9 0 0		offset 00000979)
;;;def VLR-Command-Reactor 1455
(000005AF 20 3 0 2 0)
(000005B4 100 2		UNVar2)
(000005B6 9 202 0		':user-data)
(000005B9 5 0		UnVar0)
(000005BB 95 2 154 32 0 0		Command-Reactor)
(000005C1 11)
(000005C2 8 2		UnVar2)
(000005C4 5 1		UnVar1)
(000005C6 95 2 17 8 0 0		VL-reactor-set-functions)
(000005CC 10)
(000005CD 5 2		UnVar2)
(000005CF 97 1 121 9 0 0		offset 00000979)
;;;def VLR-Lisp-Reactor 1493
(000005D5 20 3 0 2 0)
(000005DA 100 2		UNVar2)
(000005DC 9 202 0		':user-data)
(000005DF 5 0		UnVar0)
(000005E1 95 2 243 32 0 0		Lisp-Reactor)
(000005E7 11)
(000005E8 8 2		UnVar2)
(000005EA 5 1		UnVar1)
(000005EC 95 2 17 8 0 0		VL-reactor-set-functions)
(000005F2 10)
(000005F3 5 2		UnVar2)
(000005F5 97 1 121 9 0 0		offset 00000979)
;;;def VLR-DXF-Reactor 1531
(000005FB 20 3 0 2 0)
(00000600 100 2		UNVar2)
(00000602 9 202 0		':user-data)
(00000605 5 0		UnVar0)
(00000607 95 2 76 33 0 0		DXF-Reactor)
(0000060D 11)
(0000060E 8 2		UnVar2)
(00000610 5 1		UnVar1)
(00000612 95 2 17 8 0 0		VL-reactor-set-functions)
(00000618 10)
(00000619 5 2		UnVar2)
(0000061B 97 1 121 9 0 0		offset 00000979)
;;;def VLR-DWG-Reactor 1569
(00000621 20 3 0 2 0)
(00000626 100 2		UNVar2)
(00000628 9 202 0		':user-data)
(0000062B 5 0		UnVar0)
(0000062D 95 2 165 33 0 0		DWG-Reactor)
(00000633 11)
(00000634 8 2		UnVar2)
(00000636 5 1		UnVar1)
(00000638 95 2 17 8 0 0		VL-reactor-set-functions)
(0000063E 10)
(0000063F 5 2		UnVar2)
(00000641 97 1 121 9 0 0		offset 00000979)
;;;def VLR-Insert-Reactor 1607
(00000647 20 3 0 2 0)
(0000064C 100 2		UNVar2)
(0000064E 9 202 0		':user-data)
(00000651 5 0		UnVar0)
(00000653 95 2 87 34 0 0		Insert-Reactor)
(00000659 11)
(0000065A 8 2		UnVar2)
(0000065C 5 1		UnVar1)
(0000065E 95 2 17 8 0 0		VL-reactor-set-functions)
(00000664 10)
(00000665 5 2		UnVar2)
(00000667 97 1 121 9 0 0		offset 00000979)
;;;def VLR-Wblock-Reactor 1645
(0000066D 20 3 0 2 0)
(00000672 100 2		UNVar2)
(00000674 9 202 0		':user-data)
(00000677 5 0		UnVar0)
(00000679 95 2 176 34 0 0		Wblock-Reactor)
(0000067F 11)
(00000680 8 2		UnVar2)
(00000682 5 1		UnVar1)
(00000684 95 2 17 8 0 0		VL-reactor-set-functions)
(0000068A 10)
(0000068B 5 2		UnVar2)
(0000068D 97 1 121 9 0 0		offset 00000979)
;;;def VLR-SysVar-Reactor 1683
(00000693 20 3 0 2 0)
(00000698 100 2		UNVar2)
(0000069A 9 202 0		':user-data)
(0000069D 5 0		UnVar0)
(0000069F 95 2 254 33 0 0		SysVar-Reactor)
(000006A5 11)
(000006A6 8 2		UnVar2)
(000006A8 5 1		UnVar1)
(000006AA 95 2 17 8 0 0		VL-reactor-set-functions)
(000006B0 10)
(000006B1 5 2		UnVar2)
(000006B3 97 1 121 9 0 0		offset 00000979)
;;;def VLR-DeepClone-Reactor 1721
(000006B9 20 3 0 2 0)
(000006BE 100 2		UNVar2)
(000006C0 9 202 0		':user-data)
(000006C3 5 0		UnVar0)
(000006C5 95 2 9 35 0 0		DeepClone-Reactor)
(000006CB 11)
(000006CC 8 2		UnVar2)
(000006CE 5 1		UnVar1)
(000006D0 95 2 17 8 0 0		VL-reactor-set-functions)
(000006D6 10)
(000006D7 5 2		UnVar2)
(000006D9 97 1 121 9 0 0		offset 00000979)
;;;def VLR-XREF-Reactor 1759
(000006DF 20 3 0 2 0)
(000006E4 100 2		UNVar2)
(000006E6 9 202 0		':user-data)
(000006E9 5 0		UnVar0)
(000006EB 95 2 98 35 0 0		XREF-Reactor)
(000006F1 11)
(000006F2 8 2		UnVar2)
(000006F4 5 1		UnVar1)
(000006F6 95 2 17 8 0 0		VL-reactor-set-functions)
(000006FC 10)
(000006FD 5 2		UnVar2)
(000006FF 97 1 121 9 0 0		offset 00000979)
;;;def VLR-Undo-Reactor 1797
(00000705 20 3 0 2 0)
(0000070A 100 2		UNVar2)
(0000070C 9 202 0		':user-data)
(0000070F 5 0		UnVar0)
(00000711 95 2 187 35 0 0		Undo-Reactor)
(00000717 11)
(00000718 8 2		UnVar2)
(0000071A 5 1		UnVar1)
(0000071C 95 2 17 8 0 0		VL-reactor-set-functions)
(00000722 10)
(00000723 5 2		UnVar2)
(00000725 97 1 121 9 0 0		offset 00000979)
;;;def VLR-Window-Reactor 1835
(0000072B 20 3 0 2 0)
(00000730 100 2		UNVar2)
(00000732 9 202 0		':user-data)
(00000735 5 0		UnVar0)
(00000737 95 2 198 36 0 0		Window-Reactor)
(0000073D 11)
(0000073E 8 2		UnVar2)
(00000740 5 1		UnVar1)
(00000742 95 2 17 8 0 0		VL-reactor-set-functions)
(00000748 10)
(00000749 5 2		UnVar2)
(0000074B 97 1 121 9 0 0		offset 00000979)
;;;def VLR-Toolbar-Reactor 1873
(00000751 20 3 0 2 0)
(00000756 100 2		UNVar2)
(00000758 9 202 0		':user-data)
(0000075B 5 0		UnVar0)
(0000075D 95 2 20 36 0 0		Toolbar-Reactor)
(00000763 11)
(00000764 8 2		UnVar2)
(00000766 5 1		UnVar1)
(00000768 95 2 17 8 0 0		VL-reactor-set-functions)
(0000076E 10)
(0000076F 5 2		UnVar2)
(00000771 97 1 121 9 0 0		offset 00000979)
;;;def VLR-Mouse-Reactor 1911
(00000777 20 3 0 2 0)
(0000077C 100 2		UNVar2)
(0000077E 9 202 0		':user-data)
(00000781 5 0		UnVar0)
(00000783 95 2 109 36 0 0		Mouse-Reactor)
(00000789 11)
(0000078A 8 2		UnVar2)
(0000078C 5 1		UnVar1)
(0000078E 95 2 17 8 0 0		VL-reactor-set-functions)
(00000794 10)
(00000795 5 2		UnVar2)
(00000797 97 1 121 9 0 0		offset 00000979)
;;;def VLR-Miscellaneous-Reactor 1949
(0000079D 20 3 0 2 0)
(000007A2 100 2		UNVar2)
(000007A4 9 202 0		':user-data)
(000007A7 5 0		UnVar0)
(000007A9 95 2 31 37 0 0		Miscellaneous-Reactor)
(000007AF 11)
(000007B0 8 2		UnVar2)
(000007B2 5 1		UnVar1)
(000007B4 95 2 17 8 0 0		VL-reactor-set-functions)
(000007BA 10)
(000007BB 5 2		UnVar2)
(000007BD 97 1 121 9 0 0		offset 00000979)
;;;def VLR-Object-Reactor 1987
(000007C3 20 6 0 3 0)
(000007C8 100 3		UNVar3)
(000007CA 9 202 0		':user-data)
(000007CD 5 1		UnVar1)
(000007CF 95 2 120 37 0 0		Object-Reactor)
(000007D5 8 3		UnVar3)
(000007D7 5 0		UnVar0)
(000007D9 8 4		UnVar4)
(000007DB 100 5		UNVar5)
(000007DD 15 21 0		JMP 000007F5)
(000007E0 5 4		UnVar4)
(000007E2 40		car)
(000007E3 8 5		UnVar5)
(000007E5 5 4		UnVar4)
(000007E7 41		cdr)
(000007E8 8 4		UnVar4)
(000007EA 5 3		UnVar3)
(000007EC 5 5		UnVar5)
(000007EE 95 2 200 27 0 0		VLR-Owner-Add)
(000007F4 10)
(000007F5 5 4		UnVar4)
(000007F7 60 230 255		T->JMP 000007E0)
(000007FA 5 3		UnVar3)
(000007FC 95 1 116 9 0 0		add-reactor)
(00000802 10)
(00000803 5 3		UnVar3)
(00000805 5 2		UnVar2)
(00000807 95 2 17 8 0 0		VL-reactor-set-functions)
(0000080D 10)
(0000080E 5 3		UnVar3)
(00000810 22		ret)
;;;def VL-reactor-set-functions 2065
(00000811 20 5 2 2 0)
(00000816 5 0		UnVar0)
(00000818 5 1		UnVar1)
(0000081A 8 2		UnVar2)
(0000081C 100 3		UNVar3)
(0000081E 15 34 0		JMP 00000843)
(00000821 5 2		UnVar2)
(00000823 40		car)
(00000824 8 4		UnVar4)
(00000826 5 4		UnVar4)
(00000828 40		car)
(00000829 81 1 240 0 1 0		lpp-sym?)
(0000082F 5 4		UnVar4)
(00000831 41		cdr)
(00000832 81 1 192 0 1 0		string)
(00000838 42		cons)
(00000839 5 3		UnVar3)
(0000083B 42		cons)
(0000083C 8 3		UnVar3)
(0000083E 5 2		UnVar2)
(00000840 41		cdr)
(00000841 8 2		UnVar2)
(00000843 5 2		UnVar2)
(00000845 60 217 255		T->JMP 00000821)
(00000848 5 3		UnVar3)
(0000084A 81 1 247 0 1 0		nreverse)
(00000850 97 2 47 15 0 0		offset 00000F2F)
;;;def VL-create 2134
(00000856 20 5 1 1 1)
(0000085B 100 2		UNVar2)
(0000085D 100 3		UNVar3)
(0000085F 100 4		UNVar4)
(00000861 5 0		UnVar0)
(00000863 81 1 240 0 1 0		lpp-sym?)
(00000869 3 246 0		*VLAReactor-Class-Names-Vector*)
(0000086C 81 2 239 0 1 0		vector-position)
(00000872 11)
(00000873 8 4		UnVar4)
(00000875 13 19 0		nil->JMP 0000088B)
(00000878 3 242 0		*VLAReactor-Class-Creators-Vector*)
(0000087B 5 4		UnVar4)
(0000087D 81 2 235 0 1 0		vector-elt)
(00000883 5 1		UnVar1)
(00000885 83		apply)
(00000886 8 3		UnVar3)
(00000888 15 23 0		JMP 000008A2)
(0000088B 9 238 0		"VLMSG.DLL")
(0000088E 51 210 110 0 0		28370)
(00000893 81 2 237 0 1 0		string-resource)
(00000899 5 0		UnVar0)
(0000089B 81 2 221 0 1 0		_msg-err)
(000008A1 10)
(000008A2 5 3		UnVar3)
(000008A4 9 191 0		"can't create reactor of type")
(000008A7 5 0		UnVar0)
(000008A9 53 3 190 0 1 32		assert)
(000008AF 10)
(000008B0 5 0		UnVar0)
(000008B2 5 1		UnVar1)
(000008B4 95 2 207 8 0 0		collect-function-names)
(000008BA 8 2		UnVar2)
(000008BC 5 2		UnVar2)
(000008BE 13 11 0		nil->JMP 000008CC)
(000008C1 5 3		UnVar3)
(000008C3 5 2		UnVar2)
(000008C5 95 2 42 15 0 0		VL-Reactor.reactions-list<-)
(000008CB 10)
(000008CC 5 3		UnVar3)
(000008CE 22		ret)
;;;def collect-function-names 2255
(000008CF 20 2 2 2 0)
(000008D4 5 1		UnVar1)
(000008D6 5 0		UnVar0)
(000008D8 95 1 204 0 0 0		VLR-Reaction-Names)
(000008DE 97 2 233 8 0 0		offset 000008E9)
;;;def nil 2276
(000008E4 20 2 2 2 0)
(000008E9 5 0		UnVar0)
(000008EB 63		nil->ret)
(000008EC 5 0		UnVar0)
(000008EE 40		car)
(000008EF 5 1		UnVar1)
(000008F1 81 2 189 0 1 0		member)
(000008F7 13 22 0		nil->JMP 00000910)
(000008FA 5 0		UnVar0)
(000008FC 40		car)
(000008FD 5 0		UnVar0)
(000008FF 41		cdr)
(00000900 40		car)
(00000901 42		cons)
(00000902 5 0		UnVar0)
(00000904 41		cdr)
(00000905 41		cdr)
(00000906 5 1		UnVar1)
(00000908 95 2 228 8 0 0		func 000008E4)
(0000090E 42		cons)
(0000090F 22		ret)
(00000910 5 0		UnVar0)
(00000912 41		cdr)
(00000913 41		cdr)
(00000914 5 1		UnVar1)
(00000916 97 2 233 8 0 0		offset 000008E9)
;;;def get-Type 2332
(0000091C 20 2 1 1 0)
(00000921 9 188 0		'get-Type)
(00000924 5 0		UnVar0)
(00000926 81 2 187 0 1 0		compute-applicable-methods)
(0000092C 8 1		UnVar1)
(0000092E 5 1		UnVar1)
(00000930 13 3 0		nil->JMP 00000936)
(00000933 15 12 0		JMP 00000942)
(00000936 9 188 0		'get-Type)
(00000939 5 0		UnVar0)
(0000093B 81 2 186 0 1 0		no-applicable-method)
(00000941 10)
(00000942 5 0		UnVar0)
(00000944 5 1		UnVar1)
(00000946 46 1		invoke+ret)
;;;def get-Notification-Names 2376
(00000948 20 2 1 1 0)
(0000094D 9 185 0		'get-Notification-Names)
(00000950 5 0		UnVar0)
(00000952 81 2 187 0 1 0		compute-applicable-methods)
(00000958 8 1		UnVar1)
(0000095A 5 1		UnVar1)
(0000095C 13 3 0		nil->JMP 00000962)
(0000095F 15 12 0		JMP 0000096E)
(00000962 9 185 0		'get-Notification-Names)
(00000965 5 0		UnVar0)
(00000967 81 2 186 0 1 0		no-applicable-method)
(0000096D 10)
(0000096E 5 0		UnVar0)
(00000970 5 1		UnVar1)
(00000972 46 1		invoke+ret)
;;;def add-reactor 2420
(00000974 20 2 1 1 0)
(00000979 9 201 0		'add-reactor)
(0000097C 5 0		UnVar0)
(0000097E 81 2 187 0 1 0		compute-applicable-methods)
(00000984 8 1		UnVar1)
(00000986 5 1		UnVar1)
(00000988 13 3 0		nil->JMP 0000098E)
(0000098B 15 12 0		JMP 0000099A)
(0000098E 9 201 0		'add-reactor)
(00000991 5 0		UnVar0)
(00000993 81 2 186 0 1 0		no-applicable-method)
(00000999 10)
(0000099A 5 0		UnVar0)
(0000099C 5 1		UnVar1)
(0000099E 46 1		invoke+ret)
;;;def remove-Reactor 2464
(000009A0 20 2 1 1 0)
(000009A5 9 184 0		'remove-Reactor)
(000009A8 5 0		UnVar0)
(000009AA 81 2 187 0 1 0		compute-applicable-methods)
(000009B0 8 1		UnVar1)
(000009B2 5 1		UnVar1)
(000009B4 13 3 0		nil->JMP 000009BA)
(000009B7 15 12 0		JMP 000009C6)
(000009BA 9 184 0		'remove-Reactor)
(000009BD 5 0		UnVar0)
(000009BF 81 2 186 0 1 0		no-applicable-method)
(000009C5 10)
(000009C6 5 0		UnVar0)
(000009C8 5 1		UnVar1)
(000009CA 46 1		invoke+ret)
;;;def Sync-LISP->CPP 2508
(000009CC 20 2 1 1 0)
(000009D1 9 183 0		'Sync-LISP->CPP)
(000009D4 5 0		UnVar0)
(000009D6 81 2 187 0 1 0		compute-applicable-methods)
(000009DC 8 1		UnVar1)
(000009DE 5 1		UnVar1)
(000009E0 13 3 0		nil->JMP 000009E6)
(000009E3 15 12 0		JMP 000009F2)
(000009E6 9 183 0		'Sync-LISP->CPP)
(000009E9 5 0		UnVar0)
(000009EB 81 2 186 0 1 0		no-applicable-method)
(000009F1 10)
(000009F2 5 0		UnVar0)
(000009F4 5 1		UnVar1)
(000009F6 46 1		invoke+ret)
;;;def Reactor-apply 2552
(000009F8 20 3 1 1 1)
(000009FD 100 2		UNVar2)
(000009FF 9 182 0		'*in-Reactor-apply*)
(00000A02 2		T)
(00000A03 24 2 0)
(00000A06 3 181 0		*vlr-reactors-trace-input*)
(00000A09 13 15 0		nil->JMP 00000A1B)
(00000A0C 3 219 0		*trace-output*)
(00000A0F 9 180 0		"~&reaction argument list: ~a~%~!")
(00000A12 5 1		UnVar1)
(00000A14 53 3 179 0 1 32		prinf)
(00000A1A 10)
(00000A1B 9 178 0		'Reactor-apply)
(00000A1E 5 0		UnVar0)
(00000A20 81 2 187 0 1 0		compute-applicable-methods)
(00000A26 11)
(00000A27 8 2		UnVar2)
(00000A29 13 3 0		nil->JMP 00000A2F)
(00000A2C 15 18 0		JMP 00000A41)
(00000A2F 9 186 0		'no-applicable-method)
(00000A32 9 178 0		'Reactor-apply)
(00000A35 5 0		UnVar0)
(00000A37 5 1		UnVar1)
(00000A39 81 3 222 0 1 0		list*)
(00000A3F 83		apply)
(00000A40 10)
(00000A41 5 2		UnVar2)
(00000A43 5 0		UnVar0)
(00000A45 5 1		UnVar1)
(00000A47 42		cons)
(00000A48 83		apply)
(00000A49 25 1 0)
(00000A4C 22		ret)
;;;def check-VL-Reactor 2637
(00000A4D 20 1 1 1 0)
(00000A52 5 0		UnVar0)
(00000A54 95 1 186 10 0 0		VL-Reactor-p)
(00000A5A 13 3 0		nil->JMP 00000A60)
(00000A5D 5 0		UnVar0)
(00000A5F 22		ret)
(00000A60 9 177 0		"VLReactor:")
(00000A63 5 0		UnVar0)
(00000A65 81 2 236 0 1 0		_bat-err)
(00000A6B 22		ret)
;;;def VLR-Add 2668
(00000A6C 20 1 1 1 0)
(00000A71 5 0		UnVar0)
(00000A73 95 1 77 10 0 0		check-VL-Reactor)
(00000A79 96 1 116 9 0 0		add-reactor)
;;;def VLR-Remove 2687
(00000A7F 20 1 1 1 0)
(00000A84 5 0		UnVar0)
(00000A86 95 1 77 10 0 0		check-VL-Reactor)
(00000A8C 96 1 160 9 0 0		remove-Reactor)
;;;def VLR-Type 2706
(00000A92 20 2 1 1 0)
(00000A97 100 1		UNVar1)
(00000A99 5 0		UnVar0)
(00000A9B 95 1 77 10 0 0		check-VL-Reactor)
(00000AA1 10)
(00000AA2 3 246 0		*VLAReactor-Class-Names-Vector*)
(00000AA5 5 0		UnVar0)
(00000AA7 95 1 28 9 0 0		get-Type)
(00000AAD 81 2 235 0 1 0		vector-elt)
(00000AB3 81 1 231 0 1 0		al-sym?)
(00000AB9 22		ret)
;;;def VL-Reactor-p 2746
(00000ABA 20 1 1 1 0)
(00000ABF 5 0		UnVar0)
(00000AC1 9 176 0		'VL-Reactor)
(00000AC4 47 2 175 0 32 32		typep)
;;;def VL-Reactor.new-instance 2762
(00000ACA 20 9 1 1 1)
(00000ACF 5 1		UnVar1)
(00000AD1 8 2		UnVar2)
(00000AD3 5 2		UnVar2)
(00000AD5 9 174 0		':range)
(00000AD8 50 0		0)
(00000ADA 81 3 173 0 1 0		getf)
(00000AE0 8 3		UnVar3)
(00000AE2 5 2		UnVar2)
(00000AE4 9 202 0		':user-data)
(00000AE7 1		nil)
(00000AE8 81 3 173 0 1 0		getf)
(00000AEE 8 4		UnVar4)
(00000AF0 5 2		UnVar2)
(00000AF2 9 172 0		':Function-Names)
(00000AF5 1		nil)
(00000AF6 81 3 173 0 1 0		getf)
(00000AFC 8 5		UnVar5)
(00000AFE 5 2		UnVar2)
(00000B00 9 171 0		':INDEX)
(00000B03 50 255		-1)
(00000B05 81 3 173 0 1 0		getf)
(00000B0B 8 6		UnVar6)
(00000B0D 5 2		UnVar2)
(00000B0F 9 170 0		':lisplet-reference)
(00000B12 1		nil)
(00000B13 81 3 173 0 1 0		getf)
(00000B19 8 7		UnVar7)
(00000B1B 5 0		UnVar0)
(00000B1D 8 8		UnVar8)
(00000B1F 5 3		UnVar3)
(00000B21 13 14 0		nil->JMP 00000B32)
(00000B24 5 8		UnVar8)
(00000B26 5 3		UnVar3)
(00000B28 9 169 0		'range)
(00000B2B 81 3 168 0 1 0		slot-value<-)
(00000B31 10)
(00000B32 5 4		UnVar4)
(00000B34 13 14 0		nil->JMP 00000B45)
(00000B37 5 8		UnVar8)
(00000B39 5 4		UnVar4)
(00000B3B 9 167 0		'user-data)
(00000B3E 81 3 168 0 1 0		slot-value<-)
(00000B44 10)
(00000B45 5 5		UnVar5)
(00000B47 13 14 0		nil->JMP 00000B58)
(00000B4A 5 8		UnVar8)
(00000B4C 5 5		UnVar5)
(00000B4E 9 166 0		'Function-Names)
(00000B51 81 3 168 0 1 0		slot-value<-)
(00000B57 10)
(00000B58 5 6		UnVar6)
(00000B5A 13 14 0		nil->JMP 00000B6B)
(00000B5D 5 8		UnVar8)
(00000B5F 5 6		UnVar6)
(00000B61 9 165 0		'index)
(00000B64 81 3 168 0 1 0		slot-value<-)
(00000B6A 10)
(00000B6B 5 7		UnVar7)
(00000B6D 13 14 0		nil->JMP 00000B7E)
(00000B70 5 8		UnVar8)
(00000B72 5 7		UnVar7)
(00000B74 9 164 0		'lisplet-reference)
(00000B77 81 3 168 0 1 0		slot-value<-)
(00000B7D 10)
(00000B7E 5 0		UnVar0)
(00000B80 22		ret)
;;;def VL-Reactor.print-object 2945
(00000B81 20 4 1 2 0)
(00000B86 100 2		UNVar2)
(00000B88 100 3		UNVar3)
(00000B8A 9 163 0		"#<")
(00000B8D 5 1		UnVar1)
(00000B8F 81 2 213 0 1 0		princ)
(00000B95 10)
(00000B96 3 162 0		%al-print%)
(00000B99 13 20 0		nil->JMP 00000BB0)
(00000B9C 5 0		UnVar0)
(00000B9E 53 1 161 0 1 32		as:type)
(00000BA4 5 1		UnVar1)
(00000BA6 81 2 213 0 1 0		princ)
(00000BAC 10)
(00000BAD 15 11 0		JMP 00000BBB)
(00000BB0 5 0		UnVar0)
(00000BB2 5 1		UnVar1)
(00000BB4 81 2 160 0 1 0		_print-object-hdr)
(00000BBA 10)
(00000BBB 9 159 0		">")
(00000BBE 5 1		UnVar1)
(00000BC0 81 2 213 0 1 0		princ)
(00000BC6 10)
(00000BC7 5 0		UnVar0)
(00000BC9 22		ret)
;;;def VL-Reactor.axvlo-dump 3018
(00000BCA 20 1 1 1 0)
(00000BCF 5 0		UnVar0)
(00000BD1 95 1 71 14 0 0		VL-Reactor.reactions-list)
(00000BD7 5 0		UnVar0)
(00000BD9 9 167 0		'user-data)
(00000BDC 81 2 158 0 1 0		slot-value)
(00000BE2 5 0		UnVar0)
(00000BE4 9 169 0		'range)
(00000BE7 81 2 158 0 1 0		slot-value)
(00000BED 5 0		UnVar0)
(00000BEF 9 164 0		'lisplet-reference)
(00000BF2 81 2 158 0 1 0		slot-value)
(00000BF8 61 1 0		nil->JMP 00000BFC)
(00000BFB 2		T)
(00000BFC 57 4 0		list)
(00000BFF 22		ret)
;;;def VL-Reactor.axvlo-restore 3072
(00000C00 20 3 2 3 0)
(00000C05 5 0		UnVar0)
(00000C07 95 1 121 12 0 0		VL-Reactor.init)
(00000C0D 10)
(00000C0E 5 0		UnVar0)
(00000C10 5 1		UnVar1)
(00000C12 40		car)
(00000C13 95 2 42 15 0 0		VL-Reactor.reactions-list<-)
(00000C19 10)
(00000C1A 5 0		UnVar0)
(00000C1C 5 1		UnVar1)
(00000C1E 41		cdr)
(00000C1F 40		car)
(00000C20 9 167 0		'user-data)
(00000C23 81 3 168 0 1 0		slot-value<-)
(00000C29 10)
(00000C2A 5 0		UnVar0)
(00000C2C 5 1		UnVar1)
(00000C2E 41		cdr)
(00000C2F 41		cdr)
(00000C30 40		car)
(00000C31 9 169 0		'range)
(00000C34 81 3 168 0 1 0		slot-value<-)
(00000C3A 10)
(00000C3B 5 0		UnVar0)
(00000C3D 5 1		UnVar1)
(00000C3F 41		cdr)
(00000C40 41		cdr)
(00000C41 41		cdr)
(00000C42 40		car)
(00000C43 9 164 0		'lisplet-reference)
(00000C46 81 3 168 0 1 0		slot-value<-)
(00000C4C 10)
(00000C4D 5 0		UnVar0)
(00000C4F 9 164 0		'lisplet-reference)
(00000C52 81 2 158 0 1 0		slot-value)
(00000C58 13 18 0		nil->JMP 00000C6D)
(00000C5B 5 0		UnVar0)
(00000C5D 53 0 157 0 1 32		get-lisplet-reference)
(00000C63 9 164 0		'lisplet-reference)
(00000C66 81 3 168 0 1 0		slot-value<-)
(00000C6C 10)
(00000C6D 5 0		UnVar0)
(00000C6F 95 1 116 9 0 0		add-reactor)
(00000C75 10)
(00000C76 5 0		UnVar0)
(00000C78 22		ret)
;;;def VL-Reactor.init 3193
(00000C79 20 3 1 1 0)
(00000C7E 100 1		UNVar1)
(00000C80 5 0		UnVar0)
(00000C82 8 2		UnVar2)
(00000C84 5 2		UnVar2)
(00000C86 1		nil)
(00000C87 9 166 0		'Function-Names)
(00000C8A 81 3 168 0 1 0		slot-value<-)
(00000C90 10)
(00000C91 5 2		UnVar2)
(00000C93 50 255		-1)
(00000C95 9 165 0		'index)
(00000C98 81 3 168 0 1 0		slot-value<-)
(00000C9E 10)
(00000C9F 5 2		UnVar2)
(00000CA1 1		nil)
(00000CA2 9 167 0		'user-data)
(00000CA5 81 3 168 0 1 0		slot-value<-)
(00000CAB 10)
(00000CAC 5 2		UnVar2)
(00000CAE 50 0		0)
(00000CB0 9 169 0		'range)
(00000CB3 81 3 168 0 1 0		slot-value<-)
(00000CB9 10)
(00000CBA 5 2		UnVar2)
(00000CBC 1		nil)
(00000CBD 9 164 0		'lisplet-reference)
(00000CC0 81 3 168 0 1 0		slot-value<-)
(00000CC6 22		ret)
;;;def VL-Reactor._Reactor-apply 3271
(00000CC7 20 3 3 3 0)
(00000CCC 5 1		UnVar1)
(00000CCE 37 4		stringp)
(00000CD0 13 12 0		nil->JMP 00000CDF)
(00000CD3 5 0		UnVar0)
(00000CD5 5 1		UnVar1)
(00000CD7 5 2		UnVar2)
(00000CD9 47 3 156 0 32 32		_lisplet-reference-apply)
(00000CDF 5 1		UnVar1)
(00000CE1 37 3		symbolp)
(00000CE3 13 5 0		nil->JMP 00000CEB)
(00000CE6 5 1		UnVar1)
(00000CE8 5 2		UnVar2)
(00000CEA 84		apply+ret)
(00000CEB 9 238 0		"VLMSG.DLL")
(00000CEE 51 220 110 0 0		28380)
(00000CF3 81 2 237 0 1 0		string-resource)
(00000CF9 5 1		UnVar1)
(00000CFB 81 2 221 0 1 0		_msg-err)
(00000D01 22		ret)
;;;def VL-Reactor.Reactor-apply 3330
(00000D02 20 4 2 2 1)
(00000D07 100 3		UNVar3)
(00000D09 9 217 0		'*reaction-name*)
(00000D0C 5 0		UnVar0)
(00000D0E 5 1		UnVar1)
(00000D10 95 2 242 13 0 0		VL-Reactor.index->Reaction-name)
(00000D16 24 2 0)
(00000D19 5 0		UnVar0)
(00000D1B 5 1		UnVar1)
(00000D1D 95 2 146 13 0 0		VL-Reactor.index->function)
(00000D23 8 3		UnVar3)
(00000D25 5 0		UnVar0)
(00000D27 9 164 0		'lisplet-reference)
(00000D2A 81 2 158 0 1 0		slot-value)
(00000D30 5 3		UnVar3)
(00000D32 5 0		UnVar0)
(00000D34 5 2		UnVar2)
(00000D36 57 2 0		list)
(00000D39 95 3 199 12 0 0		VL-Reactor._Reactor-apply)
(00000D3F 25 1 0)
(00000D42 22		ret)
;;;def VL-Reactor.add-reactor 3395
(00000D43 20 1 1 1 0)
(00000D48 5 0		UnVar0)
(00000D4A 96 1 172 15 0 0		VL-Reactor.add)
;;;def VL-Reactor.remove-Reactor 3408
(00000D50 20 1 1 1 0)
(00000D55 5 0		UnVar0)
(00000D57 96 1 163 16 0 0		VL-Reactor.remove)
;;;def VL-Reactor.max-reaction-number 3421
(00000D5D 20 1 1 1 0)
(00000D62 5 0		UnVar0)
(00000D64 95 1 72 9 0 0		get-Notification-Names)
(00000D6A 81 1 228 0 1 0		vector-length)
(00000D70 22		ret)
;;;def VL-Reactor.reaction-number-valid-p 3441
(00000D71 20 3 2 2 0)
(00000D76 50 0		0)
(00000D78 5 1		UnVar1)
(00000D7A 78		<=)
(00000D7B 63		nil->ret)
(00000D7C 5 1		UnVar1)
(00000D7E 5 0		UnVar0)
(00000D80 8 2		UnVar2)
(00000D82 5 2		UnVar2)
(00000D84 95 1 72 9 0 0		get-Notification-Names)
(00000D8A 81 1 228 0 1 0		vector-length)
(00000D90 76		<)
(00000D91 22		ret)
;;;def VL-Reactor.index->function 3474
(00000D92 20 4 2 2 0)
(00000D97 100 2		UNVar2)
(00000D99 5 0		UnVar0)
(00000D9B 8 3		UnVar3)
(00000D9D 5 1		UnVar1)
(00000D9F 5 3		UnVar3)
(00000DA1 9 166 0		'Function-Names)
(00000DA4 81 2 158 0 1 0		slot-value)
(00000DAA 81 2 155 0 1 0		assoc)
(00000DB0 11)
(00000DB1 8 2		UnVar2)
(00000DB3 63		nil->ret)
(00000DB4 5 2		UnVar2)
(00000DB6 41		cdr)
(00000DB7 22		ret)
;;;def VL-Reactor.Reaction-name->index 3512
(00000DB8 20 3 2 3 0)
(00000DBD 5 1		UnVar1)
(00000DBF 81 1 240 0 1 0		lpp-sym?)
(00000DC5 5 0		UnVar0)
(00000DC7 95 1 72 9 0 0		get-Notification-Names)
(00000DCD 81 2 239 0 1 0		vector-position)
(00000DD3 62		T->ret)
(00000DD4 5 2		UnVar2)
(00000DD6 13 2 0		nil->JMP 00000DDB)
(00000DD9 1		nil)
(00000DDA 22		ret)
(00000DDB 9 238 0		"VLMSG.DLL")
(00000DDE 51 230 110 0 0		28390)
(00000DE3 81 2 237 0 1 0		string-resource)
(00000DE9 5 1		UnVar1)
(00000DEB 81 2 221 0 1 0		_msg-err)
(00000DF1 22		ret)
;;;def VL-Reactor.index->Reaction-name 3570
(00000DF2 20 6 2 3 0)
(00000DF7 5 0		UnVar0)
(00000DF9 8 3		UnVar3)
(00000DFB 5 1		UnVar1)
(00000DFD 8 4		UnVar4)
(00000DFF 50 0		0)
(00000E01 5 4		UnVar4)
(00000E03 78		<=)
(00000E04 61 21 0		nil->JMP 00000E1C)
(00000E07 5 4		UnVar4)
(00000E09 5 3		UnVar3)
(00000E0B 8 5		UnVar5)
(00000E0D 5 5		UnVar5)
(00000E0F 95 1 72 9 0 0		get-Notification-Names)
(00000E15 81 1 228 0 1 0		vector-length)
(00000E1B 76		<)
(00000E1C 13 17 0		nil->JMP 00000E30)
(00000E1F 5 0		UnVar0)
(00000E21 95 1 72 9 0 0		get-Notification-Names)
(00000E27 5 1		UnVar1)
(00000E29 81 2 235 0 1 0		vector-elt)
(00000E2F 22		ret)
(00000E30 9 238 0		"VLMSG.DLL")
(00000E33 51 240 110 0 0		28400)
(00000E38 81 2 237 0 1 0		string-resource)
(00000E3E 5 1		UnVar1)
(00000E40 81 2 221 0 1 0		_msg-err)
(00000E46 22		ret)
;;;def VL-Reactor.reactions-list 3655
(00000E47 20 10 1 1 0)
(00000E4C 100 1		UNVar1)
(00000E4E 100 2		UNVar2)
(00000E50 100 3		UNVar3)
(00000E52 5 0		UnVar0)
(00000E54 8 4		UnVar4)
(00000E56 5 0		UnVar0)
(00000E58 95 1 72 9 0 0		get-Notification-Names)
(00000E5E 8 1		UnVar1)
(00000E60 5 4		UnVar4)
(00000E62 9 166 0		'Function-Names)
(00000E65 81 2 158 0 1 0		slot-value)
(00000E6B 8 5		UnVar5)
(00000E6D 100 6		UNVar6)
(00000E6F 15 80 0		JMP 00000EC2)
(00000E72 5 5		UnVar5)
(00000E74 40		car)
(00000E75 8 6		UnVar6)
(00000E77 5 5		UnVar5)
(00000E79 41		cdr)
(00000E7A 8 5		UnVar5)
(00000E7C 5 0		UnVar0)
(00000E7E 8 7		UnVar7)
(00000E80 5 6		UnVar6)
(00000E82 40		car)
(00000E83 8 8		UnVar8)
(00000E85 50 0		0)
(00000E87 5 8		UnVar8)
(00000E89 78		<=)
(00000E8A 61 21 0		nil->JMP 00000EA2)
(00000E8D 5 8		UnVar8)
(00000E8F 5 7		UnVar7)
(00000E91 8 9		UnVar9)
(00000E93 5 9		UnVar9)
(00000E95 95 1 72 9 0 0		get-Notification-Names)
(00000E9B 81 1 228 0 1 0		vector-length)
(00000EA1 76		<)
(00000EA2 9 154 0		"Index out of range")
(00000EA5 5 6		UnVar6)
(00000EA7 53 3 190 0 1 32		assert)
(00000EAD 10)
(00000EAE 5 1		UnVar1)
(00000EB0 5 6		UnVar6)
(00000EB2 40		car)
(00000EB3 81 2 235 0 1 0		vector-elt)
(00000EB9 5 6		UnVar6)
(00000EBB 41		cdr)
(00000EBC 42		cons)
(00000EBD 5 2		UnVar2)
(00000EBF 42		cons)
(00000EC0 8 2		UnVar2)
(00000EC2 5 5		UnVar5)
(00000EC4 60 171 255		T->JMP 00000E72)
(00000EC7 5 2		UnVar2)
(00000EC9 81 1 247 0 1 0		nreverse)
(00000ECF 22		ret)
;;;def VLR-Reactions 3792
(00000ED0 20 4 1 1 0)
(00000ED5 5 0		UnVar0)
(00000ED7 95 1 77 10 0 0		check-VL-Reactor)
(00000EDD 95 1 71 14 0 0		VL-Reactor.reactions-list)
(00000EE3 8 1		UnVar1)
(00000EE5 100 2		UNVar2)
(00000EE7 15 50 0		JMP 00000F1C)
(00000EEA 5 1		UnVar1)
(00000EEC 40		car)
(00000EED 8 3		UnVar3)
(00000EEF 5 3		UnVar3)
(00000EF1 41		cdr)
(00000EF2 37 4		stringp)
(00000EF4 13 25 0		nil->JMP 00000F10)
(00000EF7 5 3		UnVar3)
(00000EF9 40		car)
(00000EFA 81 1 231 0 1 0		al-sym?)
(00000F00 5 3		UnVar3)
(00000F02 41		cdr)
(00000F03 9 153 0		':AUTOLISP)
(00000F06 81 2 243 0 1 0		intern)
(00000F0C 42		cons)
(00000F0D 15 2 0		JMP 00000F12)
(00000F10 5 3		UnVar3)
(00000F12 5 2		UnVar2)
(00000F14 42		cons)
(00000F15 8 2		UnVar2)
(00000F17 5 1		UnVar1)
(00000F19 41		cdr)
(00000F1A 8 1		UnVar1)
(00000F1C 5 1		UnVar1)
(00000F1E 60 201 255		T->JMP 00000EEA)
(00000F21 5 2		UnVar2)
(00000F23 81 1 247 0 1 0		nreverse)
(00000F29 22		ret)
;;;def VL-Reactor.reactions-list<- 3882
(00000F2A 20 4 2 2 0)
(00000F2F 5 1		UnVar1)
(00000F31 8 2		UnVar2)
(00000F33 100 3		UNVar3)
(00000F35 15 25 0		JMP 00000F51)
(00000F38 5 2		UnVar2)
(00000F3A 40		car)
(00000F3B 8 3		UnVar3)
(00000F3D 5 2		UnVar2)
(00000F3F 41		cdr)
(00000F40 8 2		UnVar2)
(00000F42 5 0		UnVar0)
(00000F44 5 3		UnVar3)
(00000F46 40		car)
(00000F47 5 3		UnVar3)
(00000F49 41		cdr)
(00000F4A 95 3 244 16 0 0		VLR-Reaction-Set)
(00000F50 10)
(00000F51 5 2		UnVar2)
(00000F53 60 226 255		T->JMP 00000F38)
(00000F56 1		nil)
(00000F57 22		ret)
;;;def VL-Reactor.added-p 3928
(00000F58 20 2 1 1 0)
(00000F5D 5 0		UnVar0)
(00000F5F 8 1		UnVar1)
(00000F61 5 1		UnVar1)
(00000F63 9 165 0		'index)
(00000F66 81 2 158 0 1 0		slot-value)
(00000F6C 50 0		0)
(00000F6E 77		>=)
(00000F6F 22		ret)
;;;def VL-Reactor.check-added-p 3952
(00000F70 20 1 1 1 0)
(00000F75 5 0		UnVar0)
(00000F77 95 1 88 15 0 0		VL-Reactor.added-p)
(00000F7D 13 2 0		nil->JMP 00000F82)
(00000F80 1		nil)
(00000F81 22		ret)
(00000F82 9 238 0		"VLMSG.DLL")
(00000F85 51 250 110 0 0		28410)
(00000F8A 81 2 237 0 1 0		string-resource)
(00000F90 5 0		UnVar0)
(00000F92 81 2 221 0 1 0		_msg-err)
(00000F98 22		ret)
;;;def VLR-added-p 3993
(00000F99 20 1 1 1 0)
(00000F9E 5 0		UnVar0)
(00000FA0 95 1 77 10 0 0		check-VL-Reactor)
(00000FA6 96 1 88 15 0 0		VL-Reactor.added-p)
;;;def VL-Reactor.add 4012
(00000FAC 20 4 1 3 0)
(00000FB1 100 3		UNVar3)
(00000FB3 5 0		UnVar0)
(00000FB5 95 1 88 15 0 0		VL-Reactor.added-p)
(00000FBB 13 2 0		nil->JMP 00000FC0)
(00000FBE 1		nil)
(00000FBF 22		ret)
(00000FC0 5 0		UnVar0)
(00000FC2 95 1 28 9 0 0		get-Type)
(00000FC8 5 0		UnVar0)
(00000FCA 53 2 152 0 1 32		ax:reactor-create)
(00000FD0 8 3		UnVar3)
(00000FD2 5 3		UnVar3)
(00000FD4 13 3 0		nil->JMP 00000FDA)
(00000FD7 15 23 0		JMP 00000FF1)
(00000FDA 9 238 0		"VLMSG.DLL")
(00000FDD 51 4 111 0 0		28420)
(00000FE2 81 2 237 0 1 0		string-resource)
(00000FE8 5 0		UnVar0)
(00000FEA 81 2 221 0 1 0		_msg-err)
(00000FF0 10)
(00000FF1 5 0		UnVar0)
(00000FF3 5 3		UnVar3)
(00000FF5 9 165 0		'index)
(00000FF8 81 3 168 0 1 0		slot-value<-)
(00000FFE 10)
(00000FFF 5 0		UnVar0)
(00001001 5 1		UnVar1)
(00001003 5 2		UnVar2)
(00001005 97 3 16 16 0 0		offset 00001010)
;;;def VL-Reactor.reInit 4107
(0000100B 20 4 1 3 0)
(00001010 100 3		UNVar3)
(00001012 5 0		UnVar0)
(00001014 95 1 88 15 0 0		VL-Reactor.added-p)
(0000101A 63		nil->ret)
(0000101B 5 2		UnVar2)
(0000101D 13 3 0		nil->JMP 00001023)
(00001020 15 9 0		JMP 0000102C)
(00001023 5 0		UnVar0)
(00001025 95 1 83 23 0 0		VL-Reactor._unregistrate)
(0000102B 10)
(0000102C 5 0		UnVar0)
(0000102E 95 1 17 19 0 0		VL-Reactor.All-Slots-LISP->CPP)
(00001034 10)
(00001035 5 1		UnVar1)
(00001037 35		not)
(00001038 13 18 0		nil->JMP 0000104D)
(0000103B 5 0		UnVar0)
(0000103D 53 0 151 0 1 32		get-true-lisplet-ref)
(00001043 9 164 0		'lisplet-reference)
(00001046 81 3 168 0 1 0		slot-value<-)
(0000104C 10)
(0000104D 5 0		UnVar0)
(0000104F 95 1 28 9 0 0		get-Type)
(00001055 11)
(00001056 8 3		UnVar3)
(00001058 5 0		UnVar0)
(0000105A 9 165 0		'index)
(0000105D 81 2 158 0 1 0		slot-value)
(00001063 5 0		UnVar0)
(00001065 9 169 0		'range)
(00001068 81 2 158 0 1 0		slot-value)
(0000106E 53 3 150 0 1 32		ax:reactor-range)
(00001074 10)
(00001075 5 3		UnVar3)
(00001077 5 0		UnVar0)
(00001079 9 165 0		'index)
(0000107C 81 2 158 0 1 0		slot-value)
(00001082 53 0 149 0 1 32		vlAcDoc:getCurrent)
(00001088 53 3 148 0 1 32		ax:reactor-document)
(0000108E 10)
(0000108F 5 2		UnVar2)
(00001091 13 3 0		nil->JMP 00001097)
(00001094 15 9 0		JMP 000010A0)
(00001097 5 0		UnVar0)
(00001099 95 1 250 22 0 0		VL-Reactor._registrate)
(0000109F 10)
(000010A0 5 0		UnVar0)
(000010A2 22		ret)
;;;def VL-Reactor.remove 4259
(000010A3 20 3 1 1 0)
(000010A8 100 1		UNVar1)
(000010AA 5 0		UnVar0)
(000010AC 8 2		UnVar2)
(000010AE 5 0		UnVar0)
(000010B0 95 1 88 15 0 0		VL-Reactor.added-p)
(000010B6 63		nil->ret)
(000010B7 5 0		UnVar0)
(000010B9 95 1 28 9 0 0		get-Type)
(000010BF 5 2		UnVar2)
(000010C1 9 165 0		'index)
(000010C4 81 2 158 0 1 0		slot-value)
(000010CA 53 2 147 0 1 32		ax:reactor-remove)
(000010D0 8 1		UnVar1)
(000010D2 5 1		UnVar1)
(000010D4 13 23 0		nil->JMP 000010EE)
(000010D7 5 2		UnVar2)
(000010D9 50 255		-1)
(000010DB 9 165 0		'index)
(000010DE 81 3 168 0 1 0		slot-value<-)
(000010E4 10)
(000010E5 5 0		UnVar0)
(000010E7 95 1 83 23 0 0		VL-Reactor._unregistrate)
(000010ED 10)
(000010EE 5 1		UnVar1)
(000010F0 63		nil->ret)
(000010F1 5 0		UnVar0)
(000010F3 22		ret)
;;;def VLR-Reaction-Set 4340
(000010F4 20 3 3 3 0)
(000010F9 5 2		UnVar2)
(000010FB 37 3		symbolp)
(000010FD 14 4 0		T->JMP 00001104)
(00001100 5 2		UnVar2)
(00001102 37 4		stringp)
(00001104 13 3 0		nil->JMP 0000110A)
(00001107 15 23 0		JMP 00001121)
(0000110A 9 238 0		"VLMSG.DLL")
(0000110D 51 14 121 0 0		30990)
(00001112 81 2 237 0 1 0		string-resource)
(00001118 5 2		UnVar2)
(0000111A 81 2 221 0 1 0		_msg-err)
(00001120 10)
(00001121 5 2		UnVar2)
(00001123 37 3		symbolp)
(00001125 13 10 0		nil->JMP 00001132)
(00001128 5 2		UnVar2)
(0000112A 81 1 192 0 1 0		string)
(00001130 8 2		UnVar2)
(00001132 5 0		UnVar0)
(00001134 95 1 77 10 0 0		check-VL-Reactor)
(0000113A 5 1		UnVar1)
(0000113C 5 2		UnVar2)
(0000113E 97 3 73 17 0 0		offset 00001149)
;;;def VL-Reactor.Set-Slot 4420
(00001144 20 3 3 3 0)
(00001149 5 0		UnVar0)
(0000114B 5 0		UnVar0)
(0000114D 5 1		UnVar1)
(0000114F 95 2 184 13 0 0		VL-Reactor.Reaction-name->index)
(00001155 5 2		UnVar2)
(00001157 95 3 97 17 0 0		VL-Reactor.Set-Slot-I)
(0000115D 10)
(0000115E 5 2		UnVar2)
(00001160 22		ret)
;;;def VL-Reactor.Set-Slot-I 4449
(00001161 20 8 3 3 0)
(00001166 100 3		UNVar3)
(00001168 5 0		UnVar0)
(0000116A 8 4		UnVar4)
(0000116C 5 0		UnVar0)
(0000116E 8 5		UnVar5)
(00001170 5 1		UnVar1)
(00001172 8 6		UnVar6)
(00001174 50 0		0)
(00001176 5 6		UnVar6)
(00001178 78		<=)
(00001179 61 21 0		nil->JMP 00001191)
(0000117C 5 6		UnVar6)
(0000117E 5 5		UnVar5)
(00001180 8 7		UnVar7)
(00001182 5 7		UnVar7)
(00001184 95 1 72 9 0 0		get-Notification-Names)
(0000118A 81 1 228 0 1 0		vector-length)
(00001190 76		<)
(00001191 9 238 0		"VLMSG.DLL")
(00001194 51 24 111 0 0		28440)
(00001199 81 2 237 0 1 0		string-resource)
(0000119F 5 1		UnVar1)
(000011A1 53 3 190 0 1 32		assert)
(000011A7 10)
(000011A8 5 0		UnVar0)
(000011AA 95 1 88 15 0 0		VL-Reactor.added-p)
(000011B0 13 13 0		nil->JMP 000011C0)
(000011B3 5 0		UnVar0)
(000011B5 5 1		UnVar1)
(000011B7 5 2		UnVar2)
(000011B9 95 3 109 18 0 0		VL-Reactor.Slot-LISP->CPP-I)
(000011BF 10)
(000011C0 5 1		UnVar1)
(000011C2 5 4		UnVar4)
(000011C4 9 166 0		'Function-Names)
(000011C7 81 2 158 0 1 0		slot-value)
(000011CD 81 2 155 0 1 0		assoc)
(000011D3 8 3		UnVar3)
(000011D5 5 2		UnVar2)
(000011D7 13 51 0		nil->JMP 0000120D)
(000011DA 5 3		UnVar3)
(000011DC 13 14 0		nil->JMP 000011ED)
(000011DF 5 3		UnVar3)
(000011E1 5 2		UnVar2)
(000011E3 81 2 146 0 1 0		setcdr)
(000011E9 10)
(000011EA 15 29 0		JMP 0000120A)
(000011ED 5 4		UnVar4)
(000011EF 5 1		UnVar1)
(000011F1 5 2		UnVar2)
(000011F3 42		cons)
(000011F4 5 4		UnVar4)
(000011F6 9 166 0		'Function-Names)
(000011F9 81 2 158 0 1 0		slot-value)
(000011FF 42		cons)
(00001200 9 166 0		'Function-Names)
(00001203 81 3 168 0 1 0		slot-value<-)
(00001209 10)
(0000120A 15 36 0		JMP 00001231)
(0000120D 5 3		UnVar3)
(0000120F 13 31 0		nil->JMP 00001231)
(00001212 5 4		UnVar4)
(00001214 5 3		UnVar3)
(00001216 5 4		UnVar4)
(00001218 9 166 0		'Function-Names)
(0000121B 81 2 158 0 1 0		slot-value)
(00001221 81 2 145 0 1 0		delete)
(00001227 9 166 0		'Function-Names)
(0000122A 81 3 168 0 1 0		slot-value<-)
(00001230 10)
(00001231 5 0		UnVar0)
(00001233 22		ret)
;;;def VL-Reactor.Clear-ALL-Slots 4660
(00001234 20 4 1 1 0)
(00001239 5 0		UnVar0)
(0000123B 8 1		UnVar1)
(0000123D 5 1		UnVar1)
(0000123F 9 166 0		'Function-Names)
(00001242 81 2 158 0 1 0		slot-value)
(00001248 8 2		UnVar2)
(0000124A 100 3		UNVar3)
(0000124C 15 23 0		JMP 00001266)
(0000124F 5 2		UnVar2)
(00001251 40		car)
(00001252 8 3		UnVar3)
(00001254 5 2		UnVar2)
(00001256 41		cdr)
(00001257 8 2		UnVar2)
(00001259 5 0		UnVar0)
(0000125B 5 3		UnVar3)
(0000125D 40		car)
(0000125E 1		nil)
(0000125F 95 3 97 17 0 0		VL-Reactor.Set-Slot-I)
(00001265 10)
(00001266 5 2		UnVar2)
(00001268 60 228 255		T->JMP 0000124F)
(0000126B 1		nil)
(0000126C 22		ret)
;;;def VL-Reactor.Slot-LISP->CPP-I 4717
(0000126D 20 8 3 3 0)
(00001272 100 3		UNVar3)
(00001274 100 4		UNVar4)
(00001276 100 5		UNVar5)
(00001278 100 6		UNVar6)
(0000127A 5 0		UnVar0)
(0000127C 8 7		UnVar7)
(0000127E 5 0		UnVar0)
(00001280 95 1 88 15 0 0		VL-Reactor.added-p)
(00001286 9 144 0		"not yet added to C++")
(00001289 53 2 190 0 1 32		assert)
(0000128F 10)
(00001290 5 0		UnVar0)
(00001292 95 1 28 9 0 0		get-Type)
(00001298 8 5		UnVar5)
(0000129A 5 2		UnVar2)
(0000129C 13 5 0		nil->JMP 000012A4)
(0000129F 50 1		1)
(000012A1 15 2 0		JMP 000012A6)
(000012A4 50 0		0)
(000012A6 8 4		UnVar4)
(000012A8 5 5		UnVar5)
(000012AA 5 7		UnVar7)
(000012AC 9 165 0		'index)
(000012AF 81 2 158 0 1 0		slot-value)
(000012B5 5 1		UnVar1)
(000012B7 5 4		UnVar4)
(000012B9 53 4 143 0 1 32		ax:reactor-slot-set)
(000012BF 8 3		UnVar3)
(000012C1 5 3		UnVar3)
(000012C3 13 3 0		nil->JMP 000012C9)
(000012C6 15 23 0		JMP 000012E0)
(000012C9 9 238 0		"VLMSG.DLL")
(000012CC 51 34 111 0 0		28450)
(000012D1 81 2 237 0 1 0		string-resource)
(000012D7 5 0		UnVar0)
(000012D9 81 2 221 0 1 0		_msg-err)
(000012DF 10)
(000012E0 5 4		UnVar4)
(000012E2 5 5		UnVar5)
(000012E4 5 7		UnVar7)
(000012E6 9 165 0		'index)
(000012E9 81 2 158 0 1 0		slot-value)
(000012EF 5 1		UnVar1)
(000012F1 53 3 142 0 1 32		ax:reactor-slot)
(000012F7 11)
(000012F8 8 6		UnVar6)
(000012FA 81 2 141 0 1 0		=&)
(00001300 9 140 0		"error in writing value to C++ slot")
(00001303 5 4		UnVar4)
(00001305 5 6		UnVar6)
(00001307 53 4 190 0 1 32		assert)
(0000130D 10)
(0000130E 5 0		UnVar0)
(00001310 22		ret)
;;;def VL-Reactor.All-Slots-LISP->CPP 4881
(00001311 20 4 1 1 0)
(00001316 5 0		UnVar0)
(00001318 8 1		UnVar1)
(0000131A 5 1		UnVar1)
(0000131C 9 166 0		'Function-Names)
(0000131F 81 2 158 0 1 0		slot-value)
(00001325 8 2		UnVar2)
(00001327 100 3		UNVar3)
(00001329 15 25 0		JMP 00001345)
(0000132C 5 2		UnVar2)
(0000132E 40		car)
(0000132F 8 3		UnVar3)
(00001331 5 2		UnVar2)
(00001333 41		cdr)
(00001334 8 2		UnVar2)
(00001336 5 0		UnVar0)
(00001338 5 3		UnVar3)
(0000133A 40		car)
(0000133B 5 3		UnVar3)
(0000133D 41		cdr)
(0000133E 95 3 109 18 0 0		VL-Reactor.Slot-LISP->CPP-I)
(00001344 10)
(00001345 5 2		UnVar2)
(00001347 60 226 255		T->JMP 0000132C)
(0000134A 1		nil)
(0000134B 22		ret)
;;;def VL-Reactor.data 4940
(0000134C 20 2 1 1 0)
(00001351 5 0		UnVar0)
(00001353 8 1		UnVar1)
(00001355 5 1		UnVar1)
(00001357 9 167 0		'user-data)
(0000135A 81 2 158 0 1 0		slot-value)
(00001360 22		ret)
;;;def VLR-Data 4961
(00001361 20 1 1 1 0)
(00001366 5 0		UnVar0)
(00001368 95 1 77 10 0 0		check-VL-Reactor)
(0000136E 96 1 76 19 0 0		VL-Reactor.data)
;;;def VL-Reactor.data<- 4980
(00001374 20 3 2 2 0)
(00001379 5 0		UnVar0)
(0000137B 8 2		UnVar2)
(0000137D 5 2		UnVar2)
(0000137F 5 1		UnVar1)
(00001381 9 167 0		'user-data)
(00001384 81 3 168 0 1 0		slot-value<-)
(0000138A 22		ret)
;;;def VLR-Data-Set 5003
(0000138B 20 2 2 2 0)
(00001390 5 0		UnVar0)
(00001392 95 1 77 10 0 0		check-VL-Reactor)
(00001398 5 1		UnVar1)
(0000139A 96 2 116 19 0 0		VL-Reactor.data<-)
;;;def VL-Reactor.range 5024
(000013A0 20 2 1 1 0)
(000013A5 5 0		UnVar0)
(000013A7 8 1		UnVar1)
(000013A9 5 1		UnVar1)
(000013AB 9 165 0		'index)
(000013AE 81 2 158 0 1 0		slot-value)
(000013B4 50 0		0)
(000013B6 77		>=)
(000013B7 63		nil->ret)
(000013B8 5 0		UnVar0)
(000013BA 95 1 28 9 0 0		get-Type)
(000013C0 5 1		UnVar1)
(000013C2 9 165 0		'index)
(000013C5 81 2 158 0 1 0		slot-value)
(000013CB 47 2 150 0 32 32		ax:reactor-range)
;;;def VL-Reactor.range<- 5073
(000013D1 20 3 2 2 0)
(000013D6 5 0		UnVar0)
(000013D8 8 2		UnVar2)
(000013DA 5 2		UnVar2)
(000013DC 9 165 0		'index)
(000013DF 81 2 158 0 1 0		slot-value)
(000013E5 50 0		0)
(000013E7 77		>=)
(000013E8 13 3 0		nil->JMP 000013EE)
(000013EB 15 23 0		JMP 00001405)
(000013EE 9 238 0		"VLMSG.DLL")
(000013F1 51 44 111 0 0		28460)
(000013F6 81 2 237 0 1 0		string-resource)
(000013FC 5 0		UnVar0)
(000013FE 81 2 221 0 1 0		_msg-err)
(00001404 10)
(00001405 5 2		UnVar2)
(00001407 5 1		UnVar1)
(00001409 9 169 0		'range)
(0000140C 81 3 168 0 1 0		slot-value<-)
(00001412 10)
(00001413 5 0		UnVar0)
(00001415 95 1 28 9 0 0		get-Type)
(0000141B 5 2		UnVar2)
(0000141D 9 165 0		'index)
(00001420 81 2 158 0 1 0		slot-value)
(00001426 5 2		UnVar2)
(00001428 9 169 0		'range)
(0000142B 81 2 158 0 1 0		slot-value)
(00001431 47 3 150 0 32 32		ax:reactor-range)
;;;def VLR-notification 5175
(00001437 20 2 1 1 0)
(0000143C 5 0		UnVar0)
(0000143E 95 1 77 10 0 0		check-VL-Reactor)
(00001444 95 1 160 19 0 0		VL-Reactor.range)
(0000144A 8 1		UnVar1)
(0000144C 5 1		UnVar1)
(0000144E 50 0		0)
(00001450 81 2 141 0 1 0		=&)
(00001456 13 6 0		nil->JMP 0000145F)
(00001459 9 139 0		'active-document-only)
(0000145C 15 30 0		JMP 0000147D)
(0000145F 5 1		UnVar1)
(00001461 50 1		1)
(00001463 81 2 141 0 1 0		=&)
(00001469 13 6 0		nil->JMP 00001472)
(0000146C 9 138 0		'all-documents)
(0000146F 15 11 0		JMP 0000147D)
(00001472 9 137 0		"Illegal notification value:")
(00001475 5 1		UnVar1)
(00001477 81 2 221 0 1 0		_msg-err)
(0000147D 81 1 231 0 1 0		al-sym?)
(00001483 22		ret)
;;;def VLR-set-notification 5252
(00001484 20 3 2 2 0)
(00001489 100 2		UNVar2)
(0000148B 5 1		UnVar1)
(0000148D 81 1 240 0 1 0		lpp-sym?)
(00001493 8 2		UnVar2)
(00001495 5 0		UnVar0)
(00001497 95 1 77 10 0 0		check-VL-Reactor)
(0000149D 5 2		UnVar2)
(0000149F 9 139 0		'active-document-only)
(000014A2 38		=)
(000014A3 13 5 0		nil->JMP 000014AB)
(000014A6 50 0		0)
(000014A8 15 25 0		JMP 000014C4)
(000014AB 5 2		UnVar2)
(000014AD 9 138 0		'all-documents)
(000014B0 38		=)
(000014B1 13 5 0		nil->JMP 000014B9)
(000014B4 50 1		1)
(000014B6 15 11 0		JMP 000014C4)
(000014B9 9 136 0		"Incorrect notification value:")
(000014BC 5 2		UnVar2)
(000014BE 81 2 221 0 1 0		_msg-err)
(000014C4 95 2 209 19 0 0		VL-Reactor.range<-)
(000014CA 10)
(000014CB 5 0		UnVar0)
(000014CD 22		ret)
;;;def VL-Reactor.document 5326
(000014CE 20 2 1 1 0)
(000014D3 5 0		UnVar0)
(000014D5 8 1		UnVar1)
(000014D7 5 1		UnVar1)
(000014D9 9 165 0		'index)
(000014DC 81 2 158 0 1 0		slot-value)
(000014E2 50 0		0)
(000014E4 77		>=)
(000014E5 63		nil->ret)
(000014E6 5 0		UnVar0)
(000014E8 95 1 28 9 0 0		get-Type)
(000014EE 5 1		UnVar1)
(000014F0 9 165 0		'index)
(000014F3 81 2 158 0 1 0		slot-value)
(000014F9 47 2 148 0 32 32		ax:reactor-document)
;;;def VL-Reactor.document<- 5375
(000014FF 20 3 2 2 0)
(00001504 5 0		UnVar0)
(00001506 8 2		UnVar2)
(00001508 5 2		UnVar2)
(0000150A 9 165 0		'index)
(0000150D 81 2 158 0 1 0		slot-value)
(00001513 50 0		0)
(00001515 77		>=)
(00001516 13 3 0		nil->JMP 0000151C)
(00001519 15 23 0		JMP 00001533)
(0000151C 9 238 0		"VLMSG.DLL")
(0000151F 51 44 111 0 0		28460)
(00001524 81 2 237 0 1 0		string-resource)
(0000152A 5 0		UnVar0)
(0000152C 81 2 221 0 1 0		_msg-err)
(00001532 10)
(00001533 5 0		UnVar0)
(00001535 95 1 28 9 0 0		get-Type)
(0000153B 5 2		UnVar2)
(0000153D 9 165 0		'index)
(00001540 81 2 158 0 1 0		slot-value)
(00001546 5 1		UnVar1)
(00001548 47 3 148 0 32 32		ax:reactor-document)
;;;def VLR-document 5454
(0000154E 20 1 1 1 0)
(00001553 5 0		UnVar0)
(00001555 95 1 77 10 0 0		check-VL-Reactor)
(0000155B 95 1 206 20 0 0		VL-Reactor.document)
(00001561 47 1 135 0 32 32		vlAcDoc:IDispatch)
;;;def VL-document-Set 5479
(00001567 20 3 2 2 0)
(0000156C 100 2		UNVar2)
(0000156E 5 0		UnVar0)
(00001570 95 1 83 23 0 0		VL-Reactor._unregistrate)
(00001576 10)
(00001577 5 0		UnVar0)
(00001579 95 1 77 10 0 0		check-VL-Reactor)
(0000157F 95 1 206 20 0 0		VL-Reactor.document)
(00001585 8 2		UnVar2)
(00001587 5 0		UnVar0)
(00001589 5 1		UnVar1)
(0000158B 95 2 255 20 0 0		VL-Reactor.document<-)
(00001591 10)
(00001592 5 0		UnVar0)
(00001594 95 1 250 22 0 0		VL-Reactor._registrate)
(0000159A 10)
(0000159B 5 2		UnVar2)
(0000159D 22		ret)
;;;def VL-Reactor.prepare-reactions-list 5534
(0000159E 20 1 1 1 0)
(000015A3 9 134 0		"{Reactions} ")
(000015A6 1		nil)
(000015A7 9 29 1		'(3792 VLR-Reactions))
(000015AA 57 3 0		list)
(000015AD 9 133 0		"{added-p} ")
(000015B0 1		nil)
(000015B1 9 28 1		'(3993 VLR-added-p))
(000015B4 57 3 0		list)
(000015B7 9 132 0		"[Data] ")
(000015BA 2		T)
(000015BB 9 27 1		'(4961 VLR-Data))
(000015BE 9 26 1		'(5003 VLR-Data-Set))
(000015C1 57 4 0		list)
(000015C4 9 238 0		"VLMSG.DLL")
(000015C7 51 70 55 0 0		14150)
(000015CC 81 2 237 0 1 0		string-resource)
(000015D2 1		nil)
(000015D3 9 25 1		'(5175 VLR-notification))
(000015D6 57 3 0		list)
(000015D9 9 238 0		"VLMSG.DLL")
(000015DC 51 80 55 0 0		14160)
(000015E1 81 2 237 0 1 0		string-resource)
(000015E7 1		nil)
(000015E8 9 24 1		'(5454 VLR-document))
(000015EB 57 3 0		list)
(000015EE 57 5 0		list)
(000015F1 22		ret)
;;;def VL-Reactor.inspect-object 5618
(000015F2 20 4 1 3 0)
(000015F7 100 3		UNVar3)
(000015F9 5 0		UnVar0)
(000015FB 5 0		UnVar0)
(000015FD 95 1 158 21 0 0		VL-Reactor.prepare-reactions-list)
(00001603 53 2 131 0 1 32		structure-inspector)
(00001609 8 3		UnVar3)
(0000160B 5 3		UnVar3)
(0000160D 5 1		UnVar1)
(0000160F 5 2		UnVar2)
(00001611 53 3 130 0 1 32		inspector.show)
(00001617 10)
(00001618 5 3		UnVar3)
(0000161A 22		ret)
;;;def nil 5659
(0000161B 20 0 0 0 0)
(00001620 9 129 0		'make-vector)
(00001623 3 246 0		*VLAReactor-Class-Names-Vector*)
(00001626 81 1 228 0 1 0		vector-length)
(0000162C 57 2 0		list)
(0000162F 22		ret)
;;;def VL-makeRegistrationVectorPrototype 5680
(00001630 20 0 0 0 0)
(00001635 50 19		19)
(00001637 81 1 129 0 1 0		make-vector)
(0000163D 22		ret)
;;;def VL-getRegistrationVector 5694
(0000163E 20 3 0 2 0)
(00001643 100 2		UNVar2)
(00001645 5 0		UnVar0)
(00001647 14 6 0		T->JMP 00001650)
(0000164A 53 0 157 0 1 32		get-lisplet-reference)
(00001650 8 0		UnVar0)
(00001652 5 0		UnVar0)
(00001654 3 128 0		*VLAReactor-Registration-ALIST*)
(00001657 81 2 155 0 1 0		assoc)
(0000165D 8 2		UnVar2)
(0000165F 5 2		UnVar2)
(00001661 13 4 0		nil->JMP 00001668)
(00001664 5 2		UnVar2)
(00001666 41		cdr)
(00001667 22		ret)
(00001668 5 1		UnVar1)
(0000166A 13 24 0		nil->JMP 00001685)
(0000166D 5 0		UnVar0)
(0000166F 95 0 48 22 0 0		VL-makeRegistrationVectorPrototype)
(00001675 42		cons)
(00001676 8 2		UnVar2)
(00001678 5 2		UnVar2)
(0000167A 3 128 0		*VLAReactor-Registration-ALIST*)
(0000167D 42		cons)
(0000167E 6 128 0		*VLAReactor-Registration-ALIST*)
(00001681 5 2		UnVar2)
(00001683 41		cdr)
(00001684 22		ret)
(00001685 1		nil)
(00001686 22		ret)
;;;def VL-Reactor.getRegKey 5767
(00001687 20 1 1 1 0)
(0000168C 5 0		UnVar0)
(0000168E 9 164 0		'lisplet-reference)
(00001691 81 2 158 0 1 0		slot-value)
(00001697 62		T->ret)
(00001698 5 0		UnVar0)
(0000169A 96 1 206 20 0 0		VL-Reactor.document)
;;;def VL-Reactor.getDictKey 5792
(000016A0 20 1 1 1 0)
(000016A5 5 0		UnVar0)
(000016A7 9 164 0		'lisplet-reference)
(000016AA 81 2 158 0 1 0		slot-value)
(000016B0 13 17 0		nil->JMP 000016C4)
(000016B3 5 0		UnVar0)
(000016B5 9 164 0		'lisplet-reference)
(000016B8 81 2 158 0 1 0		slot-value)
(000016BE 47 1 127 0 32 32		lisplet-reference->string)
(000016C4 5 0		UnVar0)
(000016C6 95 1 28 9 0 0		get-Type)
(000016CC 81 1 192 0 1 0		string)
(000016D2 22		ret)
;;;def VLR-Reactor.getDictKey 5843
(000016D3 20 1 0 1 0)
(000016D8 5 0		UnVar0)
(000016DA 13 17 0		nil->JMP 000016EE)
(000016DD 5 0		UnVar0)
(000016DF 95 1 77 10 0 0		check-VL-Reactor)
(000016E5 63		nil->ret)
(000016E6 5 0		UnVar0)
(000016E8 97 1 165 22 0 0		offset 000016A5)
(000016EE 53 0 157 0 1 32		get-lisplet-reference)
(000016F4 47 1 127 0 32 32		lisplet-reference->string)
;;;def VL-Reactor._registrate 5882
(000016FA 20 4 1 1 0)
(000016FF 100 1		UNVar1)
(00001701 100 2		UNVar2)
(00001703 100 3		UNVar3)
(00001705 5 0		UnVar0)
(00001707 95 1 28 9 0 0		get-Type)
(0000170D 8 3		UnVar3)
(0000170F 5 0		UnVar0)
(00001711 95 1 135 22 0 0		VL-Reactor.getRegKey)
(00001717 2		T)
(00001718 95 2 62 22 0 0		VL-getRegistrationVector)
(0000171E 8 1		UnVar1)
(00001720 5 1		UnVar1)
(00001722 5 3		UnVar3)
(00001724 81 2 235 0 1 0		vector-elt)
(0000172A 8 2		UnVar2)
(0000172C 5 0		UnVar0)
(0000172E 5 2		UnVar2)
(00001730 81 2 189 0 1 0		member)
(00001736 13 3 0		nil->JMP 0000173C)
(00001739 15 20 0		JMP 00001750)
(0000173C 5 0		UnVar0)
(0000173E 5 2		UnVar2)
(00001740 42		cons)
(00001741 8 2		UnVar2)
(00001743 5 1		UnVar1)
(00001745 5 2		UnVar2)
(00001747 5 3		UnVar3)
(00001749 81 3 126 0 1 0		vector-elt<-)
(0000174F 10)
(00001750 5 2		UnVar2)
(00001752 22		ret)
;;;def VL-Reactor._unregistrate 5971
(00001753 20 4 1 1 0)
(00001758 100 1		UNVar1)
(0000175A 100 2		UNVar2)
(0000175C 100 3		UNVar3)
(0000175E 5 0		UnVar0)
(00001760 95 1 135 22 0 0		VL-Reactor.getRegKey)
(00001766 95 1 62 22 0 0		VL-getRegistrationVector)
(0000176C 8 1		UnVar1)
(0000176E 5 1		UnVar1)
(00001770 63		nil->ret)
(00001771 5 0		UnVar0)
(00001773 95 1 28 9 0 0		get-Type)
(00001779 8 3		UnVar3)
(0000177B 5 0		UnVar0)
(0000177D 5 1		UnVar1)
(0000177F 5 3		UnVar3)
(00001781 81 2 235 0 1 0		vector-elt)
(00001787 81 2 145 0 1 0		delete)
(0000178D 8 2		UnVar2)
(0000178F 5 1		UnVar1)
(00001791 5 2		UnVar2)
(00001793 5 3		UnVar3)
(00001795 81 3 126 0 1 0		vector-elt<-)
(0000179B 22		ret)
;;;def VL-Object-Reactor-p 6044
(0000179C 20 1 1 1 0)
(000017A1 5 0		UnVar0)
(000017A3 9 125 0		'VL-Object-Reactor)
(000017A6 47 2 175 0 32 32		typep)
;;;def VL-Object-Reactor.new-instance 6060
(000017AC 20 5 1 1 1)
(000017B1 5 1		UnVar1)
(000017B3 8 2		UnVar2)
(000017B5 5 2		UnVar2)
(000017B7 9 124 0		':reactor-owners)
(000017BA 1		nil)
(000017BB 81 3 173 0 1 0		getf)
(000017C1 8 3		UnVar3)
(000017C3 5 0		UnVar0)
(000017C5 8 4		UnVar4)
(000017C7 9 23 1		'(2762 VL-Reactor.new-instance))
(000017CA 5 0		UnVar0)
(000017CC 5 1		UnVar1)
(000017CE 42		cons)
(000017CF 83		apply)
(000017D0 10)
(000017D1 5 3		UnVar3)
(000017D3 13 14 0		nil->JMP 000017E4)
(000017D6 5 4		UnVar4)
(000017D8 5 3		UnVar3)
(000017DA 9 123 0		'reactor-owners)
(000017DD 81 3 168 0 1 0		slot-value<-)
(000017E3 10)
(000017E4 5 0		UnVar0)
(000017E6 22		ret)
;;;def VL-Object-Reactor.axvlo-dump 6119
(000017E7 20 4 1 1 0)
(000017EC 5 0		UnVar0)
(000017EE 8 1		UnVar1)
(000017F0 5 0		UnVar0)
(000017F2 95 1 71 14 0 0		VL-Reactor.reactions-list)
(000017F8 5 1		UnVar1)
(000017FA 9 123 0		'reactor-owners)
(000017FD 81 2 158 0 1 0		slot-value)
(00001803 8 2		UnVar2)
(00001805 100 3		UNVar3)
(00001807 15 15 0		JMP 00001819)
(0000180A 5 2		UnVar2)
(0000180C 40		car)
(0000180D 41		cdr)
(0000180E 40		car)
(0000180F 5 3		UnVar3)
(00001811 42		cons)
(00001812 8 3		UnVar3)
(00001814 5 2		UnVar2)
(00001816 41		cdr)
(00001817 8 2		UnVar2)
(00001819 5 2		UnVar2)
(0000181B 60 236 255		T->JMP 0000180A)
(0000181E 5 3		UnVar3)
(00001820 81 1 247 0 1 0		nreverse)
(00001826 5 1		UnVar1)
(00001828 9 167 0		'user-data)
(0000182B 81 2 158 0 1 0		slot-value)
(00001831 5 1		UnVar1)
(00001833 9 169 0		'range)
(00001836 81 2 158 0 1 0		slot-value)
(0000183C 5 1		UnVar1)
(0000183E 9 164 0		'lisplet-reference)
(00001841 81 2 158 0 1 0		slot-value)
(00001847 61 17 0		nil->JMP 0000185B)
(0000184A 5 1		UnVar1)
(0000184C 9 164 0		'lisplet-reference)
(0000184F 81 2 158 0 1 0		slot-value)
(00001855 53 1 122 0 1 32		lisplet-reference-save)
(0000185B 57 5 0		list)
(0000185E 22		ret)
;;;def VL-Object-Reactor.axvlo-restore 6239
(0000185F 20 9 2 3 0)
(00001864 100 3		UNVar3)
(00001866 5 0		UnVar0)
(00001868 8 4		UnVar4)
(0000186A 1		nil)
(0000186B 5 1		UnVar1)
(0000186D 41		cdr)
(0000186E 40		car)
(0000186F 81 2 121 0 1 0		delq)
(00001875 8 5		UnVar5)
(00001877 100 6		UNVar6)
(00001879 15 82 0		JMP 000018CE)
(0000187C 5 5		UnVar5)
(0000187E 40		car)
(0000187F 8 7		UnVar7)
(00001881 100 8		UNVar8)
(00001883 5 7		UnVar7)
(00001885 53 1 120 0 1 32		IDispatchp)
(0000188B 61 8 0		nil->JMP 00001896)
(0000188E 5 7		UnVar7)
(00001890 95 1 220 38 0 0		Idisp/ent->id)
(00001896 8 8		UnVar8)
(00001898 5 8		UnVar8)
(0000189A 81 1 119 0 1 0		fixnump)
(000018A0 13 3 0		nil->JMP 000018A6)
(000018A3 15 23 0		JMP 000018BD)
(000018A6 9 238 0		"VLMSG.DLL")
(000018A9 51 160 110 0 0		28320)
(000018AE 81 2 237 0 1 0		string-resource)
(000018B4 5 7		UnVar7)
(000018B6 81 2 221 0 1 0		_msg-err)
(000018BC 10)
(000018BD 5 8		UnVar8)
(000018BF 5 7		UnVar7)
(000018C1 57 2 0		list)
(000018C4 5 6		UnVar6)
(000018C6 42		cons)
(000018C7 8 6		UnVar6)
(000018C9 5 5		UnVar5)
(000018CB 41		cdr)
(000018CC 8 5		UnVar5)
(000018CE 5 5		UnVar5)
(000018D0 60 169 255		T->JMP 0000187C)
(000018D3 5 6		UnVar6)
(000018D5 81 1 247 0 1 0		nreverse)
(000018DB 8 3		UnVar3)
(000018DD 5 0		UnVar0)
(000018DF 95 1 121 12 0 0		VL-Reactor.init)
(000018E5 10)
(000018E6 5 4		UnVar4)
(000018E8 5 3		UnVar3)
(000018EA 9 123 0		'reactor-owners)
(000018ED 81 3 168 0 1 0		slot-value<-)
(000018F3 10)
(000018F4 5 4		UnVar4)
(000018F6 5 1		UnVar1)
(000018F8 41		cdr)
(000018F9 41		cdr)
(000018FA 40		car)
(000018FB 9 167 0		'user-data)
(000018FE 81 3 168 0 1 0		slot-value<-)
(00001904 10)
(00001905 5 4		UnVar4)
(00001907 5 1		UnVar1)
(00001909 41		cdr)
(0000190A 41		cdr)
(0000190B 41		cdr)
(0000190C 40		car)
(0000190D 9 169 0		'range)
(00001910 81 3 168 0 1 0		slot-value<-)
(00001916 10)
(00001917 5 4		UnVar4)
(00001919 5 1		UnVar1)
(0000191B 41		cdr)
(0000191C 41		cdr)
(0000191D 41		cdr)
(0000191E 41		cdr)
(0000191F 40		car)
(00001920 9 164 0		'lisplet-reference)
(00001923 81 3 168 0 1 0		slot-value<-)
(00001929 10)
(0000192A 5 4		UnVar4)
(0000192C 9 164 0		'lisplet-reference)
(0000192F 81 2 158 0 1 0		slot-value)
(00001935 13 29 0		nil->JMP 00001955)
(00001938 5 4		UnVar4)
(0000193A 5 4		UnVar4)
(0000193C 9 164 0		'lisplet-reference)
(0000193F 81 2 158 0 1 0		slot-value)
(00001945 53 1 118 0 1 32		lisplet-reference-restore)
(0000194B 9 164 0		'lisplet-reference)
(0000194E 81 3 168 0 1 0		slot-value<-)
(00001954 10)
(00001955 5 0		UnVar0)
(00001957 95 1 116 9 0 0		add-reactor)
(0000195D 10)
(0000195E 5 0		UnVar0)
(00001960 5 1		UnVar1)
(00001962 40		car)
(00001963 95 2 42 15 0 0		VL-Reactor.reactions-list<-)
(00001969 10)
(0000196A 5 0		UnVar0)
(0000196C 22		ret)
;;;def VL-Object-Reactor 6509
(0000196D 20 1 0 0 1)
(00001972 9 22 1		'(6060 VL-Object-Reactor.new-instance))
(00001975 9 125 0		'VL-Object-Reactor)
(00001978 53 1 117 0 1 32		allocate-instance)
(0000197E 5 0		UnVar0)
(00001980 42		cons)
(00001981 84		apply+ret)
;;;def VL-Object-Reactor.init 6530
(00001982 20 2 1 1 0)
(00001987 5 0		UnVar0)
(00001989 8 1		UnVar1)
(0000198B 5 0		UnVar0)
(0000198D 95 1 121 12 0 0		VL-Reactor.init)
(00001993 10)
(00001994 5 1		UnVar1)
(00001996 1		nil)
(00001997 9 123 0		'reactor-owners)
(0000199A 81 3 168 0 1 0		slot-value<-)
(000019A0 22		ret)
;;;def VL-Object-Reactor.Reactor-apply 6561
(000019A1 20 6 2 2 1)
(000019A6 100 3		UNVar3)
(000019A8 100 4		UNVar4)
(000019AA 5 0		UnVar0)
(000019AC 8 5		UnVar5)
(000019AE 9 217 0		'*reaction-name*)
(000019B1 5 0		UnVar0)
(000019B3 5 1		UnVar1)
(000019B5 95 2 242 13 0 0		VL-Reactor.index->Reaction-name)
(000019BB 24 2 0)
(000019BE 5 0		UnVar0)
(000019C0 5 1		UnVar1)
(000019C2 95 2 146 13 0 0		VL-Reactor.index->function)
(000019C8 8 3		UnVar3)
(000019CA 5 3		UnVar3)
(000019CC 61 94 0		nil->JMP 00001A2D)
(000019CF 5 2		UnVar2)
(000019D1 40		car)
(000019D2 5 5		UnVar5)
(000019D4 9 123 0		'reactor-owners)
(000019D7 81 2 158 0 1 0		slot-value)
(000019DD 81 2 155 0 1 0		assoc)
(000019E3 11)
(000019E4 8 4		UnVar4)
(000019E6 13 9 0		nil->JMP 000019F2)
(000019E9 5 4		UnVar4)
(000019EB 41		cdr)
(000019EC 40		car)
(000019ED 8 4		UnVar4)
(000019EF 15 21 0		JMP 00001A07)
(000019F2 5 2		UnVar2)
(000019F4 40		car)
(000019F5 8 4		UnVar4)
(000019F7 3 116 0		*ActiveDocument-wcash*)
(000019FA 52 0 1		)
(000019FD 5 4		UnVar4)
(000019FF 53 2 115 0 1 32		vla-ObjectIDToObject)
(00001A05 8 4		UnVar4)
(00001A07 5 4		UnVar4)
(00001A09 61 33 0		nil->JMP 00001A2D)
(00001A0C 5 4		UnVar4)
(00001A0E 5 0		UnVar0)
(00001A10 5 2		UnVar2)
(00001A12 41		cdr)
(00001A13 57 3 0		list)
(00001A16 8 2		UnVar2)
(00001A18 5 5		UnVar5)
(00001A1A 9 164 0		'lisplet-reference)
(00001A1D 81 2 158 0 1 0		slot-value)
(00001A23 5 3		UnVar3)
(00001A25 5 2		UnVar2)
(00001A27 95 3 199 12 0 0		VL-Reactor._Reactor-apply)
(00001A2D 25 1 0)
(00001A30 22		ret)
;;;def VL-Object-Reactor.add-reactor 6705
(00001A31 20 1 1 1 0)
(00001A36 5 0		UnVar0)
(00001A38 96 1 75 26 0 0		VL-Object-Reactor.add)
;;;def VL-Object-Reactor.remove-Reactor 6718
(00001A3E 20 1 1 1 0)
(00001A43 5 0		UnVar0)
(00001A45 96 1 156 26 0 0		VL-Object-Reactor.remove)
;;;def VL-Object-Reactor.add 6731
(00001A4B 20 5 1 1 0)
(00001A50 100 1		UNVar1)
(00001A52 5 0		UnVar0)
(00001A54 8 2		UnVar2)
(00001A56 5 0		UnVar0)
(00001A58 95 1 88 15 0 0		VL-Reactor.added-p)
(00001A5E 13 2 0		nil->JMP 00001A63)
(00001A61 1		nil)
(00001A62 22		ret)
(00001A63 5 0		UnVar0)
(00001A65 95 1 172 15 0 0		VL-Reactor.add)
(00001A6B 10)
(00001A6C 5 2		UnVar2)
(00001A6E 9 123 0		'reactor-owners)
(00001A71 81 2 158 0 1 0		slot-value)
(00001A77 8 3		UnVar3)
(00001A79 100 4		UNVar4)
(00001A7B 15 22 0		JMP 00001A94)
(00001A7E 5 3		UnVar3)
(00001A80 40		car)
(00001A81 8 4		UnVar4)
(00001A83 5 3		UnVar3)
(00001A85 41		cdr)
(00001A86 8 3		UnVar3)
(00001A88 5 0		UnVar0)
(00001A8A 5 4		UnVar4)
(00001A8C 40		car)
(00001A8D 95 2 219 28 0 0		VL-Object-Reactor.add-owner-LISP->CPP)
(00001A93 10)
(00001A94 5 3		UnVar3)
(00001A96 60 229 255		T->JMP 00001A7E)
(00001A99 5 0		UnVar0)
(00001A9B 22		ret)
;;;def VL-Object-Reactor.remove 6812
(00001A9C 20 2 1 1 0)
(00001AA1 5 0		UnVar0)
(00001AA3 8 1		UnVar1)
(00001AA5 5 0		UnVar0)
(00001AA7 96 1 163 16 0 0		VL-Reactor.remove)
;;;def check-Object-reactor 6829
(00001AAD 20 1 1 1 0)
(00001AB2 5 0		UnVar0)
(00001AB4 95 1 156 23 0 0		VL-Object-Reactor-p)
(00001ABA 60 23 0		T->JMP 00001AD4)
(00001ABD 9 238 0		"VLMSG.DLL")
(00001AC0 51 190 110 0 0		28350)
(00001AC5 81 2 237 0 1 0		string-resource)
(00001ACB 5 0		UnVar0)
(00001ACD 81 2 236 0 1 0		_bat-err)
(00001AD3 10)
(00001AD4 5 0		UnVar0)
(00001AD6 22		ret)
;;;def VL-Object-Reactor.find-owner 6871
(00001AD7 20 3 2 2 0)
(00001ADC 5 0		UnVar0)
(00001ADE 8 2		UnVar2)
(00001AE0 5 1		UnVar1)
(00001AE2 5 2		UnVar2)
(00001AE4 9 123 0		'reactor-owners)
(00001AE7 81 2 158 0 1 0		slot-value)
(00001AED 81 2 155 0 1 0		assoc)
(00001AF3 22		ret)
;;;def nil 6900
(00001AF4 20 2 1 1 0)
(00001AF9 100 1		UNVar1)
(00001AFB 5 0		UnVar0)
(00001AFD 53 1 120 0 1 32		IDispatchp)
(00001B03 13 9 0		nil->JMP 00001B0F)
(00001B06 5 0		UnVar0)
(00001B08 2		T)
(00001B09 97 2 225 38 0 0		offset 000026E1)
(00001B0F 9 238 0		"VLMSG.DLL")
(00001B12 51 200 110 0 0		28360)
(00001B17 81 2 237 0 1 0		string-resource)
(00001B1D 5 0		UnVar0)
(00001B1F 81 2 221 0 1 0		_msg-err)
(00001B25 22		ret)
;;;def VL-Object-Reactor.add-owner 6950
(00001B26 20 5 2 2 0)
(00001B2B 100 2		UNVar2)
(00001B2D 100 3		UNVar3)
(00001B2F 5 0		UnVar0)
(00001B31 8 4		UnVar4)
(00001B33 5 1		UnVar1)
(00001B35 95 1 244 26 0 0		func 00001AF4)
(00001B3B 8 2		UnVar2)
(00001B3D 5 0		UnVar0)
(00001B3F 5 2		UnVar2)
(00001B41 95 2 215 26 0 0		VL-Object-Reactor.find-owner)
(00001B47 13 2 0		nil->JMP 00001B4C)
(00001B4A 1		nil)
(00001B4B 22		ret)
(00001B4C 5 2		UnVar2)
(00001B4E 5 1		UnVar1)
(00001B50 57 2 0		list)
(00001B53 8 3		UnVar3)
(00001B55 5 4		UnVar4)
(00001B57 5 3		UnVar3)
(00001B59 5 4		UnVar4)
(00001B5B 9 123 0		'reactor-owners)
(00001B5E 81 2 158 0 1 0		slot-value)
(00001B64 42		cons)
(00001B65 9 123 0		'reactor-owners)
(00001B68 81 3 168 0 1 0		slot-value<-)
(00001B6E 10)
(00001B6F 5 0		UnVar0)
(00001B71 95 1 88 15 0 0		VL-Reactor.added-p)
(00001B77 13 43 0		nil->JMP 00001BA5)
(00001B7A 5 0		UnVar0)
(00001B7C 5 2		UnVar2)
(00001B7E 95 2 219 28 0 0		VL-Object-Reactor.add-owner-LISP->CPP)
(00001B84 13 3 0		nil->JMP 00001B8A)
(00001B87 15 24 0		JMP 00001BA2)
(00001B8A 5 4		UnVar4)
(00001B8C 5 4		UnVar4)
(00001B8E 9 123 0		'reactor-owners)
(00001B91 81 2 158 0 1 0		slot-value)
(00001B97 41		cdr)
(00001B98 9 123 0		'reactor-owners)
(00001B9B 81 3 168 0 1 0		slot-value<-)
(00001BA1 10)
(00001BA2 15 23 0		JMP 00001BBC)
(00001BA5 5 4		UnVar4)
(00001BA7 9 123 0		'reactor-owners)
(00001BAA 81 2 158 0 1 0		slot-value)
(00001BB0 13 9 0		nil->JMP 00001BBC)
(00001BB3 5 0		UnVar0)
(00001BB5 95 1 75 26 0 0		VL-Object-Reactor.add)
(00001BBB 10)
(00001BBC 5 4		UnVar4)
(00001BBE 9 123 0		'reactor-owners)
(00001BC1 81 2 158 0 1 0		slot-value)
(00001BC7 22		ret)
;;;def VLR-Owner-Add 7112
(00001BC8 20 2 2 2 0)
(00001BCD 5 0		UnVar0)
(00001BCF 95 1 173 26 0 0		check-Object-reactor)
(00001BD5 10)
(00001BD6 5 0		UnVar0)
(00001BD8 5 1		UnVar1)
(00001BDA 95 2 38 27 0 0		VL-Object-Reactor.add-owner)
(00001BE0 10)
(00001BE1 5 1		UnVar1)
(00001BE3 22		ret)
;;;def VL-Object-Reactor.remove-owner 7140
(00001BE4 20 6 2 2 0)
(00001BE9 100 2		UNVar2)
(00001BEB 100 3		UNVar3)
(00001BED 100 4		UNVar4)
(00001BEF 5 0		UnVar0)
(00001BF1 8 5		UnVar5)
(00001BF3 5 1		UnVar1)
(00001BF5 95 1 244 26 0 0		func 00001AF4)
(00001BFB 8 4		UnVar4)
(00001BFD 5 0		UnVar0)
(00001BFF 5 4		UnVar4)
(00001C01 95 2 215 26 0 0		VL-Object-Reactor.find-owner)
(00001C07 11)
(00001C08 8 2		UnVar2)
(00001C0A 63		nil->ret)
(00001C0B 2		T)
(00001C0C 8 3		UnVar3)
(00001C0E 5 0		UnVar0)
(00001C10 95 1 88 15 0 0		VL-Reactor.added-p)
(00001C16 13 13 0		nil->JMP 00001C26)
(00001C19 5 0		UnVar0)
(00001C1B 5 2		UnVar2)
(00001C1D 40		car)
(00001C1E 95 2 255 28 0 0		VL-Object-Reactor.remove-owner-LISP->CPP)
(00001C24 8 3		UnVar3)
(00001C26 5 3		UnVar3)
(00001C28 13 31 0		nil->JMP 00001C4A)
(00001C2B 5 5		UnVar5)
(00001C2D 5 2		UnVar2)
(00001C2F 5 5		UnVar5)
(00001C31 9 123 0		'reactor-owners)
(00001C34 81 2 158 0 1 0		slot-value)
(00001C3A 81 2 145 0 1 0		delete)
(00001C40 9 123 0		'reactor-owners)
(00001C43 81 3 168 0 1 0		slot-value<-)
(00001C49 10)
(00001C4A 5 5		UnVar5)
(00001C4C 9 123 0		'reactor-owners)
(00001C4F 81 2 158 0 1 0		slot-value)
(00001C55 13 3 0		nil->JMP 00001C5B)
(00001C58 15 9 0		JMP 00001C64)
(00001C5B 5 0		UnVar0)
(00001C5D 95 1 156 26 0 0		VL-Object-Reactor.remove)
(00001C63 10)
(00001C64 5 5		UnVar5)
(00001C66 9 123 0		'reactor-owners)
(00001C69 81 2 158 0 1 0		slot-value)
(00001C6F 22		ret)
;;;def VLR-Owner-Remove 7280
(00001C70 20 2 2 2 0)
(00001C75 5 0		UnVar0)
(00001C77 95 1 173 26 0 0		check-Object-reactor)
(00001C7D 10)
(00001C7E 5 0		UnVar0)
(00001C80 5 1		UnVar1)
(00001C82 95 2 228 27 0 0		VL-Object-Reactor.remove-owner)
(00001C88 10)
(00001C89 5 1		UnVar1)
(00001C8B 22		ret)
;;;def VL-Object-Reactor.get-owners 7308
(00001C8C 20 2 1 1 0)
(00001C91 5 0		UnVar0)
(00001C93 8 1		UnVar1)
(00001C95 5 1		UnVar1)
(00001C97 9 123 0		'reactor-owners)
(00001C9A 81 2 158 0 1 0		slot-value)
(00001CA0 22		ret)
;;;def VLR-Owners 7329
(00001CA1 20 3 1 1 0)
(00001CA6 5 0		UnVar0)
(00001CA8 95 1 173 26 0 0		check-Object-reactor)
(00001CAE 10)
(00001CAF 5 0		UnVar0)
(00001CB1 95 1 140 28 0 0		VL-Object-Reactor.get-owners)
(00001CB7 8 1		UnVar1)
(00001CB9 100 2		UNVar2)
(00001CBB 15 15 0		JMP 00001CCD)
(00001CBE 5 1		UnVar1)
(00001CC0 40		car)
(00001CC1 41		cdr)
(00001CC2 40		car)
(00001CC3 5 2		UnVar2)
(00001CC5 42		cons)
(00001CC6 8 2		UnVar2)
(00001CC8 5 1		UnVar1)
(00001CCA 41		cdr)
(00001CCB 8 1		UnVar1)
(00001CCD 5 1		UnVar1)
(00001CCF 60 236 255		T->JMP 00001CBE)
(00001CD2 5 2		UnVar2)
(00001CD4 81 1 247 0 1 0		nreverse)
(00001CDA 22		ret)
;;;def VL-Object-Reactor.add-owner-LISP->CPP 7387
(00001CDB 20 3 2 2 0)
(00001CE0 5 0		UnVar0)
(00001CE2 8 2		UnVar2)
(00001CE4 5 0		UnVar0)
(00001CE6 95 1 28 9 0 0		get-Type)
(00001CEC 5 2		UnVar2)
(00001CEE 9 165 0		'index)
(00001CF1 81 2 158 0 1 0		slot-value)
(00001CF7 5 1		UnVar1)
(00001CF9 47 3 114 0 32 32		ax:reactor-add-owner)
;;;def VL-Object-Reactor.remove-owner-LISP->CPP 7423
(00001CFF 20 3 2 2 0)
(00001D04 5 0		UnVar0)
(00001D06 8 2		UnVar2)
(00001D08 5 0		UnVar0)
(00001D0A 95 1 28 9 0 0		get-Type)
(00001D10 5 2		UnVar2)
(00001D12 9 165 0		'index)
(00001D15 81 2 158 0 1 0		slot-value)
(00001D1B 5 1		UnVar1)
(00001D1D 47 3 113 0 32 32		ax:reactor-remove-owner)
;;;def VL-Object-Reactor.prepare-reactions-list 7459
(00001D23 20 1 1 1 0)
(00001D28 9 112 0		"{Owners} ")
(00001D2B 1		nil)
(00001D2C 9 21 1		'(7329 VLR-Owners))
(00001D2F 57 3 0		list)
(00001D32 5 0		UnVar0)
(00001D34 95 1 158 21 0 0		VL-Reactor.prepare-reactions-list)
(00001D3A 42		cons)
(00001D3B 22		ret)
;;;def VL-Object-Reactor.inspect-object 7484
(00001D3C 20 4 1 3 0)
(00001D41 100 3		UNVar3)
(00001D43 5 0		UnVar0)
(00001D45 5 0		UnVar0)
(00001D47 95 1 35 29 0 0		VL-Object-Reactor.prepare-reactions-list)
(00001D4D 53 2 131 0 1 32		structure-inspector)
(00001D53 8 3		UnVar3)
(00001D55 5 3		UnVar3)
(00001D57 5 1		UnVar1)
(00001D59 5 2		UnVar2)
(00001D5B 53 3 130 0 1 32		inspector.show)
(00001D61 10)
(00001D62 5 3		UnVar3)
(00001D64 22		ret)
;;;def nil 7525
(00001D65 20 6 3 3 0)
(00001D6A 9 255 0		'eval-when)
(00001D6D 9 254 0		'eval)
(00001D70 9 253 0		'load)
(00001D73 57 2 0		list)
(00001D76 9 111 0		'defclass)
(00001D79 5 1		UnVar1)
(00001D7B 5 0		UnVar0)
(00001D7D 57 1 0		list)
(00001D80 9 110 0		':SLOTS)
(00001D83 57 1 0		list)
(00001D86 9 109 0		':CLASS-SLOT)
(00001D89 9 108 0		'reactor-type)
(00001D8C 9 107 0		':TYPE)
(00001D8F 9 106 0		'fixnum)
(00001D92 57 1 0		list)
(00001D95 9 105 0		':INITFORM)
(00001D98 5 1		UnVar1)
(00001D9A 3 250 0		*VLAReactor-Class-Vector*)
(00001D9D 81 2 239 0 1 0		vector-position)
(00001DA3 9 104 0		':DOCUMENTATION)
(00001DA6 9 103 0		"type of this reactors")
(00001DA9 57 8 0		list)
(00001DAC 9 109 0		':CLASS-SLOT)
(00001DAF 9 234 0		'Notification-Names)
(00001DB2 9 105 0		':INITFORM)
(00001DB5 9 249 0		'vector)
(00001DB8 5 2		UnVar2)
(00001DBA 53 1 254 0 1 32		eval)
(00001DC0 8 3		UnVar3)
(00001DC2 100 4		UNVar4)
(00001DC4 15 32 0		JMP 00001DE7)
(00001DC7 5 3		UnVar3)
(00001DC9 40		car)
(00001DCA 8 5		UnVar5)
(00001DCC 9 245 0		":VLR-")
(00001DCF 5 5		UnVar5)
(00001DD1 81 2 244 0 1 0		concat)
(00001DD7 81 1 243 0 1 0		intern)
(00001DDD 5 4		UnVar4)
(00001DDF 42		cons)
(00001DE0 8 4		UnVar4)
(00001DE2 5 3		UnVar3)
(00001DE4 41		cdr)
(00001DE5 8 3		UnVar3)
(00001DE7 5 3		UnVar3)
(00001DE9 60 219 255		T->JMP 00001DC7)
(00001DEC 5 4		UnVar4)
(00001DEE 81 1 247 0 1 0		nreverse)
(00001DF4 42		cons)
(00001DF5 9 104 0		':DOCUMENTATION)
(00001DF8 9 102 0		"symbolic names of C++ slots")
(00001DFB 57 6 0		list)
(00001DFE 9 101 0		':methods)
(00001E01 9 188 0		'get-Type)
(00001E04 9 100 0		':ROLE)
(00001E07 9 99 0		':direct)
(00001E0A 57 3 0		list)
(00001E0D 9 185 0		'get-Notification-Names)
(00001E10 9 100 0		':ROLE)
(00001E13 9 99 0		':direct)
(00001E16 57 3 0		list)
(00001E19 57 3 0		list)
(00001E1C 9 98 0		':sob-initializer)
(00001E1F 9 97 0		'new-instance)
(00001E22 57 2 0		list)
(00001E25 9 96 0		':predicate)
(00001E28 57 1 0		list)
(00001E2B 9 104 0		':DOCUMENTATION)
(00001E2E 9 95 0		"Class for ")
(00001E31 5 1		UnVar1)
(00001E33 81 1 94 0 1 0		symbol-name)
(00001E39 9 93 0		" reactors")
(00001E3C 81 3 244 0 1 0		concat)
(00001E42 57 2 0		list)
(00001E45 57 10 0		list)
(00001E48 9 92 0		'mk-al-type)
(00001E4B 9 91 0		'quote)
(00001E4E 5 1		UnVar1)
(00001E50 57 2 0		list)
(00001E53 9 90 0		'pack-name)
(00001E56 9 209 0		"VLR-")
(00001E59 9 91 0		'quote)
(00001E5C 5 1		UnVar1)
(00001E5E 57 2 0		list)
(00001E61 57 3 0		list)
(00001E64 57 3 0		list)
(00001E67 9 210 0		'defun)
(00001E6A 5 1		UnVar1)
(00001E6C 9 89 0		'&rest)
(00001E6F 9 88 0		'args)
(00001E72 57 2 0		list)
(00001E75 9 87 0		'apply)
(00001E78 9 241 0		'function)
(00001E7B 5 1		UnVar1)
(00001E7D 9 86 0		".new-instance")
(00001E80 81 2 244 0 1 0		concat)
(00001E86 81 1 243 0 1 0		intern)
(00001E8C 57 2 0		list)
(00001E8F 9 85 0		'cons)
(00001E92 9 117 0		'allocate-instance)
(00001E95 9 91 0		'quote)
(00001E98 5 1		UnVar1)
(00001E9A 57 2 0		list)
(00001E9D 57 2 0		list)
(00001EA0 9 88 0		'args)
(00001EA3 57 3 0		list)
(00001EA6 57 3 0		list)
(00001EA9 57 4 0		list)
(00001EAC 9 84 0		'defmethod)
(00001EAF 5 1		UnVar1)
(00001EB1 9 83 0		".get-Type")
(00001EB4 81 2 244 0 1 0		concat)
(00001EBA 81 1 243 0 1 0		intern)
(00001EC0 9 82 0		':private)
(00001EC3 9 81 0		'self)
(00001EC6 57 1 0		list)
(00001EC9 9 80 0		'class-slot-value)
(00001ECC 9 81 0		'self)
(00001ECF 9 91 0		'quote)
(00001ED2 9 108 0		'reactor-type)
(00001ED5 57 2 0		list)
(00001ED8 57 3 0		list)
(00001EDB 57 5 0		list)
(00001EDE 9 84 0		'defmethod)
(00001EE1 5 1		UnVar1)
(00001EE3 9 79 0		".get-Notification-Names")
(00001EE6 81 2 244 0 1 0		concat)
(00001EEC 81 1 243 0 1 0		intern)
(00001EF2 9 82 0		':private)
(00001EF5 9 81 0		'self)
(00001EF8 57 1 0		list)
(00001EFB 9 80 0		'class-slot-value)
(00001EFE 9 81 0		'self)
(00001F01 9 91 0		'quote)
(00001F04 9 234 0		'Notification-Names)
(00001F07 57 2 0		list)
(00001F0A 57 3 0		list)
(00001F0D 57 5 0		list)
(00001F10 57 7 0		list)
(00001F13 22		ret)
;;;def Linker-Reactor-p 7956
(00001F14 20 1 1 1 0)
(00001F19 5 0		UnVar0)
(00001F1B 9 78 0		'Linker-Reactor)
(00001F1E 47 2 175 0 32 32		typep)
;;;def Linker-Reactor.new-instance 7972
(00001F24 20 2 1 1 1)
(00001F29 9 23 1		'(2762 VL-Reactor.new-instance))
(00001F2C 5 0		UnVar0)
(00001F2E 5 1		UnVar1)
(00001F30 42		cons)
(00001F31 83		apply)
(00001F32 10)
(00001F33 5 0		UnVar0)
(00001F35 22		ret)
;;;def Linker-Reactor 7990
(00001F36 20 1 0 0 1)
(00001F3B 9 20 1		'(7972 Linker-Reactor.new-instance))
(00001F3E 9 78 0		'Linker-Reactor)
(00001F41 53 1 117 0 1 32		allocate-instance)
(00001F47 5 0		UnVar0)
(00001F49 42		cons)
(00001F4A 84		apply+ret)
;;;def Linker-Reactor.get-Type 8011
(00001F4B 20 1 1 1 0)
(00001F50 5 0		UnVar0)
(00001F52 9 108 0		'reactor-type)
(00001F55 81 2 80 0 1 0		class-slot-value)
(00001F5B 22		ret)
;;;def Linker-Reactor.get-Notification-Names 8028
(00001F5C 20 1 1 1 0)
(00001F61 5 0		UnVar0)
(00001F63 9 234 0		'Notification-Names)
(00001F66 81 2 80 0 1 0		class-slot-value)
(00001F6C 22		ret)
;;;def Editor-Reactor-p 8045
(00001F6D 20 1 1 1 0)
(00001F72 5 0		UnVar0)
(00001F74 9 77 0		'Editor-Reactor)
(00001F77 47 2 175 0 32 32		typep)
;;;def Editor-Reactor.new-instance 8061
(00001F7D 20 2 1 1 1)
(00001F82 9 23 1		'(2762 VL-Reactor.new-instance))
(00001F85 5 0		UnVar0)
(00001F87 5 1		UnVar1)
(00001F89 42		cons)
(00001F8A 83		apply)
(00001F8B 10)
(00001F8C 5 0		UnVar0)
(00001F8E 22		ret)
;;;def Editor-Reactor 8079
(00001F8F 20 1 0 0 1)
(00001F94 9 19 1		'(8061 Editor-Reactor.new-instance))
(00001F97 9 77 0		'Editor-Reactor)
(00001F9A 53 1 117 0 1 32		allocate-instance)
(00001FA0 5 0		UnVar0)
(00001FA2 42		cons)
(00001FA3 84		apply+ret)
;;;def Editor-Reactor.get-Type 8100
(00001FA4 20 1 1 1 0)
(00001FA9 5 0		UnVar0)
(00001FAB 9 108 0		'reactor-type)
(00001FAE 81 2 80 0 1 0		class-slot-value)
(00001FB4 22		ret)
;;;def Editor-Reactor.get-Notification-Names 8117
(00001FB5 20 1 1 1 0)
(00001FBA 5 0		UnVar0)
(00001FBC 9 234 0		'Notification-Names)
(00001FBF 81 2 80 0 1 0		class-slot-value)
(00001FC5 22		ret)
;;;def AcDb-Reactor-p 8134
(00001FC6 20 1 1 1 0)
(00001FCB 5 0		UnVar0)
(00001FCD 9 76 0		'AcDb-Reactor)
(00001FD0 47 2 175 0 32 32		typep)
;;;def AcDb-Reactor.new-instance 8150
(00001FD6 20 2 1 1 1)
(00001FDB 9 23 1		'(2762 VL-Reactor.new-instance))
(00001FDE 5 0		UnVar0)
(00001FE0 5 1		UnVar1)
(00001FE2 42		cons)
(00001FE3 83		apply)
(00001FE4 10)
(00001FE5 5 0		UnVar0)
(00001FE7 22		ret)
;;;def AcDb-Reactor 8168
(00001FE8 20 1 0 0 1)
(00001FED 9 18 1		'(8150 AcDb-Reactor.new-instance))
(00001FF0 9 76 0		'AcDb-Reactor)
(00001FF3 53 1 117 0 1 32		allocate-instance)
(00001FF9 5 0		UnVar0)
(00001FFB 42		cons)
(00001FFC 84		apply+ret)
;;;def AcDb-Reactor.get-Type 8189
(00001FFD 20 1 1 1 0)
(00002002 5 0		UnVar0)
(00002004 9 108 0		'reactor-type)
(00002007 81 2 80 0 1 0		class-slot-value)
(0000200D 22		ret)
;;;def AcDb-Reactor.get-Notification-Names 8206
(0000200E 20 1 1 1 0)
(00002013 5 0		UnVar0)
(00002015 9 234 0		'Notification-Names)
(00002018 81 2 80 0 1 0		class-slot-value)
(0000201E 22		ret)
;;;def DocManager-Reactor-p 8223
(0000201F 20 1 1 1 0)
(00002024 5 0		UnVar0)
(00002026 9 75 0		'DocManager-Reactor)
(00002029 47 2 175 0 32 32		typep)
;;;def DocManager-Reactor.new-instance 8239
(0000202F 20 2 1 1 1)
(00002034 9 23 1		'(2762 VL-Reactor.new-instance))
(00002037 5 0		UnVar0)
(00002039 5 1		UnVar1)
(0000203B 42		cons)
(0000203C 83		apply)
(0000203D 10)
(0000203E 5 0		UnVar0)
(00002040 22		ret)
;;;def DocManager-Reactor 8257
(00002041 20 1 0 0 1)
(00002046 9 17 1		'(8239 DocManager-Reactor.new-instance))
(00002049 9 75 0		'DocManager-Reactor)
(0000204C 53 1 117 0 1 32		allocate-instance)
(00002052 5 0		UnVar0)
(00002054 42		cons)
(00002055 84		apply+ret)
;;;def DocManager-Reactor.get-Type 8278
(00002056 20 1 1 1 0)
(0000205B 5 0		UnVar0)
(0000205D 9 108 0		'reactor-type)
(00002060 81 2 80 0 1 0		class-slot-value)
(00002066 22		ret)
;;;def DocManager-Reactor.get-Notification-Names 8295
(00002067 20 1 1 1 0)
(0000206C 5 0		UnVar0)
(0000206E 9 234 0		'Notification-Names)
(00002071 81 2 80 0 1 0		class-slot-value)
(00002077 22		ret)
;;;def Command-Reactor-p 8312
(00002078 20 1 1 1 0)
(0000207D 5 0		UnVar0)
(0000207F 9 74 0		'Command-Reactor)
(00002082 47 2 175 0 32 32		typep)
;;;def Command-Reactor.new-instance 8328
(00002088 20 2 1 1 1)
(0000208D 9 23 1		'(2762 VL-Reactor.new-instance))
(00002090 5 0		UnVar0)
(00002092 5 1		UnVar1)
(00002094 42		cons)
(00002095 83		apply)
(00002096 10)
(00002097 5 0		UnVar0)
(00002099 22		ret)
;;;def Command-Reactor 8346
(0000209A 20 1 0 0 1)
(0000209F 9 16 1		'(8328 Command-Reactor.new-instance))
(000020A2 9 74 0		'Command-Reactor)
(000020A5 53 1 117 0 1 32		allocate-instance)
(000020AB 5 0		UnVar0)
(000020AD 42		cons)
(000020AE 84		apply+ret)
;;;def Command-Reactor.get-Type 8367
(000020AF 20 1 1 1 0)
(000020B4 5 0		UnVar0)
(000020B6 9 108 0		'reactor-type)
(000020B9 81 2 80 0 1 0		class-slot-value)
(000020BF 22		ret)
;;;def Command-Reactor.get-Notification-Names 8384
(000020C0 20 1 1 1 0)
(000020C5 5 0		UnVar0)
(000020C7 9 234 0		'Notification-Names)
(000020CA 81 2 80 0 1 0		class-slot-value)
(000020D0 22		ret)
;;;def Lisp-Reactor-p 8401
(000020D1 20 1 1 1 0)
(000020D6 5 0		UnVar0)
(000020D8 9 73 0		'Lisp-Reactor)
(000020DB 47 2 175 0 32 32		typep)
;;;def Lisp-Reactor.new-instance 8417
(000020E1 20 2 1 1 1)
(000020E6 9 23 1		'(2762 VL-Reactor.new-instance))
(000020E9 5 0		UnVar0)
(000020EB 5 1		UnVar1)
(000020ED 42		cons)
(000020EE 83		apply)
(000020EF 10)
(000020F0 5 0		UnVar0)
(000020F2 22		ret)
;;;def Lisp-Reactor 8435
(000020F3 20 1 0 0 1)
(000020F8 9 15 1		'(8417 Lisp-Reactor.new-instance))
(000020FB 9 73 0		'Lisp-Reactor)
(000020FE 53 1 117 0 1 32		allocate-instance)
(00002104 5 0		UnVar0)
(00002106 42		cons)
(00002107 84		apply+ret)
;;;def Lisp-Reactor.get-Type 8456
(00002108 20 1 1 1 0)
(0000210D 5 0		UnVar0)
(0000210F 9 108 0		'reactor-type)
(00002112 81 2 80 0 1 0		class-slot-value)
(00002118 22		ret)
;;;def Lisp-Reactor.get-Notification-Names 8473
(00002119 20 1 1 1 0)
(0000211E 5 0		UnVar0)
(00002120 9 234 0		'Notification-Names)
(00002123 81 2 80 0 1 0		class-slot-value)
(00002129 22		ret)
;;;def DXF-Reactor-p 8490
(0000212A 20 1 1 1 0)
(0000212F 5 0		UnVar0)
(00002131 9 72 0		'DXF-Reactor)
(00002134 47 2 175 0 32 32		typep)
;;;def DXF-Reactor.new-instance 8506
(0000213A 20 2 1 1 1)
(0000213F 9 23 1		'(2762 VL-Reactor.new-instance))
(00002142 5 0		UnVar0)
(00002144 5 1		UnVar1)
(00002146 42		cons)
(00002147 83		apply)
(00002148 10)
(00002149 5 0		UnVar0)
(0000214B 22		ret)
;;;def DXF-Reactor 8524
(0000214C 20 1 0 0 1)
(00002151 9 14 1		'(8506 DXF-Reactor.new-instance))
(00002154 9 72 0		'DXF-Reactor)
(00002157 53 1 117 0 1 32		allocate-instance)
(0000215D 5 0		UnVar0)
(0000215F 42		cons)
(00002160 84		apply+ret)
;;;def DXF-Reactor.get-Type 8545
(00002161 20 1 1 1 0)
(00002166 5 0		UnVar0)
(00002168 9 108 0		'reactor-type)
(0000216B 81 2 80 0 1 0		class-slot-value)
(00002171 22		ret)
;;;def DXF-Reactor.get-Notification-Names 8562
(00002172 20 1 1 1 0)
(00002177 5 0		UnVar0)
(00002179 9 234 0		'Notification-Names)
(0000217C 81 2 80 0 1 0		class-slot-value)
(00002182 22		ret)
;;;def DWG-Reactor-p 8579
(00002183 20 1 1 1 0)
(00002188 5 0		UnVar0)
(0000218A 9 71 0		'DWG-Reactor)
(0000218D 47 2 175 0 32 32		typep)
;;;def DWG-Reactor.new-instance 8595
(00002193 20 2 1 1 1)
(00002198 9 23 1		'(2762 VL-Reactor.new-instance))
(0000219B 5 0		UnVar0)
(0000219D 5 1		UnVar1)
(0000219F 42		cons)
(000021A0 83		apply)
(000021A1 10)
(000021A2 5 0		UnVar0)
(000021A4 22		ret)
;;;def DWG-Reactor 8613
(000021A5 20 1 0 0 1)
(000021AA 9 13 1		'(8595 DWG-Reactor.new-instance))
(000021AD 9 71 0		'DWG-Reactor)
(000021B0 53 1 117 0 1 32		allocate-instance)
(000021B6 5 0		UnVar0)
(000021B8 42		cons)
(000021B9 84		apply+ret)
;;;def DWG-Reactor.get-Type 8634
(000021BA 20 1 1 1 0)
(000021BF 5 0		UnVar0)
(000021C1 9 108 0		'reactor-type)
(000021C4 81 2 80 0 1 0		class-slot-value)
(000021CA 22		ret)
;;;def DWG-Reactor.get-Notification-Names 8651
(000021CB 20 1 1 1 0)
(000021D0 5 0		UnVar0)
(000021D2 9 234 0		'Notification-Names)
(000021D5 81 2 80 0 1 0		class-slot-value)
(000021DB 22		ret)
;;;def SysVar-Reactor-p 8668
(000021DC 20 1 1 1 0)
(000021E1 5 0		UnVar0)
(000021E3 9 70 0		'SysVar-Reactor)
(000021E6 47 2 175 0 32 32		typep)
;;;def SysVar-Reactor.new-instance 8684
(000021EC 20 2 1 1 1)
(000021F1 9 23 1		'(2762 VL-Reactor.new-instance))
(000021F4 5 0		UnVar0)
(000021F6 5 1		UnVar1)
(000021F8 42		cons)
(000021F9 83		apply)
(000021FA 10)
(000021FB 5 0		UnVar0)
(000021FD 22		ret)
;;;def SysVar-Reactor 8702
(000021FE 20 1 0 0 1)
(00002203 9 12 1		'(8684 SysVar-Reactor.new-instance))
(00002206 9 70 0		'SysVar-Reactor)
(00002209 53 1 117 0 1 32		allocate-instance)
(0000220F 5 0		UnVar0)
(00002211 42		cons)
(00002212 84		apply+ret)
;;;def SysVar-Reactor.get-Type 8723
(00002213 20 1 1 1 0)
(00002218 5 0		UnVar0)
(0000221A 9 108 0		'reactor-type)
(0000221D 81 2 80 0 1 0		class-slot-value)
(00002223 22		ret)
;;;def SysVar-Reactor.get-Notification-Names 8740
(00002224 20 1 1 1 0)
(00002229 5 0		UnVar0)
(0000222B 9 234 0		'Notification-Names)
(0000222E 81 2 80 0 1 0		class-slot-value)
(00002234 22		ret)
;;;def Insert-Reactor-p 8757
(00002235 20 1 1 1 0)
(0000223A 5 0		UnVar0)
(0000223C 9 69 0		'Insert-Reactor)
(0000223F 47 2 175 0 32 32		typep)
;;;def Insert-Reactor.new-instance 8773
(00002245 20 2 1 1 1)
(0000224A 9 23 1		'(2762 VL-Reactor.new-instance))
(0000224D 5 0		UnVar0)
(0000224F 5 1		UnVar1)
(00002251 42		cons)
(00002252 83		apply)
(00002253 10)
(00002254 5 0		UnVar0)
(00002256 22		ret)
;;;def Insert-Reactor 8791
(00002257 20 1 0 0 1)
(0000225C 9 11 1		'(8773 Insert-Reactor.new-instance))
(0000225F 9 69 0		'Insert-Reactor)
(00002262 53 1 117 0 1 32		allocate-instance)
(00002268 5 0		UnVar0)
(0000226A 42		cons)
(0000226B 84		apply+ret)
;;;def Insert-Reactor.get-Type 8812
(0000226C 20 1 1 1 0)
(00002271 5 0		UnVar0)
(00002273 9 108 0		'reactor-type)
(00002276 81 2 80 0 1 0		class-slot-value)
(0000227C 22		ret)
;;;def Insert-Reactor.get-Notification-Names 8829
(0000227D 20 1 1 1 0)
(00002282 5 0		UnVar0)
(00002284 9 234 0		'Notification-Names)
(00002287 81 2 80 0 1 0		class-slot-value)
(0000228D 22		ret)
;;;def Wblock-Reactor-p 8846
(0000228E 20 1 1 1 0)
(00002293 5 0		UnVar0)
(00002295 9 68 0		'Wblock-Reactor)
(00002298 47 2 175 0 32 32		typep)
;;;def Wblock-Reactor.new-instance 8862
(0000229E 20 2 1 1 1)
(000022A3 9 23 1		'(2762 VL-Reactor.new-instance))
(000022A6 5 0		UnVar0)
(000022A8 5 1		UnVar1)
(000022AA 42		cons)
(000022AB 83		apply)
(000022AC 10)
(000022AD 5 0		UnVar0)
(000022AF 22		ret)
;;;def Wblock-Reactor 8880
(000022B0 20 1 0 0 1)
(000022B5 9 10 1		'(8862 Wblock-Reactor.new-instance))
(000022B8 9 68 0		'Wblock-Reactor)
(000022BB 53 1 117 0 1 32		allocate-instance)
(000022C1 5 0		UnVar0)
(000022C3 42		cons)
(000022C4 84		apply+ret)
;;;def Wblock-Reactor.get-Type 8901
(000022C5 20 1 1 1 0)
(000022CA 5 0		UnVar0)
(000022CC 9 108 0		'reactor-type)
(000022CF 81 2 80 0 1 0		class-slot-value)
(000022D5 22		ret)
;;;def Wblock-Reactor.get-Notification-Names 8918
(000022D6 20 1 1 1 0)
(000022DB 5 0		UnVar0)
(000022DD 9 234 0		'Notification-Names)
(000022E0 81 2 80 0 1 0		class-slot-value)
(000022E6 22		ret)
;;;def DeepClone-Reactor-p 8935
(000022E7 20 1 1 1 0)
(000022EC 5 0		UnVar0)
(000022EE 9 67 0		'DeepClone-Reactor)
(000022F1 47 2 175 0 32 32		typep)
;;;def DeepClone-Reactor.new-instance 8951
(000022F7 20 2 1 1 1)
(000022FC 9 23 1		'(2762 VL-Reactor.new-instance))
(000022FF 5 0		UnVar0)
(00002301 5 1		UnVar1)
(00002303 42		cons)
(00002304 83		apply)
(00002305 10)
(00002306 5 0		UnVar0)
(00002308 22		ret)
;;;def DeepClone-Reactor 8969
(00002309 20 1 0 0 1)
(0000230E 9 9 1		'(8951 DeepClone-Reactor.new-instance))
(00002311 9 67 0		'DeepClone-Reactor)
(00002314 53 1 117 0 1 32		allocate-instance)
(0000231A 5 0		UnVar0)
(0000231C 42		cons)
(0000231D 84		apply+ret)
;;;def DeepClone-Reactor.get-Type 8990
(0000231E 20 1 1 1 0)
(00002323 5 0		UnVar0)
(00002325 9 108 0		'reactor-type)
(00002328 81 2 80 0 1 0		class-slot-value)
(0000232E 22		ret)
;;;def DeepClone-Reactor.get-Notification-Names 9007
(0000232F 20 1 1 1 0)
(00002334 5 0		UnVar0)
(00002336 9 234 0		'Notification-Names)
(00002339 81 2 80 0 1 0		class-slot-value)
(0000233F 22		ret)
;;;def XREF-Reactor-p 9024
(00002340 20 1 1 1 0)
(00002345 5 0		UnVar0)
(00002347 9 66 0		'XREF-Reactor)
(0000234A 47 2 175 0 32 32		typep)
;;;def XREF-Reactor.new-instance 9040
(00002350 20 2 1 1 1)
(00002355 9 23 1		'(2762 VL-Reactor.new-instance))
(00002358 5 0		UnVar0)
(0000235A 5 1		UnVar1)
(0000235C 42		cons)
(0000235D 83		apply)
(0000235E 10)
(0000235F 5 0		UnVar0)
(00002361 22		ret)
;;;def XREF-Reactor 9058
(00002362 20 1 0 0 1)
(00002367 9 8 1		'(9040 XREF-Reactor.new-instance))
(0000236A 9 66 0		'XREF-Reactor)
(0000236D 53 1 117 0 1 32		allocate-instance)
(00002373 5 0		UnVar0)
(00002375 42		cons)
(00002376 84		apply+ret)
;;;def XREF-Reactor.get-Type 9079
(00002377 20 1 1 1 0)
(0000237C 5 0		UnVar0)
(0000237E 9 108 0		'reactor-type)
(00002381 81 2 80 0 1 0		class-slot-value)
(00002387 22		ret)
;;;def XREF-Reactor.get-Notification-Names 9096
(00002388 20 1 1 1 0)
(0000238D 5 0		UnVar0)
(0000238F 9 234 0		'Notification-Names)
(00002392 81 2 80 0 1 0		class-slot-value)
(00002398 22		ret)
;;;def Undo-Reactor-p 9113
(00002399 20 1 1 1 0)
(0000239E 5 0		UnVar0)
(000023A0 9 65 0		'Undo-Reactor)
(000023A3 47 2 175 0 32 32		typep)
;;;def Undo-Reactor.new-instance 9129
(000023A9 20 2 1 1 1)
(000023AE 9 23 1		'(2762 VL-Reactor.new-instance))
(000023B1 5 0		UnVar0)
(000023B3 5 1		UnVar1)
(000023B5 42		cons)
(000023B6 83		apply)
(000023B7 10)
(000023B8 5 0		UnVar0)
(000023BA 22		ret)
;;;def Undo-Reactor 9147
(000023BB 20 1 0 0 1)
(000023C0 9 7 1		'(9129 Undo-Reactor.new-instance))
(000023C3 9 65 0		'Undo-Reactor)
(000023C6 53 1 117 0 1 32		allocate-instance)
(000023CC 5 0		UnVar0)
(000023CE 42		cons)
(000023CF 84		apply+ret)
;;;def Undo-Reactor.get-Type 9168
(000023D0 20 1 1 1 0)
(000023D5 5 0		UnVar0)
(000023D7 9 108 0		'reactor-type)
(000023DA 81 2 80 0 1 0		class-slot-value)
(000023E0 22		ret)
;;;def Undo-Reactor.get-Notification-Names 9185
(000023E1 20 1 1 1 0)
(000023E6 5 0		UnVar0)
(000023E8 9 234 0		'Notification-Names)
(000023EB 81 2 80 0 1 0		class-slot-value)
(000023F1 22		ret)
;;;def Toolbar-Reactor-p 9202
(000023F2 20 1 1 1 0)
(000023F7 5 0		UnVar0)
(000023F9 9 64 0		'Toolbar-Reactor)
(000023FC 47 2 175 0 32 32		typep)
;;;def Toolbar-Reactor.new-instance 9218
(00002402 20 2 1 1 1)
(00002407 9 23 1		'(2762 VL-Reactor.new-instance))
(0000240A 5 0		UnVar0)
(0000240C 5 1		UnVar1)
(0000240E 42		cons)
(0000240F 83		apply)
(00002410 10)
(00002411 5 0		UnVar0)
(00002413 22		ret)
;;;def Toolbar-Reactor 9236
(00002414 20 1 0 0 1)
(00002419 9 6 1		'(9218 Toolbar-Reactor.new-instance))
(0000241C 9 64 0		'Toolbar-Reactor)
(0000241F 53 1 117 0 1 32		allocate-instance)
(00002425 5 0		UnVar0)
(00002427 42		cons)
(00002428 84		apply+ret)
;;;def Toolbar-Reactor.get-Type 9257
(00002429 20 1 1 1 0)
(0000242E 5 0		UnVar0)
(00002430 9 108 0		'reactor-type)
(00002433 81 2 80 0 1 0		class-slot-value)
(00002439 22		ret)
;;;def Toolbar-Reactor.get-Notification-Names 9274
(0000243A 20 1 1 1 0)
(0000243F 5 0		UnVar0)
(00002441 9 234 0		'Notification-Names)
(00002444 81 2 80 0 1 0		class-slot-value)
(0000244A 22		ret)
;;;def Mouse-Reactor-p 9291
(0000244B 20 1 1 1 0)
(00002450 5 0		UnVar0)
(00002452 9 63 0		'Mouse-Reactor)
(00002455 47 2 175 0 32 32		typep)
;;;def Mouse-Reactor.new-instance 9307
(0000245B 20 2 1 1 1)
(00002460 9 23 1		'(2762 VL-Reactor.new-instance))
(00002463 5 0		UnVar0)
(00002465 5 1		UnVar1)
(00002467 42		cons)
(00002468 83		apply)
(00002469 10)
(0000246A 5 0		UnVar0)
(0000246C 22		ret)
;;;def Mouse-Reactor 9325
(0000246D 20 1 0 0 1)
(00002472 9 5 1		'(9307 Mouse-Reactor.new-instance))
(00002475 9 63 0		'Mouse-Reactor)
(00002478 53 1 117 0 1 32		allocate-instance)
(0000247E 5 0		UnVar0)
(00002480 42		cons)
(00002481 84		apply+ret)
;;;def Mouse-Reactor.get-Type 9346
(00002482 20 1 1 1 0)
(00002487 5 0		UnVar0)
(00002489 9 108 0		'reactor-type)
(0000248C 81 2 80 0 1 0		class-slot-value)
(00002492 22		ret)
;;;def Mouse-Reactor.get-Notification-Names 9363
(00002493 20 1 1 1 0)
(00002498 5 0		UnVar0)
(0000249A 9 234 0		'Notification-Names)
(0000249D 81 2 80 0 1 0		class-slot-value)
(000024A3 22		ret)
;;;def Window-Reactor-p 9380
(000024A4 20 1 1 1 0)
(000024A9 5 0		UnVar0)
(000024AB 9 62 0		'Window-Reactor)
(000024AE 47 2 175 0 32 32		typep)
;;;def Window-Reactor.new-instance 9396
(000024B4 20 2 1 1 1)
(000024B9 9 23 1		'(2762 VL-Reactor.new-instance))
(000024BC 5 0		UnVar0)
(000024BE 5 1		UnVar1)
(000024C0 42		cons)
(000024C1 83		apply)
(000024C2 10)
(000024C3 5 0		UnVar0)
(000024C5 22		ret)
;;;def Window-Reactor 9414
(000024C6 20 1 0 0 1)
(000024CB 9 4 1		'(9396 Window-Reactor.new-instance))
(000024CE 9 62 0		'Window-Reactor)
(000024D1 53 1 117 0 1 32		allocate-instance)
(000024D7 5 0		UnVar0)
(000024D9 42		cons)
(000024DA 84		apply+ret)
;;;def Window-Reactor.get-Type 9435
(000024DB 20 1 1 1 0)
(000024E0 5 0		UnVar0)
(000024E2 9 108 0		'reactor-type)
(000024E5 81 2 80 0 1 0		class-slot-value)
(000024EB 22		ret)
;;;def Window-Reactor.get-Notification-Names 9452
(000024EC 20 1 1 1 0)
(000024F1 5 0		UnVar0)
(000024F3 9 234 0		'Notification-Names)
(000024F6 81 2 80 0 1 0		class-slot-value)
(000024FC 22		ret)
;;;def Miscellaneous-Reactor-p 9469
(000024FD 20 1 1 1 0)
(00002502 5 0		UnVar0)
(00002504 9 61 0		'Miscellaneous-Reactor)
(00002507 47 2 175 0 32 32		typep)
;;;def Miscellaneous-Reactor.new-instance 9485
(0000250D 20 2 1 1 1)
(00002512 9 23 1		'(2762 VL-Reactor.new-instance))
(00002515 5 0		UnVar0)
(00002517 5 1		UnVar1)
(00002519 42		cons)
(0000251A 83		apply)
(0000251B 10)
(0000251C 5 0		UnVar0)
(0000251E 22		ret)
;;;def Miscellaneous-Reactor 9503
(0000251F 20 1 0 0 1)
(00002524 9 3 1		'(9485 Miscellaneous-Reactor.new-instance))
(00002527 9 61 0		'Miscellaneous-Reactor)
(0000252A 53 1 117 0 1 32		allocate-instance)
(00002530 5 0		UnVar0)
(00002532 42		cons)
(00002533 84		apply+ret)
;;;def Miscellaneous-Reactor.get-Type 9524
(00002534 20 1 1 1 0)
(00002539 5 0		UnVar0)
(0000253B 9 108 0		'reactor-type)
(0000253E 81 2 80 0 1 0		class-slot-value)
(00002544 22		ret)
;;;def Miscellaneous-Reactor.get-Notification-Names 9541
(00002545 20 1 1 1 0)
(0000254A 5 0		UnVar0)
(0000254C 9 234 0		'Notification-Names)
(0000254F 81 2 80 0 1 0		class-slot-value)
(00002555 22		ret)
;;;def Object-Reactor-p 9558
(00002556 20 1 1 1 0)
(0000255B 5 0		UnVar0)
(0000255D 9 195 0		'Object-Reactor)
(00002560 47 2 175 0 32 32		typep)
;;;def Object-Reactor.new-instance 9574
(00002566 20 2 1 1 1)
(0000256B 9 22 1		'(6060 VL-Object-Reactor.new-instance))
(0000256E 5 0		UnVar0)
(00002570 5 1		UnVar1)
(00002572 42		cons)
(00002573 83		apply)
(00002574 10)
(00002575 5 0		UnVar0)
(00002577 22		ret)
;;;def Object-Reactor 9592
(00002578 20 1 0 0 1)
(0000257D 9 2 1		'(9574 Object-Reactor.new-instance))
(00002580 9 195 0		'Object-Reactor)
(00002583 53 1 117 0 1 32		allocate-instance)
(00002589 5 0		UnVar0)
(0000258B 42		cons)
(0000258C 84		apply+ret)
;;;def Object-Reactor.get-Type 9613
(0000258D 20 1 1 1 0)
(00002592 5 0		UnVar0)
(00002594 9 108 0		'reactor-type)
(00002597 81 2 80 0 1 0		class-slot-value)
(0000259D 22		ret)
;;;def Object-Reactor.get-Notification-Names 9630
(0000259E 20 1 1 1 0)
(000025A3 5 0		UnVar0)
(000025A5 9 234 0		'Notification-Names)
(000025A8 81 2 80 0 1 0		class-slot-value)
(000025AE 22		ret)
;;;def _vl-acdb-cleanup 9647
(000025AF 20 2 2 2 0)
(000025B4 3 60 0		*VLAReactor-Registration-Vector*)
(000025B7 53 1 59 0 1 32		copy-vector)
(000025BD 6 58 0		*_Save-VLAReactor-Registration-Vector*)
(000025C0 5 1		UnVar1)
(000025C2 40		car)
(000025C3 53 1 57 0 1 32		vlAcDoc:isCurrent)
(000025C9 63		nil->ret)
(000025CA 47 0 56 0 32 32		_kill-enames)
;;;def _vlr-object-reactors-clear 9680
(000025D0 20 2 0 0 0)
(000025D5 100 0		UNVar0)
(000025D7 100 1		UNVar1)
(000025D9 1		nil)
(000025DA 22		ret)
;;;def _vlr-global-reactors-clear 9691
(000025DB 20 0 0 0 0)
(000025E0 1		nil)
(000025E1 22		ret)
;;;def _clear-saved-global-reactors 9698
(000025E2 20 3 1 1 0)
(000025E7 5 0		UnVar0)
(000025E9 8 1		UnVar1)
(000025EB 100 2		UNVar2)
(000025ED 15 19 0		JMP 00002603)
(000025F0 5 1		UnVar1)
(000025F2 40		car)
(000025F3 8 2		UnVar2)
(000025F5 5 1		UnVar1)
(000025F7 41		cdr)
(000025F8 8 1		UnVar1)
(000025FA 5 2		UnVar2)
(000025FC 95 1 163 16 0 0		VL-Reactor.remove)
(00002602 10)
(00002603 5 1		UnVar1)
(00002605 60 232 255		T->JMP 000025F0)
(00002608 1		nil)
(00002609 22		ret)
;;;def nil 9738
(0000260A 20 2 1 1 0)
(0000260F 100 1		UNVar1)
(00002611 5 0		UnVar0)
(00002613 9 55 0		'((0 . :vlAcDoc-kNone) (1 . :vlAcDoc-kAutoWrite) (2 . :vlAcDoc-kNotLocked) (4 . :vlAcDoc-kWrite) (8 . :vlAcDoc-kRead) (16 . :vlAcDoc-kXWrite)))
(00002616 81 2 54 0 1 0		assq)
(0000261C 11)
(0000261D 8 1		UnVar1)
(0000261F 13 7 0		nil->JMP 00002629)
(00002622 5 1		UnVar1)
(00002624 41		cdr)
(00002625 57 1 0		list)
(00002628 22		ret)
(00002629 5 0		UnVar0)
(0000262B 22		ret)
;;;def vlAcDoc-lockMode 9772
(0000262C 20 2 1 2 0)
(00002631 5 0		UnVar0)
(00002633 5 1		UnVar1)
(00002635 53 2 53 0 1 32		vlAcDoc:lockMode)
(0000263B 97 1 15 38 0 0		offset 0000260F)
;;;def vlAcDoc-myLockMode 9793
(00002641 20 1 1 1 0)
(00002646 5 0		UnVar0)
(00002648 53 1 52 0 1 32		vlAcDoc:myLockMode)
(0000264E 96 1 10 38 0 0		func 0000260A)
;;;def nil 9812
(00002654 20 2 1 1 0)
(00002659 100 1		UNVar1)
(0000265B 5 0		UnVar0)
(0000265D 81 1 51 0 1 0		lentityp)
(00002663 13 24 0		nil->JMP 0000267E)
(00002666 5 0		UnVar0)
(00002668 81 1 50 0 1 0		lentity-live-p)
(0000266E 63		nil->ret)
(0000266F 5 0		UnVar0)
(00002671 53 1 49 0 1 32		ax:entity->objId)
(00002677 11)
(00002678 8 1		UnVar1)
(0000267A 63		nil->ret)
(0000267B 5 1		UnVar1)
(0000267D 22		ret)
(0000267E 5 0		UnVar0)
(00002680 53 1 120 0 1 32		IDispatchp)
(00002686 61 8 0		nil->JMP 00002691)
(00002689 5 0		UnVar0)
(0000268B 81 1 48 0 1 0		icom-connected-p)
(00002691 13 70 0		nil->JMP 000026DA)
(00002694 5 0		UnVar0)
(00002696 9 47 0		"ObjectID")
(00002699 81 2 46 0 1 0		IDispatch.GetIDsOfNames)
(0000269F 11)
(000026A0 8 1		UnVar1)
(000026A2 13 10 0		nil->JMP 000026AF)
(000026A5 5 0		UnVar0)
(000026A7 5 1		UnVar1)
(000026A9 47 2 45 0 32 32		vlax-get)
(000026AF 5 0		UnVar0)
(000026B1 9 44 0		"Handle")
(000026B4 81 2 46 0 1 0		IDispatch.GetIDsOfNames)
(000026BA 11)
(000026BB 8 1		UnVar1)
(000026BD 61 13 0		nil->JMP 000026CD)
(000026C0 5 0		UnVar0)
(000026C2 5 1		UnVar1)
(000026C4 53 2 45 0 1 32		vlax-get)
(000026CA 11)
(000026CB 8 1		UnVar1)
(000026CD 13 8 0		nil->JMP 000026D8)
(000026D0 5 1		UnVar1)
(000026D2 47 1 43 0 32 32		ax:handle->objId)
(000026D8 1		nil)
(000026D9 22		ret)
(000026DA 1		nil)
(000026DB 22		ret)
;;;def Idisp/ent->id 9948
(000026DC 20 2 1 2 0)
(000026E1 5 0		UnVar0)
(000026E3 95 1 84 38 0 0		func 00002654)
(000026E9 62		T->ret)
(000026EA 5 1		UnVar1)
(000026EC 63		nil->ret)
(000026ED 9 238 0		"VLMSG.DLL")
(000026F0 51 70 110 0 0		28230)
(000026F5 81 2 237 0 1 0		string-resource)
(000026FB 5 0		UnVar0)
(000026FD 81 2 221 0 1 0		_msg-err)
(00002703 22		ret)
;;;def vlax-write-enabled-p 9988
(00002704 20 2 1 1 0)
(00002709 100 1		UNVar1)
(0000270B 5 0		UnVar0)
(0000270D 2		T)
(0000270E 95 2 220 38 0 0		Idisp/ent->id)
(00002714 8 1		UnVar1)
(00002716 5 1		UnVar1)
(00002718 81 1 119 0 1 0		fixnump)
(0000271E 63		nil->ret)
(0000271F 5 1		UnVar1)
(00002721 47 1 42 0 32 32		ax:objId-is-write-enabled)
;;;def vlax-read-enabled-p 10023
(00002727 20 2 1 1 0)
(0000272C 100 1		UNVar1)
(0000272E 5 0		UnVar0)
(00002730 2		T)
(00002731 95 2 220 38 0 0		Idisp/ent->id)
(00002737 8 1		UnVar1)
(00002739 5 1		UnVar1)
(0000273B 81 1 119 0 1 0		fixnump)
(00002741 63		nil->ret)
(00002742 5 1		UnVar1)
(00002744 47 1 41 0 32 32		ax:objId-is-read-enabled)
;;;def vlax-erased-p 10058
(0000274A 20 2 1 1 0)
(0000274F 100 1		UNVar1)
(00002751 5 0		UnVar0)
(00002753 2		T)
(00002754 95 2 220 38 0 0		Idisp/ent->id)
(0000275A 8 1		UnVar1)
(0000275C 5 1		UnVar1)
(0000275E 81 1 119 0 1 0		fixnump)
(00002764 63		nil->ret)
(00002765 5 1		UnVar1)
(00002767 47 1 40 0 32 32		ax:objId-is-erased)
;;;def check-ent/dict-arg 10093
(0000276D 20 1 1 1 0)
(00002772 5 0		UnVar0)
(00002774 37 4		stringp)
(00002776 62		T->ret)
(00002777 5 0		UnVar0)
(00002779 81 1 51 0 1 0		lentityp)
(0000277F 62		T->ret)
(00002780 5 0		UnVar0)
(00002782 53 1 120 0 1 32		IDispatchp)
(00002788 62		T->ret)
(00002789 9 238 0		"VLMSG.DLL")
(0000278C 51 80 110 0 0		28240)
(00002791 81 2 237 0 1 0		string-resource)
(00002797 5 0		UnVar0)
(00002799 81 2 236 0 1 0		_bat-err)
(0000279F 22		ret)
;;;def check-dictId 10144
(000027A0 20 3 1 2 0)
(000027A5 100 2		UNVar2)
(000027A7 5 0		UnVar0)
(000027A9 95 1 109 39 0 0		check-ent/dict-arg)
(000027AF 10)
(000027B0 5 0		UnVar0)
(000027B2 37 4		stringp)
(000027B4 13 3 0		nil->JMP 000027BA)
(000027B7 15 44 0		JMP 000027E6)
(000027BA 5 0		UnVar0)
(000027BC 95 1 220 38 0 0		Idisp/ent->id)
(000027C2 11)
(000027C3 8 2		UnVar2)
(000027C5 13 7 0		nil->JMP 000027CF)
(000027C8 5 2		UnVar2)
(000027CA 8 0		UnVar0)
(000027CC 15 23 0		JMP 000027E6)
(000027CF 9 238 0		"VLMSG.DLL")
(000027D2 51 90 110 0 0		28250)
(000027D7 81 2 237 0 1 0		string-resource)
(000027DD 5 0		UnVar0)
(000027DF 81 2 221 0 1 0		_msg-err)
(000027E5 10)
(000027E6 5 0		UnVar0)
(000027E8 5 1		UnVar1)
(000027EA 53 2 39 0 1 32		ax:get-dictid)
(000027F0 8 2		UnVar2)
(000027F2 5 2		UnVar2)
(000027F4 13 4 0		nil->JMP 000027FB)
(000027F7 1		nil)
(000027F8 15 2 0		JMP 000027FD)
(000027FB 5 1		UnVar1)
(000027FD 13 23 0		nil->JMP 00002817)
(00002800 9 238 0		"VLMSG.DLL")
(00002803 51 100 110 0 0		28260)
(00002808 81 2 237 0 1 0		string-resource)
(0000280E 5 0		UnVar0)
(00002810 81 2 221 0 1 0		_msg-err)
(00002816 10)
(00002817 5 2		UnVar2)
(00002819 22		ret)
;;;def vlax-ldata-put 10266
(0000281A 20 6 3 4 0)
(0000281F 100 4		UNVar4)
(00002821 5 2		UnVar2)
(00002823 8 4		UnVar4)
(00002825 5 1		UnVar1)
(00002827 5 2		UnVar2)
(00002829 5 3		UnVar3)
(0000282B 53 3 38 0 1 32		_ll-ldata-put)
(00002831 8 5		UnVar5)
(00002833 5 5		UnVar5)
(00002835 40		car)
(00002836 8 1		UnVar1)
(00002838 5 5		UnVar5)
(0000283A 41		cdr)
(0000283B 8 2		UnVar2)
(0000283D 5 0		UnVar0)
(0000283F 2		T)
(00002840 95 2 160 39 0 0		check-dictId)
(00002846 5 2		UnVar2)
(00002848 5 1		UnVar1)
(0000284A 53 3 37 0 1 32		ax:dictid-keyval<-)
(00002850 10)
(00002851 5 4		UnVar4)
(00002853 22		ret)
;;;def vlax-ldata-get 10324
(00002854 20 5 2 4 0)
(00002859 100 4		UNVar4)
(0000285B 5 0		UnVar0)
(0000285D 95 1 160 39 0 0		check-dictId)
(00002863 8 4		UnVar4)
(00002865 5 4		UnVar4)
(00002867 13 30 0		nil->JMP 00002888)
(0000286A 5 4		UnVar4)
(0000286C 5 1		UnVar1)
(0000286E 5 3		UnVar3)
(00002870 53 2 36 0 1 32		_ll-ldata-key)
(00002876 5 2		UnVar2)
(00002878 53 3 35 0 1 32		ax:dictid-keyval)
(0000287E 5 2		UnVar2)
(00002880 5 3		UnVar3)
(00002882 47 3 34 0 32 32		_ll-ldata-get)
(00002888 5 2		UnVar2)
(0000288A 22		ret)
;;;def vlax-ldata-delete 10379
(0000288B 20 4 2 3 0)
(00002890 100 3		UNVar3)
(00002892 5 0		UnVar0)
(00002894 95 1 160 39 0 0		check-dictId)
(0000289A 11)
(0000289B 8 3		UnVar3)
(0000289D 63		nil->ret)
(0000289E 5 3		UnVar3)
(000028A0 5 1		UnVar1)
(000028A2 5 2		UnVar2)
(000028A4 53 2 36 0 1 32		_ll-ldata-key)
(000028AA 47 2 33 0 32 32		ax:dictid-delkey)
;;;def vlax-ldata-list 10416
(000028B0 20 3 1 2 0)
(000028B5 100 2		UNVar2)
(000028B7 5 0		UnVar0)
(000028B9 95 1 160 39 0 0		check-dictId)
(000028BF 11)
(000028C0 8 2		UnVar2)
(000028C2 63		nil->ret)
(000028C3 5 2		UnVar2)
(000028C5 53 1 32 0 1 32		ax:dictid-alist)
(000028CB 5 1		UnVar1)
(000028CD 47 2 31 0 32 32		_ll-ldata-get-alist)
;;;def vlax-ldata-test 10451
(000028D3 21 5 1 2 0)
(000028D8 100 2		UNVar2)
(000028DA 100 3		UNVar3)
(000028DC 100 4		UNVar4)
(000028DE 3 30 0		_%sys-error-hook%)
(000028E1 8 4		UnVar4)
(000028E3 2		T)
(000028E4 81 1 29 0 1 0		box)
(000028EA 11)
(000028EB 8 3		UnVar3)
(000028ED 57 1 0		list)
(000028F0 15 74 0		JMP 0000293D)
(000028F3 20 0 0 0 0)
(000028F8 9 30 0		'_%sys-error-hook%)
(000028FB 15 33 0		JMP 0000291F)
(000028FE 20 1 1 1 0)
(00002903 4 2 1		UpVar2-1)
(00002906 13 11 0		nil->JMP 00002914)
(00002909 4 2 4		UpVar2-4)
(0000290C 63		nil->ret)
(0000290D 5 0		UnVar0)
(0000290F 4 2 4		UpVar2-4)
(00002912 46 1		invoke+ret)
(00002914 4 2 3		UpVar2-3)
(00002917 1		nil)
(00002918 81 2 28 0 1 0		throw)
(0000291E 22		ret)
(0000291F 12 1 1		'(10494 nil))
(00002922 9 27 0		'%axvlo-io-stack%)
(00002925 81 0 26 0 1 0		make-stack)
(0000292B 24 4 0)
(0000292E 4 1 0		UpVar1-0)
(00002931 53 1 25 0 1 32		_cvo)
(00002937 10)
(00002938 2		T)
(00002939 25 2 0)
(0000293C 22		ret)
(0000293D 12 0 1		'(10483 -catch-))
(00002940 1		nil)
(00002941 81 3 24 0 1 0		_catched-apply)
(00002947 22		ret)
;;;def vlr-pers-DictName 10568
(00002948 20 0 0 0 0)
(0000294D 3 23 0		*VLR-DICT-NAME*)
(00002950 22		ret)
;;;def vlr-pers 10577
(00002951 20 6 1 1 0)
(00002956 100 1		UNVar1)
(00002958 100 2		UNVar2)
(0000295A 100 3		UNVar3)
(0000295C 100 4		UNVar4)
(0000295E 5 0		UnVar0)
(00002960 95 1 77 10 0 0		check-VL-Reactor)
(00002966 10)
(00002967 3 23 0		*VLR-DICT-NAME*)
(0000296A 2		T)
(0000296B 53 2 39 0 1 32		ax:get-dictid)
(00002971 11)
(00002972 8 3		UnVar3)
(00002974 61 26 0		nil->JMP 00002991)
(00002977 5 0		UnVar0)
(00002979 95 1 160 22 0 0		VL-Reactor.getDictKey)
(0000297F 11)
(00002980 8 2		UnVar2)
(00002982 61 12 0		nil->JMP 00002991)
(00002985 5 2		UnVar2)
(00002987 2		T)
(00002988 53 2 36 0 1 32		_ll-ldata-key)
(0000298E 11)
(0000298F 8 2		UnVar2)
(00002991 63		nil->ret)
(00002992 5 3		UnVar3)
(00002994 5 2		UnVar2)
(00002996 1		nil)
(00002997 53 3 35 0 1 32		ax:dictid-keyval)
(0000299D 8 4		UnVar4)
(0000299F 5 4		UnVar4)
(000029A1 1		nil)
(000029A2 2		T)
(000029A3 53 3 34 0 1 32		_ll-ldata-get)
(000029A9 8 4		UnVar4)
(000029AB 5 0		UnVar0)
(000029AD 5 4		UnVar4)
(000029AF 81 2 22 0 1 0		adjoin)
(000029B5 8 4		UnVar4)
(000029B7 5 2		UnVar2)
(000029B9 5 4		UnVar4)
(000029BB 2		T)
(000029BC 53 3 38 0 1 32		_ll-ldata-put)
(000029C2 8 5		UnVar5)
(000029C4 5 5		UnVar5)
(000029C6 40		car)
(000029C7 8 2		UnVar2)
(000029C9 5 5		UnVar5)
(000029CB 41		cdr)
(000029CC 8 1		UnVar1)
(000029CE 5 3		UnVar3)
(000029D0 5 1		UnVar1)
(000029D2 5 2		UnVar2)
(000029D4 53 3 37 0 1 32		ax:dictid-keyval<-)
(000029DA 10)
(000029DB 5 3		UnVar3)
(000029DD 5 1		UnVar1)
(000029DF 5 2		UnVar2)
(000029E1 53 3 37 0 1 32		ax:dictid-keyval<-)
(000029E7 10)
(000029E8 5 0		UnVar0)
(000029EA 22		ret)
;;;def vl-pers-list 10731
(000029EB 20 4 0 1 0)
(000029F0 100 1		UNVar1)
(000029F2 100 2		UNVar2)
(000029F4 100 3		UNVar3)
(000029F6 3 23 0		*VLR-DICT-NAME*)
(000029F9 53 1 39 0 1 32		ax:get-dictid)
(000029FF 11)
(00002A00 8 2		UnVar2)
(00002A02 63		nil->ret)
(00002A03 5 0		UnVar0)
(00002A05 95 1 211 22 0 0		VLR-Reactor.getDictKey)
(00002A0B 11)
(00002A0C 8 1		UnVar1)
(00002A0E 63		nil->ret)
(00002A0F 5 1		UnVar1)
(00002A11 2		T)
(00002A12 53 2 36 0 1 32		_ll-ldata-key)
(00002A18 11)
(00002A19 8 1		UnVar1)
(00002A1B 63		nil->ret)
(00002A1C 5 2		UnVar2)
(00002A1E 5 1		UnVar1)
(00002A20 1		nil)
(00002A21 53 3 35 0 1 32		ax:dictid-keyval)
(00002A27 11)
(00002A28 8 3		UnVar3)
(00002A2A 63		nil->ret)
(00002A2B 5 3		UnVar3)
(00002A2D 1		nil)
(00002A2E 2		T)
(00002A2F 53 3 34 0 1 32		_ll-ldata-get)
(00002A35 11)
(00002A36 8 3		UnVar3)
(00002A38 22		ret)
;;;def vlr-pers-list 10809
(00002A39 20 1 0 1 0)
(00002A3E 5 0		UnVar0)
(00002A40 96 1 235 41 0 0		vl-pers-list)
;;;def vlr-pers-activate 10822
(00002A46 20 4 0 1 0)
(00002A4B 100 1		UNVar1)
(00002A4D 5 0		UnVar0)
(00002A4F 95 1 57 42 0 0		vlr-pers-list)
(00002A55 11)
(00002A56 8 1		UnVar1)
(00002A58 8 2		UnVar2)
(00002A5A 100 3		UNVar3)
(00002A5C 15 19 0		JMP 00002A72)
(00002A5F 5 2		UnVar2)
(00002A61 40		car)
(00002A62 8 3		UnVar3)
(00002A64 5 2		UnVar2)
(00002A66 41		cdr)
(00002A67 8 2		UnVar2)
(00002A69 5 3		UnVar3)
(00002A6B 95 1 11 16 0 0		VL-Reactor.reInit)
(00002A71 10)
(00002A72 5 2		UnVar2)
(00002A74 60 232 255		T->JMP 00002A5F)
(00002A77 5 1		UnVar1)
(00002A79 22		ret)
;;;def vlr-pers-release 10874
(00002A7A 20 6 1 1 0)
(00002A7F 100 1		UNVar1)
(00002A81 100 2		UNVar2)
(00002A83 100 3		UNVar3)
(00002A85 100 4		UNVar4)
(00002A87 5 0		UnVar0)
(00002A89 95 1 77 10 0 0		check-VL-Reactor)
(00002A8F 10)
(00002A90 5 0		UnVar0)
(00002A92 95 1 235 41 0 0		vl-pers-list)
(00002A98 11)
(00002A99 8 4		UnVar4)
(00002A9B 63		nil->ret)
(00002A9C 5 0		UnVar0)
(00002A9E 5 4		UnVar4)
(00002AA0 81 2 145 0 1 0		delete)
(00002AA6 8 4		UnVar4)
(00002AA8 5 0		UnVar0)
(00002AAA 95 1 211 22 0 0		VLR-Reactor.getDictKey)
(00002AB0 8 3		UnVar3)
(00002AB2 5 3		UnVar3)
(00002AB4 5 4		UnVar4)
(00002AB6 2		T)
(00002AB7 53 3 38 0 1 32		_ll-ldata-put)
(00002ABD 8 5		UnVar5)
(00002ABF 5 5		UnVar5)
(00002AC1 40		car)
(00002AC2 8 3		UnVar3)
(00002AC4 5 5		UnVar5)
(00002AC6 41		cdr)
(00002AC7 8 2		UnVar2)
(00002AC9 3 23 0		*VLR-DICT-NAME*)
(00002ACC 53 1 39 0 1 32		ax:get-dictid)
(00002AD2 8 1		UnVar1)
(00002AD4 5 1		UnVar1)
(00002AD6 5 2		UnVar2)
(00002AD8 5 3		UnVar3)
(00002ADA 53 3 37 0 1 32		ax:dictid-keyval<-)
(00002AE0 10)
(00002AE1 5 0		UnVar0)
(00002AE3 22		ret)
;;;def vlr-pers-p 10980
(00002AE4 20 1 1 1 0)
(00002AE9 5 0		UnVar0)
(00002AEB 95 1 77 10 0 0		check-VL-Reactor)
(00002AF1 10)
(00002AF2 5 0		UnVar0)
(00002AF4 5 0		UnVar0)
(00002AF6 95 1 235 41 0 0		vl-pers-list)
(00002AFC 81 2 21 0 1 0		memq)
(00002B02 63		nil->ret)
(00002B03 5 0		UnVar0)
(00002B05 22		ret)
;;;def vlax-vla-object->ename 11014
(00002B06 20 2 1 1 0)
(00002B0B 100 1		UNVar1)
(00002B0D 5 0		UnVar0)
(00002B0F 53 1 120 0 1 32		IDispatchp)
(00002B15 14 11 0		T->JMP 00002B23)
(00002B18 9 20 0		"VLA-OBJECT")
(00002B1B 5 0		UnVar0)
(00002B1D 81 2 236 0 1 0		_bat-err)
(00002B23 63		nil->ret)
(00002B24 5 0		UnVar0)
(00002B26 95 1 220 38 0 0		Idisp/ent->id)
(00002B2C 11)
(00002B2D 8 1		UnVar1)
(00002B2F 63		nil->ret)
(00002B30 5 1		UnVar1)
(00002B32 81 1 119 0 1 0		fixnump)
(00002B38 63		nil->ret)
(00002B39 5 1		UnVar1)
(00002B3B 53 1 40 0 1 32		ax:objId-is-erased)
(00002B41 13 2 0		nil->JMP 00002B46)
(00002B44 1		nil)
(00002B45 22		ret)
(00002B46 5 1		UnVar1)
(00002B48 47 1 19 0 32 32		ax:objId->entity)
;;;def vlax-ename->vla-object 11086
(00002B4E 20 4 1 1 0)
(00002B53 100 1		UNVar1)
(00002B55 100 2		UNVar2)
(00002B57 100 3		UNVar3)
(00002B59 5 0		UnVar0)
(00002B5B 81 1 50 0 1 0		lentity-live-p)
(00002B61 63		nil->ret)
(00002B62 5 0		UnVar0)
(00002B64 53 1 49 0 1 32		ax:entity->objId)
(00002B6A 11)
(00002B6B 8 3		UnVar3)
(00002B6D 63		nil->ret)
(00002B6E 5 3		UnVar3)
(00002B70 81 1 119 0 1 0		fixnump)
(00002B76 63		nil->ret)
(00002B77 5 3		UnVar3)
(00002B79 53 1 40 0 1 32		ax:objId-is-erased)
(00002B7F 13 2 0		nil->JMP 00002B84)
(00002B82 1		nil)
(00002B83 22		ret)
(00002B84 3 116 0		*ActiveDocument-wcash*)
(00002B87 52 0 1		)
(00002B8A 5 3		UnVar3)
(00002B8C 47 2 115 0 32 32		vla-ObjectIDToObject)
;;;def IDisp?->Id 11154
(00002B92 20 1 1 1 0)
(00002B97 5 0		UnVar0)
(00002B99 2		T)
(00002B9A 96 2 220 38 0 0		Idisp/ent->id)
;;;def vlax-curve-getArea 11168
(00002BA0 20 2 1 1 0)
(00002BA5 5 0		UnVar0)
(00002BA7 8 1		UnVar1)
(00002BA9 5 1		UnVar1)
(00002BAB 2		T)
(00002BAC 95 2 220 38 0 0		Idisp/ent->id)
(00002BB2 47 1 18 0 32 32		ax:curve-getArea)
;;;def vlax-curve-getDistAtParam 11192
(00002BB8 20 3 2 2 0)
(00002BBD 5 0		UnVar0)
(00002BBF 8 2		UnVar2)
(00002BC1 5 2		UnVar2)
(00002BC3 2		T)
(00002BC4 95 2 220 38 0 0		Idisp/ent->id)
(00002BCA 5 1		UnVar1)
(00002BCC 47 2 17 0 32 32		ax:curve-getDistAtParam)
;;;def vlax-curve-getDistAtPoint 11218
(00002BD2 20 3 2 2 0)
(00002BD7 5 0		UnVar0)
(00002BD9 8 2		UnVar2)
(00002BDB 5 2		UnVar2)
(00002BDD 2		T)
(00002BDE 95 2 220 38 0 0		Idisp/ent->id)
(00002BE4 5 1		UnVar1)
(00002BE6 47 2 16 0 32 32		ax:curve-getDistAtPoint)
;;;def vlax-curve-getEndParam 11244
(00002BEC 20 2 1 1 0)
(00002BF1 5 0		UnVar0)
(00002BF3 8 1		UnVar1)
(00002BF5 5 1		UnVar1)
(00002BF7 2		T)
(00002BF8 95 2 220 38 0 0		Idisp/ent->id)
(00002BFE 47 1 15 0 32 32		ax:curve-getEndParam)
;;;def vlax-curve-getEndPoint 11268
(00002C04 20 2 1 1 0)
(00002C09 5 0		UnVar0)
(00002C0B 8 1		UnVar1)
(00002C0D 5 1		UnVar1)
(00002C0F 2		T)
(00002C10 95 2 220 38 0 0		Idisp/ent->id)
(00002C16 47 1 14 0 32 32		ax:curve-getEndPoint)
;;;def vlax-curve-getParamAtDist 11292
(00002C1C 20 3 2 2 0)
(00002C21 5 0		UnVar0)
(00002C23 8 2		UnVar2)
(00002C25 5 2		UnVar2)
(00002C27 2		T)
(00002C28 95 2 220 38 0 0		Idisp/ent->id)
(00002C2E 5 1		UnVar1)
(00002C30 47 2 13 0 32 32		ax:curve-getParamAtDist)
;;;def vlax-curve-getParamAtPoint 11318
(00002C36 20 3 2 2 0)
(00002C3B 5 0		UnVar0)
(00002C3D 8 2		UnVar2)
(00002C3F 5 2		UnVar2)
(00002C41 2		T)
(00002C42 95 2 220 38 0 0		Idisp/ent->id)
(00002C48 5 1		UnVar1)
(00002C4A 47 2 12 0 32 32		ax:curve-getParamAtPoint)
;;;def vlax-curve-getPointAtDist 11344
(00002C50 20 3 2 2 0)
(00002C55 5 0		UnVar0)
(00002C57 8 2		UnVar2)
(00002C59 5 2		UnVar2)
(00002C5B 2		T)
(00002C5C 95 2 220 38 0 0		Idisp/ent->id)
(00002C62 5 1		UnVar1)
(00002C64 47 2 11 0 32 32		ax:curve-getPointAtDist)
;;;def vlax-curve-getPointAtParam 11370
(00002C6A 20 3 2 2 0)
(00002C6F 5 0		UnVar0)
(00002C71 8 2		UnVar2)
(00002C73 5 2		UnVar2)
(00002C75 2		T)
(00002C76 95 2 220 38 0 0		Idisp/ent->id)
(00002C7C 5 1		UnVar1)
(00002C7E 47 2 10 0 32 32		ax:curve-getPointAtParam)
;;;def vlax-curve-getStartParam 11396
(00002C84 20 2 1 1 0)
(00002C89 5 0		UnVar0)
(00002C8B 8 1		UnVar1)
(00002C8D 5 1		UnVar1)
(00002C8F 2		T)
(00002C90 95 2 220 38 0 0		Idisp/ent->id)
(00002C96 47 1 9 0 32 32		ax:curve-getStartParam)
;;;def vlax-curve-getStartPoint 11420
(00002C9C 20 2 1 1 0)
(00002CA1 5 0		UnVar0)
(00002CA3 8 1		UnVar1)
(00002CA5 5 1		UnVar1)
(00002CA7 2		T)
(00002CA8 95 2 220 38 0 0		Idisp/ent->id)
(00002CAE 47 1 8 0 32 32		ax:curve-getStartPoint)
;;;def vlax-curve-isClosed 11444
(00002CB4 20 2 1 1 0)
(00002CB9 5 0		UnVar0)
(00002CBB 8 1		UnVar1)
(00002CBD 5 1		UnVar1)
(00002CBF 2		T)
(00002CC0 95 2 220 38 0 0		Idisp/ent->id)
(00002CC6 47 1 7 0 32 32		ax:curve-isClosed)
;;;def vlax-curve-isPeriodic 11468
(00002CCC 20 2 1 1 0)
(00002CD1 5 0		UnVar0)
(00002CD3 8 1		UnVar1)
(00002CD5 5 1		UnVar1)
(00002CD7 2		T)
(00002CD8 95 2 220 38 0 0		Idisp/ent->id)
(00002CDE 47 1 6 0 32 32		ax:curve-isPeriodic)
;;;def vlax-curve-isPlanar 11492
(00002CE4 20 2 1 1 0)
(00002CE9 5 0		UnVar0)
(00002CEB 8 1		UnVar1)
(00002CED 5 1		UnVar1)
(00002CEF 2		T)
(00002CF0 95 2 220 38 0 0		Idisp/ent->id)
(00002CF6 47 1 5 0 32 32		ax:curve-isPlanar)
;;;def vlax-curve-getClosestPointTo 11516
(00002CFC 20 4 2 3 0)
(00002D01 5 0		UnVar0)
(00002D03 8 3		UnVar3)
(00002D05 5 3		UnVar3)
(00002D07 2		T)
(00002D08 95 2 220 38 0 0		Idisp/ent->id)
(00002D0E 5 1		UnVar1)
(00002D10 5 2		UnVar2)
(00002D12 47 3 4 0 32 32		AX:CURVE-getClosestPointTo)
;;;def vlax-curve-getClosestPointToProjection 11544
(00002D18 20 5 3 4 0)
(00002D1D 5 0		UnVar0)
(00002D1F 8 4		UnVar4)
(00002D21 5 4		UnVar4)
(00002D23 2		T)
(00002D24 95 2 220 38 0 0		Idisp/ent->id)
(00002D2A 5 1		UnVar1)
(00002D2C 5 2		UnVar2)
(00002D2E 5 3		UnVar3)
(00002D30 47 4 3 0 32 32		AX:CURVE-getClosestPointToProjection)
;;;def vlax-curve-getFirstDeriv 11574
(00002D36 20 3 2 2 0)
(00002D3B 5 0		UnVar0)
(00002D3D 8 2		UnVar2)
(00002D3F 5 2		UnVar2)
(00002D41 2		T)
(00002D42 95 2 220 38 0 0		Idisp/ent->id)
(00002D48 5 1		UnVar1)
(00002D4A 47 2 2 0 32 32		AX:CURVE-getFirstDeriv)
;;;def vlax-curve-getSecondDeriv 11600
(00002D50 20 3 2 2 0)
(00002D55 5 0		UnVar0)
(00002D57 8 2		UnVar2)
(00002D59 5 2		UnVar2)
(00002D5B 2		T)
(00002D5C 95 2 220 38 0 0		Idisp/ent->id)
(00002D62 5 1		UnVar1)
(00002D64 47 2 1 0 32 32		AX:CURVE-getSecondDeriv)
;;;==========Main==========
(00000000 20 0 0 0 0)
(00000005 1		nil)
(00000006 10)
(00000007 9 83 1		"3/5/18 10:08 PM")
(0000000A 26 82 1		*reactors-date*)
(0000000D 9 82 1		'*reactors-date*)
(00000010 10)
(00000011 9 81 1		'reactors)
(00000014 81 1 80 1 0 0		provide)
(0000001A 10)
(0000001B 9 79 1		'los)
(0000001E 81 1 78 1 0 0		require)
(00000024 10)
(00000025 9 77 1		'lpparx)
(00000028 81 1 78 1 0 0		require)
(0000002E 28		[ret])
(0000002F 20 0 0 0 0)
(00000034 1		nil)
(00000035 10)
(00000036 9 76 1		'rconst)
(00000039 81 1 80 1 1 0		provide)
(0000003F 10)
(00000040 15 0 0		JMP 00000043)
(00000043 9 87 2		'nil)
(00000046 53 1 75 1 1 32		make-macro)
(0000004C 26 74 1		make-reactor-vectors)
(0000004F 9 74 1		'make-reactor-vectors)
(00000052 10)
(00000053 9 73 1		'Linker-Reactor)
(00000056 9 72 1		'Editor-Reactor)
(00000059 9 71 1		'AcDb-Reactor)
(0000005C 9 70 1		'DocManager-Reactor)
(0000005F 9 69 1		'Command-Reactor)
(00000062 9 68 1		'Lisp-Reactor)
(00000065 9 67 1		'DXF-Reactor)
(00000068 9 66 1		'DWG-Reactor)
(0000006B 9 65 1		'Insert-Reactor)
(0000006E 9 64 1		'Wblock-Reactor)
(00000071 9 63 1		'SysVar-Reactor)
(00000074 9 62 1		'DeepClone-Reactor)
(00000077 9 61 1		'XREF-Reactor)
(0000007A 9 60 1		'Undo-Reactor)
(0000007D 9 59 1		'Window-Reactor)
(00000080 9 58 1		'Toolbar-Reactor)
(00000083 9 57 1		'Mouse-Reactor)
(00000086 9 56 1		'Miscellaneous-Reactor)
(00000089 9 55 1		'Object-Reactor)
(0000008C 81 19 54 1 1 0		vector)
(00000092 26 53 1		*VLAReactor-Class-Vector*)
(00000095 9 53 1		'*VLAReactor-Class-Vector*)
(00000098 10)
(00000099 9 52 1		':VLR-Linker-Reactor)
(0000009C 9 51 1		':VLR-Editor-Reactor)
(0000009F 9 50 1		':VLR-AcDb-Reactor)
(000000A2 9 49 1		':VLR-DocManager-Reactor)
(000000A5 9 48 1		':VLR-Command-Reactor)
(000000A8 9 47 1		':VLR-Lisp-Reactor)
(000000AB 9 46 1		':VLR-DXF-Reactor)
(000000AE 9 45 1		':VLR-DWG-Reactor)
(000000B1 9 44 1		':VLR-Insert-Reactor)
(000000B4 9 43 1		':VLR-Wblock-Reactor)
(000000B7 9 42 1		':VLR-SysVar-Reactor)
(000000BA 9 41 1		':VLR-DeepClone-Reactor)
(000000BD 9 40 1		':VLR-XREF-Reactor)
(000000C0 9 39 1		':VLR-Undo-Reactor)
(000000C3 9 38 1		':VLR-Window-Reactor)
(000000C6 9 37 1		':VLR-Toolbar-Reactor)
(000000C9 9 36 1		':VLR-Mouse-Reactor)
(000000CC 9 35 1		':VLR-Miscellaneous-Reactor)
(000000CF 9 34 1		':VLR-Object-Reactor)
(000000D2 81 19 54 1 1 0		vector)
(000000D8 26 33 1		*VLAReactor-Class-Names-Vector*)
(000000DB 9 33 1		'*VLAReactor-Class-Names-Vector*)
(000000DE 10)
(000000DF 9 86 2		'Linker-Reactor)
(000000E2 9 85 2		'Editor-Reactor)
(000000E5 9 84 2		'AcDb-Reactor)
(000000E8 9 83 2		'DocManager-Reactor)
(000000EB 9 82 2		'Command-Reactor)
(000000EE 9 81 2		'Lisp-Reactor)
(000000F1 9 80 2		'DXF-Reactor)
(000000F4 9 79 2		'DWG-Reactor)
(000000F7 9 78 2		'Insert-Reactor)
(000000FA 9 77 2		'Wblock-Reactor)
(000000FD 9 76 2		'SysVar-Reactor)
(00000100 9 75 2		'DeepClone-Reactor)
(00000103 9 74 2		'XREF-Reactor)
(00000106 9 73 2		'Undo-Reactor)
(00000109 9 72 2		'Window-Reactor)
(0000010C 9 71 2		'Toolbar-Reactor)
(0000010F 9 70 2		'Mouse-Reactor)
(00000112 9 69 2		'Miscellaneous-Reactor)
(00000115 9 68 2		'Object-Reactor)
(00000118 81 19 54 1 1 0		vector)
(0000011E 26 32 1		*VLAReactor-Class-Creators-Vector*)
(00000121 9 32 1		'*VLAReactor-Class-Creators-Vector*)
(00000124 10)
(00000125 1		nil)
(00000126 10)
(00000127 1		nil)
(00000128 28		[ret])
(00000129 20 0 0 0 0)
(0000012E 1		nil)
(0000012F 10)
(00000130 1		nil)
(00000131 10)
(00000132 9 67 2		'VLR-Reaction-Names)
(00000135 26 31 1		VLR-Reaction-Names)
(00000138 9 31 1		'VLR-Reaction-Names)
(0000013B 10)
(0000013C 15 0 0		JMP 0000013F)
(0000013F 9 66 2		'nil)
(00000142 53 1 75 1 1 32		make-macro)
(00000148 26 30 1		dovector)
(0000014B 9 30 1		'dovector)
(0000014E 10)
(0000014F 9 65 2		'VLR-remove-all)
(00000152 26 29 1		VLR-remove-all)
(00000155 9 29 1		'VLR-remove-all)
(00000158 10)
(00000159 9 64 2		'VLR-reactors)
(0000015C 26 28 1		VLR-reactors)
(0000015F 9 28 1		'VLR-reactors)
(00000162 10)
(00000163 1		nil)
(00000164 10)
(00000165 1		nil)
(00000166 10)
(00000167 1		nil)
(00000168 10)
(00000169 9 63 2		'VLR-beep-reaction)
(0000016C 26 27 1		VLR-beep-reaction)
(0000016F 9 27 1		'VLR-beep-reaction)
(00000172 10)
(00000173 9 62 2		'VLR-trace-reaction)
(00000176 26 26 1		VLR-trace-reaction)
(00000179 9 26 1		'VLR-trace-reaction)
(0000017C 10)
(0000017D 9 61 2		'VLR-current-reaction-name)
(00000180 26 25 1		VLR-current-reaction-name)
(00000183 9 25 1		'VLR-current-reaction-name)
(00000186 10)
(00000187 9 60 2		'VLR-types)
(0000018A 26 24 1		VLR-types)
(0000018D 9 24 1		'VLR-types)
(00000190 28		[ret])
(00000191 20 0 0 0 0)
(00000196 1		nil)
(00000197 10)
(00000198 9 76 1		'rconst)
(0000019B 81 1 78 1 1 0		require)
(000001A1 10)
(000001A2 1		nil)
(000001A3 10)
(000001A4 15 0 0		JMP 000001A7)
(000001A7 9 59 2		'nil)
(000001AA 53 1 75 1 1 32		make-macro)
(000001B0 26 23 1		make-a-reactor)
(000001B3 9 23 1		'make-a-reactor)
(000001B6 10)
(000001B7 15 0 0		JMP 000001BA)
(000001BA 9 58 2		'nil)
(000001BD 53 1 75 1 1 32		make-macro)
(000001C3 26 22 1		make-an-object-reactor)
(000001C6 9 22 1		'make-an-object-reactor)
(000001C9 10)
(000001CA 15 0 0		JMP 000001CD)
(000001CD 9 57 2		'nil)
(000001D0 53 1 75 1 1 32		make-macro)
(000001D6 26 21 1		make-all-reactors)
(000001D9 9 21 1		'make-all-reactors)
(000001DC 10)
(000001DD 9 56 2		'VLR-Linker-Reactor)
(000001E0 26 20 1		VLR-Linker-Reactor)
(000001E3 9 20 1		'VLR-Linker-Reactor)
(000001E6 10)
(000001E7 9 55 2		'VLR-Editor-Reactor)
(000001EA 26 19 1		VLR-Editor-Reactor)
(000001ED 9 19 1		'VLR-Editor-Reactor)
(000001F0 10)
(000001F1 9 54 2		'VLR-AcDb-Reactor)
(000001F4 26 18 1		VLR-AcDb-Reactor)
(000001F7 9 18 1		'VLR-AcDb-Reactor)
(000001FA 10)
(000001FB 9 53 2		'VLR-DocManager-Reactor)
(000001FE 26 17 1		VLR-DocManager-Reactor)
(00000201 9 17 1		'VLR-DocManager-Reactor)
(00000204 10)
(00000205 9 52 2		'VLR-Command-Reactor)
(00000208 26 16 1		VLR-Command-Reactor)
(0000020B 9 16 1		'VLR-Command-Reactor)
(0000020E 10)
(0000020F 9 51 2		'VLR-Lisp-Reactor)
(00000212 26 15 1		VLR-Lisp-Reactor)
(00000215 9 15 1		'VLR-Lisp-Reactor)
(00000218 10)
(00000219 9 50 2		'VLR-DXF-Reactor)
(0000021C 26 14 1		VLR-DXF-Reactor)
(0000021F 9 14 1		'VLR-DXF-Reactor)
(00000222 10)
(00000223 9 49 2		'VLR-DWG-Reactor)
(00000226 26 13 1		VLR-DWG-Reactor)
(00000229 9 13 1		'VLR-DWG-Reactor)
(0000022C 10)
(0000022D 9 48 2		'VLR-Insert-Reactor)
(00000230 26 12 1		VLR-Insert-Reactor)
(00000233 9 12 1		'VLR-Insert-Reactor)
(00000236 10)
(00000237 9 47 2		'VLR-Wblock-Reactor)
(0000023A 26 11 1		VLR-Wblock-Reactor)
(0000023D 9 11 1		'VLR-Wblock-Reactor)
(00000240 10)
(00000241 9 46 2		'VLR-SysVar-Reactor)
(00000244 26 10 1		VLR-SysVar-Reactor)
(00000247 9 10 1		'VLR-SysVar-Reactor)
(0000024A 10)
(0000024B 9 45 2		'VLR-DeepClone-Reactor)
(0000024E 26 9 1		VLR-DeepClone-Reactor)
(00000251 9 9 1		'VLR-DeepClone-Reactor)
(00000254 10)
(00000255 9 44 2		'VLR-XREF-Reactor)
(00000258 26 8 1		VLR-XREF-Reactor)
(0000025B 9 8 1		'VLR-XREF-Reactor)
(0000025E 10)
(0000025F 9 43 2		'VLR-Undo-Reactor)
(00000262 26 7 1		VLR-Undo-Reactor)
(00000265 9 7 1		'VLR-Undo-Reactor)
(00000268 10)
(00000269 9 42 2		'VLR-Window-Reactor)
(0000026C 26 6 1		VLR-Window-Reactor)
(0000026F 9 6 1		'VLR-Window-Reactor)
(00000272 10)
(00000273 9 41 2		'VLR-Toolbar-Reactor)
(00000276 26 5 1		VLR-Toolbar-Reactor)
(00000279 9 5 1		'VLR-Toolbar-Reactor)
(0000027C 10)
(0000027D 9 40 2		'VLR-Mouse-Reactor)
(00000280 26 4 1		VLR-Mouse-Reactor)
(00000283 9 4 1		'VLR-Mouse-Reactor)
(00000286 10)
(00000287 9 39 2		'VLR-Miscellaneous-Reactor)
(0000028A 26 3 1		VLR-Miscellaneous-Reactor)
(0000028D 9 3 1		'VLR-Miscellaneous-Reactor)
(00000290 10)
(00000291 9 38 2		'VLR-Object-Reactor)
(00000294 26 2 1		VLR-Object-Reactor)
(00000297 9 2 1		'VLR-Object-Reactor)
(0000029A 10)
(0000029B 1		nil)
(0000029C 10)
(0000029D 9 37 2		'VL-reactor-set-functions)
(000002A0 26 1 1		VL-reactor-set-functions)
(000002A3 9 1 1		'VL-reactor-set-functions)
(000002A6 10)
(000002A7 9 36 2		'VL-create)
(000002AA 26 0 1		VL-create)
(000002AD 9 0 1		'VL-create)
(000002B0 10)
(000002B1 9 35 2		'collect-function-names)
(000002B4 26 255 0		collect-function-names)
(000002B7 9 255 0		'collect-function-names)
(000002BA 10)
(000002BB 1		nil)
(000002BC 10)
(000002BD 1		nil)
(000002BE 28		[ret])
(000002BF 20 0 0 0 0)
(000002C4 1		nil)
(000002C5 10)
(000002C6 9 254 0		'VLREACT)
(000002C9 81 1 80 1 1 0		provide)
(000002CF 10)
(000002D0 1		nil)
(000002D1 10)
(000002D2 3 253 0		*in-Reactor-apply*)
(000002D5 27 253 0		*in-Reactor-apply*)
(000002D8 9 253 0		'*in-Reactor-apply*)
(000002DB 10)
(000002DC 9 34 2		'get-Type)
(000002DF 26 252 0		get-Type)
(000002E2 9 252 0		'get-Type)
(000002E5 10)
(000002E6 9 33 2		'get-Notification-Names)
(000002E9 26 251 0		get-Notification-Names)
(000002EC 9 251 0		'get-Notification-Names)
(000002EF 10)
(000002F0 9 32 2		'add-reactor)
(000002F3 26 250 0		add-reactor)
(000002F6 9 250 0		'add-reactor)
(000002F9 10)
(000002FA 9 31 2		'remove-Reactor)
(000002FD 26 249 0		remove-Reactor)
(00000300 9 249 0		'remove-Reactor)
(00000303 10)
(00000304 9 30 2		'Sync-LISP->CPP)
(00000307 26 248 0		Sync-LISP->CPP)
(0000030A 9 248 0		'Sync-LISP->CPP)
(0000030D 10)
(0000030E 9 29 2		'Reactor-apply)
(00000311 26 247 0		Reactor-apply)
(00000314 9 247 0		'Reactor-apply)
(00000317 10)
(00000318 9 28 2		'check-VL-Reactor)
(0000031B 26 246 0		check-VL-Reactor)
(0000031E 9 246 0		'check-VL-Reactor)
(00000321 10)
(00000322 9 27 2		'VLR-Add)
(00000325 26 245 0		VLR-Add)
(00000328 9 245 0		'VLR-Add)
(0000032B 10)
(0000032C 9 26 2		'VLR-Remove)
(0000032F 26 244 0		VLR-Remove)
(00000332 9 244 0		'VLR-Remove)
(00000335 10)
(00000336 9 25 2		'VLR-Type)
(00000339 26 243 0		VLR-Type)
(0000033C 9 243 0		'VLR-Type)
(0000033F 10)
(00000340 9 242 0		'VL-Reactor)
(00000343 9 241 0		'(instance))
(00000346 3 240 0		*deftype-hook*)
(00000349 52 2 1		)
(0000034C 10)
(0000034D 9 242 0		'VL-Reactor)
(00000350 9 239 0		'(standard-class VL-Reactor :MIXIN :MIXED-PAGE "Generic class for ACAD reactors" ((new-instance . VL-Reactor.new-instance)) nil ((lisplet-reference . T) (index fixnum) (Function-Names list) (user-data . T) (range fixnum)) ((get-Type . VL-Reactor.get-Type) (get-Notification-Names . VL-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object))))
(00000353 53 2 238 0 1 32		find-class<-)
(00000359 10)
(0000035A 9 24 2		'VL-Reactor-p)
(0000035D 26 237 0		VL-Reactor-p)
(00000360 9 237 0		'VL-Reactor-p)
(00000363 10)
(00000364 9 23 2		'VL-Reactor.new-instance)
(00000367 26 236 0		VL-Reactor.new-instance)
(0000036A 9 236 0		'VL-Reactor.new-instance)
(0000036D 10)
(0000036E 1		nil)
(0000036F 10)
(00000370 9 22 2		'VL-Reactor.print-object)
(00000373 26 235 0		VL-Reactor.print-object)
(00000376 9 235 0		'VL-Reactor.print-object)
(00000379 10)
(0000037A 9 21 2		'VL-Reactor.axvlo-dump)
(0000037D 26 234 0		VL-Reactor.axvlo-dump)
(00000380 9 234 0		'VL-Reactor.axvlo-dump)
(00000383 10)
(00000384 9 20 2		'VL-Reactor.axvlo-restore)
(00000387 26 233 0		VL-Reactor.axvlo-restore)
(0000038A 9 233 0		'VL-Reactor.axvlo-restore)
(0000038D 10)
(0000038E 9 19 2		'VL-Reactor.init)
(00000391 26 232 0		VL-Reactor.init)
(00000394 9 232 0		'VL-Reactor.init)
(00000397 10)
(00000398 9 18 2		'VL-Reactor._Reactor-apply)
(0000039B 26 231 0		VL-Reactor._Reactor-apply)
(0000039E 9 231 0		'VL-Reactor._Reactor-apply)
(000003A1 10)
(000003A2 9 17 2		'VL-Reactor.Reactor-apply)
(000003A5 26 230 0		VL-Reactor.Reactor-apply)
(000003A8 9 230 0		'VL-Reactor.Reactor-apply)
(000003AB 10)
(000003AC 9 16 2		'VL-Reactor.add-reactor)
(000003AF 26 229 0		VL-Reactor.add-reactor)
(000003B2 9 229 0		'VL-Reactor.add-reactor)
(000003B5 10)
(000003B6 9 15 2		'VL-Reactor.remove-Reactor)
(000003B9 26 228 0		VL-Reactor.remove-Reactor)
(000003BC 9 228 0		'VL-Reactor.remove-Reactor)
(000003BF 10)
(000003C0 1		nil)
(000003C1 10)
(000003C2 9 14 2		'VL-Reactor.max-reaction-number)
(000003C5 26 227 0		VL-Reactor.max-reaction-number)
(000003C8 9 227 0		'VL-Reactor.max-reaction-number)
(000003CB 10)
(000003CC 9 13 2		'VL-Reactor.reaction-number-valid-p)
(000003CF 26 226 0		VL-Reactor.reaction-number-valid-p)
(000003D2 9 226 0		'VL-Reactor.reaction-number-valid-p)
(000003D5 10)
(000003D6 9 12 2		'VL-Reactor.index->function)
(000003D9 26 225 0		VL-Reactor.index->function)
(000003DC 9 225 0		'VL-Reactor.index->function)
(000003DF 10)
(000003E0 9 11 2		'VL-Reactor.Reaction-name->index)
(000003E3 26 224 0		VL-Reactor.Reaction-name->index)
(000003E6 9 224 0		'VL-Reactor.Reaction-name->index)
(000003E9 10)
(000003EA 9 10 2		'VL-Reactor.index->Reaction-name)
(000003ED 26 223 0		VL-Reactor.index->Reaction-name)
(000003F0 9 223 0		'VL-Reactor.index->Reaction-name)
(000003F3 10)
(000003F4 9 9 2		'VL-Reactor.reactions-list)
(000003F7 26 222 0		VL-Reactor.reactions-list)
(000003FA 9 222 0		'VL-Reactor.reactions-list)
(000003FD 10)
(000003FE 9 8 2		'VLR-Reactions)
(00000401 26 221 0		VLR-Reactions)
(00000404 9 221 0		'VLR-Reactions)
(00000407 10)
(00000408 9 7 2		'VL-Reactor.reactions-list<-)
(0000040B 26 220 0		VL-Reactor.reactions-list<-)
(0000040E 9 220 0		'VL-Reactor.reactions-list<-)
(00000411 10)
(00000412 9 6 2		'VL-Reactor.added-p)
(00000415 26 219 0		VL-Reactor.added-p)
(00000418 9 219 0		'VL-Reactor.added-p)
(0000041B 10)
(0000041C 9 5 2		'VL-Reactor.check-added-p)
(0000041F 26 218 0		VL-Reactor.check-added-p)
(00000422 9 218 0		'VL-Reactor.check-added-p)
(00000425 10)
(00000426 9 4 2		'VLR-added-p)
(00000429 26 217 0		VLR-added-p)
(0000042C 9 217 0		'VLR-added-p)
(0000042F 10)
(00000430 9 3 2		'VL-Reactor.add)
(00000433 26 216 0		VL-Reactor.add)
(00000436 9 216 0		'VL-Reactor.add)
(00000439 10)
(0000043A 9 2 2		'VL-Reactor.reInit)
(0000043D 26 215 0		VL-Reactor.reInit)
(00000440 9 215 0		'VL-Reactor.reInit)
(00000443 10)
(00000444 9 1 2		'VL-Reactor.remove)
(00000447 26 214 0		VL-Reactor.remove)
(0000044A 9 214 0		'VL-Reactor.remove)
(0000044D 10)
(0000044E 9 0 2		'VLR-Reaction-Set)
(00000451 26 213 0		VLR-Reaction-Set)
(00000454 9 213 0		'VLR-Reaction-Set)
(00000457 10)
(00000458 9 255 1		'VL-Reactor.Set-Slot)
(0000045B 26 212 0		VL-Reactor.Set-Slot)
(0000045E 9 212 0		'VL-Reactor.Set-Slot)
(00000461 10)
(00000462 9 254 1		'VL-Reactor.Set-Slot-I)
(00000465 26 211 0		VL-Reactor.Set-Slot-I)
(00000468 9 211 0		'VL-Reactor.Set-Slot-I)
(0000046B 10)
(0000046C 9 253 1		'VL-Reactor.Clear-ALL-Slots)
(0000046F 26 210 0		VL-Reactor.Clear-ALL-Slots)
(00000472 9 210 0		'VL-Reactor.Clear-ALL-Slots)
(00000475 10)
(00000476 9 252 1		'VL-Reactor.Slot-LISP->CPP-I)
(00000479 26 209 0		VL-Reactor.Slot-LISP->CPP-I)
(0000047C 9 209 0		'VL-Reactor.Slot-LISP->CPP-I)
(0000047F 10)
(00000480 9 251 1		'VL-Reactor.All-Slots-LISP->CPP)
(00000483 26 208 0		VL-Reactor.All-Slots-LISP->CPP)
(00000486 9 208 0		'VL-Reactor.All-Slots-LISP->CPP)
(00000489 10)
(0000048A 9 250 1		'VL-Reactor.data)
(0000048D 26 207 0		VL-Reactor.data)
(00000490 9 207 0		'VL-Reactor.data)
(00000493 10)
(00000494 9 249 1		'VLR-Data)
(00000497 26 206 0		VLR-Data)
(0000049A 9 206 0		'VLR-Data)
(0000049D 10)
(0000049E 9 248 1		'VL-Reactor.data<-)
(000004A1 26 205 0		VL-Reactor.data<-)
(000004A4 9 205 0		'VL-Reactor.data<-)
(000004A7 10)
(000004A8 9 247 1		'VLR-Data-Set)
(000004AB 26 204 0		VLR-Data-Set)
(000004AE 9 204 0		'VLR-Data-Set)
(000004B1 10)
(000004B2 9 246 1		'VL-Reactor.range)
(000004B5 26 203 0		VL-Reactor.range)
(000004B8 9 203 0		'VL-Reactor.range)
(000004BB 10)
(000004BC 9 245 1		'VL-Reactor.range<-)
(000004BF 26 202 0		VL-Reactor.range<-)
(000004C2 9 202 0		'VL-Reactor.range<-)
(000004C5 10)
(000004C6 9 244 1		'VLR-notification)
(000004C9 26 201 0		VLR-notification)
(000004CC 9 201 0		'VLR-notification)
(000004CF 10)
(000004D0 9 243 1		'VLR-set-notification)
(000004D3 26 200 0		VLR-set-notification)
(000004D6 9 200 0		'VLR-set-notification)
(000004D9 10)
(000004DA 9 242 1		'VL-Reactor.document)
(000004DD 26 199 0		VL-Reactor.document)
(000004E0 9 199 0		'VL-Reactor.document)
(000004E3 10)
(000004E4 9 241 1		'VL-Reactor.document<-)
(000004E7 26 198 0		VL-Reactor.document<-)
(000004EA 9 198 0		'VL-Reactor.document<-)
(000004ED 10)
(000004EE 9 240 1		'VLR-document)
(000004F1 26 197 0		VLR-document)
(000004F4 9 197 0		'VLR-document)
(000004F7 10)
(000004F8 9 239 1		'VL-document-Set)
(000004FB 26 196 0		VL-document-Set)
(000004FE 9 196 0		'VL-document-Set)
(00000501 10)
(00000502 9 238 1		'VL-Reactor.prepare-reactions-list)
(00000505 26 195 0		VL-Reactor.prepare-reactions-list)
(00000508 9 195 0		'VL-Reactor.prepare-reactions-list)
(0000050B 10)
(0000050C 9 237 1		'VL-Reactor.inspect-object)
(0000050F 26 194 0		VL-Reactor.inspect-object)
(00000512 9 194 0		'VL-Reactor.inspect-object)
(00000515 28		[ret])
(00000516 20 0 0 0 0)
(0000051B 1		nil)
(0000051C 10)
(0000051D 1		nil)
(0000051E 10)
(0000051F 15 0 0		JMP 00000522)
(00000522 9 236 1		'nil)
(00000525 53 1 75 1 1 32		make-macro)
(0000052B 26 193 0		VL-makeRegistrationVectorPrototypeM)
(0000052E 9 193 0		'VL-makeRegistrationVectorPrototypeM)
(00000531 10)
(00000532 9 235 1		'VL-makeRegistrationVectorPrototype)
(00000535 26 192 0		VL-makeRegistrationVectorPrototype)
(00000538 9 192 0		'VL-makeRegistrationVectorPrototype)
(0000053B 10)
(0000053C 50 19		19)
(0000053E 81 1 191 0 1 0		make-vector)
(00000544 26 190 0		*VLAReactor-Registration-Vector*)
(00000547 9 190 0		'*VLAReactor-Registration-Vector*)
(0000054A 10)
(0000054B 1		nil)
(0000054C 27 189 0		*VLAReactor-Registration-ALIST*)
(0000054F 9 189 0		'*VLAReactor-Registration-ALIST*)
(00000552 10)
(00000553 9 234 1		'VL-getRegistrationVector)
(00000556 26 188 0		VL-getRegistrationVector)
(00000559 9 188 0		'VL-getRegistrationVector)
(0000055C 10)
(0000055D 9 233 1		'VL-Reactor.getRegKey)
(00000560 26 187 0		VL-Reactor.getRegKey)
(00000563 9 187 0		'VL-Reactor.getRegKey)
(00000566 10)
(00000567 9 232 1		'VL-Reactor.getDictKey)
(0000056A 26 186 0		VL-Reactor.getDictKey)
(0000056D 9 186 0		'VL-Reactor.getDictKey)
(00000570 10)
(00000571 9 231 1		'VLR-Reactor.getDictKey)
(00000574 26 185 0		VLR-Reactor.getDictKey)
(00000577 9 185 0		'VLR-Reactor.getDictKey)
(0000057A 10)
(0000057B 9 230 1		'VL-Reactor._registrate)
(0000057E 26 184 0		VL-Reactor._registrate)
(00000581 9 184 0		'VL-Reactor._registrate)
(00000584 10)
(00000585 9 229 1		'VL-Reactor._unregistrate)
(00000588 26 183 0		VL-Reactor._unregistrate)
(0000058B 9 183 0		'VL-Reactor._unregistrate)
(0000058E 28		[ret])
(0000058F 20 0 0 0 0)
(00000594 1		nil)
(00000595 10)
(00000596 9 182 0		'gobjrct)
(00000599 81 1 80 1 1 0		provide)
(0000059F 10)
(000005A0 9 254 0		'VLREACT)
(000005A3 81 1 78 1 1 0		require)
(000005A9 10)
(000005AA 1		nil)
(000005AB 10)
(000005AC 9 181 0		'VL-Object-Reactor)
(000005AF 9 180 0		'(VL-Reactor))
(000005B2 3 240 0		*deftype-hook*)
(000005B5 52 2 1		)
(000005B8 10)
(000005B9 9 181 0		'VL-Object-Reactor)
(000005BC 9 179 0		'(standard-class VL-Object-Reactor :MIXIN :MIXED-PAGE "Generic Class for Object reactors" ((new-instance . VL-Object-Reactor.new-instance)) nil ((lisplet-reference . T) (index fixnum) (Function-Names list) (user-data . T) (range fixnum) (reactor-owners . T)) ((get-Type . VL-Object-Reactor.get-Type) (get-Notification-Names . VL-Object-Reactor.get-Notification-Names) (axvlo-dump . VL-Object-Reactor.axvlo-dump) (axvlo-restore . VL-Object-Reactor.axvlo-restore) (Reactor-apply . VL-Object-Reactor.Reactor-apply) (add-reactor . VL-Object-Reactor.add-reactor) (remove-Reactor . VL-Object-Reactor.remove-Reactor) (Sync-LISP->CPP . VL-Object-Reactor.Sync-LISP->CPP) (print-object . VL-Reactor.print-object) (inspect-object . VL-Object-Reactor.inspect-object))))
(000005BF 53 2 238 0 1 32		find-class<-)
(000005C5 10)
(000005C6 9 228 1		'VL-Object-Reactor-p)
(000005C9 26 178 0		VL-Object-Reactor-p)
(000005CC 9 178 0		'VL-Object-Reactor-p)
(000005CF 10)
(000005D0 9 227 1		'VL-Object-Reactor.new-instance)
(000005D3 26 177 0		VL-Object-Reactor.new-instance)
(000005D6 9 177 0		'VL-Object-Reactor.new-instance)
(000005D9 10)
(000005DA 1		nil)
(000005DB 10)
(000005DC 9 226 1		'VL-Object-Reactor.axvlo-dump)
(000005DF 26 176 0		VL-Object-Reactor.axvlo-dump)
(000005E2 9 176 0		'VL-Object-Reactor.axvlo-dump)
(000005E5 10)
(000005E6 9 225 1		'VL-Object-Reactor.axvlo-restore)
(000005E9 26 175 0		VL-Object-Reactor.axvlo-restore)
(000005EC 9 175 0		'VL-Object-Reactor.axvlo-restore)
(000005EF 10)
(000005F0 9 224 1		'VL-Object-Reactor)
(000005F3 26 181 0		VL-Object-Reactor)
(000005F6 9 181 0		'VL-Object-Reactor)
(000005F9 10)
(000005FA 9 223 1		'VL-Object-Reactor.init)
(000005FD 26 174 0		VL-Object-Reactor.init)
(00000600 9 174 0		'VL-Object-Reactor.init)
(00000603 10)
(00000604 1		nil)
(00000605 10)
(00000606 9 222 1		'VL-Object-Reactor.Reactor-apply)
(00000609 26 173 0		VL-Object-Reactor.Reactor-apply)
(0000060C 9 173 0		'VL-Object-Reactor.Reactor-apply)
(0000060F 10)
(00000610 9 221 1		'VL-Object-Reactor.add-reactor)
(00000613 26 172 0		VL-Object-Reactor.add-reactor)
(00000616 9 172 0		'VL-Object-Reactor.add-reactor)
(00000619 10)
(0000061A 9 220 1		'VL-Object-Reactor.remove-Reactor)
(0000061D 26 171 0		VL-Object-Reactor.remove-Reactor)
(00000620 9 171 0		'VL-Object-Reactor.remove-Reactor)
(00000623 10)
(00000624 9 219 1		'VL-Object-Reactor.add)
(00000627 26 170 0		VL-Object-Reactor.add)
(0000062A 9 170 0		'VL-Object-Reactor.add)
(0000062D 10)
(0000062E 9 218 1		'VL-Object-Reactor.remove)
(00000631 26 169 0		VL-Object-Reactor.remove)
(00000634 9 169 0		'VL-Object-Reactor.remove)
(00000637 10)
(00000638 9 217 1		'check-Object-reactor)
(0000063B 26 168 0		check-Object-reactor)
(0000063E 9 168 0		'check-Object-reactor)
(00000641 10)
(00000642 9 216 1		'VL-Object-Reactor.find-owner)
(00000645 26 167 0		VL-Object-Reactor.find-owner)
(00000648 9 167 0		'VL-Object-Reactor.find-owner)
(0000064B 10)
(0000064C 1		nil)
(0000064D 10)
(0000064E 1		nil)
(0000064F 10)
(00000650 9 215 1		'VL-Object-Reactor.add-owner)
(00000653 26 166 0		VL-Object-Reactor.add-owner)
(00000656 9 166 0		'VL-Object-Reactor.add-owner)
(00000659 10)
(0000065A 9 214 1		'VLR-Owner-Add)
(0000065D 26 165 0		VLR-Owner-Add)
(00000660 9 165 0		'VLR-Owner-Add)
(00000663 10)
(00000664 9 213 1		'VL-Object-Reactor.remove-owner)
(00000667 26 164 0		VL-Object-Reactor.remove-owner)
(0000066A 9 164 0		'VL-Object-Reactor.remove-owner)
(0000066D 10)
(0000066E 9 212 1		'VLR-Owner-Remove)
(00000671 26 163 0		VLR-Owner-Remove)
(00000674 9 163 0		'VLR-Owner-Remove)
(00000677 10)
(00000678 9 211 1		'VL-Object-Reactor.get-owners)
(0000067B 26 162 0		VL-Object-Reactor.get-owners)
(0000067E 9 162 0		'VL-Object-Reactor.get-owners)
(00000681 10)
(00000682 9 210 1		'VLR-Owners)
(00000685 26 161 0		VLR-Owners)
(00000688 9 161 0		'VLR-Owners)
(0000068B 10)
(0000068C 9 209 1		'VL-Object-Reactor.add-owner-LISP->CPP)
(0000068F 26 160 0		VL-Object-Reactor.add-owner-LISP->CPP)
(00000692 9 160 0		'VL-Object-Reactor.add-owner-LISP->CPP)
(00000695 10)
(00000696 9 208 1		'VL-Object-Reactor.remove-owner-LISP->CPP)
(00000699 26 159 0		VL-Object-Reactor.remove-owner-LISP->CPP)
(0000069C 9 159 0		'VL-Object-Reactor.remove-owner-LISP->CPP)
(0000069F 10)
(000006A0 9 207 1		'VL-Object-Reactor.prepare-reactions-list)
(000006A3 26 158 0		VL-Object-Reactor.prepare-reactions-list)
(000006A6 9 158 0		'VL-Object-Reactor.prepare-reactions-list)
(000006A9 10)
(000006AA 9 206 1		'VL-Object-Reactor.inspect-object)
(000006AD 26 157 0		VL-Object-Reactor.inspect-object)
(000006B0 9 157 0		'VL-Object-Reactor.inspect-object)
(000006B3 28		[ret])
(000006B4 20 0 0 0 0)
(000006B9 1		nil)
(000006BA 10)
(000006BB 1		nil)
(000006BC 10)
(000006BD 15 0 0		JMP 000006C0)
(000006C0 9 205 1		'nil)
(000006C3 53 1 75 1 1 32		make-macro)
(000006C9 26 156 0		make-reactor-class)
(000006CC 9 156 0		'make-reactor-class)
(000006CF 28		[ret])
(000006D0 20 0 0 0 0)
(000006D5 1		nil)
(000006D6 10)
(000006D7 9 73 1		'Linker-Reactor)
(000006DA 9 180 0		'(VL-Reactor))
(000006DD 3 240 0		*deftype-hook*)
(000006E0 52 2 1		)
(000006E3 10)
(000006E4 9 73 1		'Linker-Reactor)
(000006E7 9 155 0		'(standard-class Linker-Reactor :MIXIN :MIXED-PAGE "Class for Linker-Reactor reactors" ((new-instance . Linker-Reactor.new-instance)) nil ((lisplet-reference . T) (index fixnum) (Function-Names list) (user-data . T) (range fixnum)) ((get-Type . Linker-Reactor.get-Type) (get-Notification-Names . Linker-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-rxAppLoaded :VLR-rxAppUnLoaded) (reactor-type . 0))))
(000006EA 53 2 238 0 1 32		find-class<-)
(000006F0 10)
(000006F1 9 204 1		'Linker-Reactor-p)
(000006F4 26 154 0		Linker-Reactor-p)
(000006F7 9 154 0		'Linker-Reactor-p)
(000006FA 10)
(000006FB 9 203 1		'Linker-Reactor.new-instance)
(000006FE 26 153 0		Linker-Reactor.new-instance)
(00000701 9 153 0		'Linker-Reactor.new-instance)
(00000704 10)
(00000705 1		nil)
(00000706 10)
(00000707 9 73 1		'Linker-Reactor)
(0000070A 9 152 0		"VLR-")
(0000070D 9 73 1		'Linker-Reactor)
(00000710 81 2 151 0 1 0		concat)
(00000716 81 1 150 0 1 0		intern)
(0000071C 53 2 149 0 1 32		mk-al-type)
(00000722 10)
(00000723 9 86 2		'Linker-Reactor)
(00000726 26 73 1		Linker-Reactor)
(00000729 9 73 1		'Linker-Reactor)
(0000072C 10)
(0000072D 9 202 1		'Linker-Reactor.get-Type)
(00000730 26 148 0		Linker-Reactor.get-Type)
(00000733 9 148 0		'Linker-Reactor.get-Type)
(00000736 10)
(00000737 9 201 1		'Linker-Reactor.get-Notification-Names)
(0000073A 26 147 0		Linker-Reactor.get-Notification-Names)
(0000073D 9 147 0		'Linker-Reactor.get-Notification-Names)
(00000740 10)
(00000741 1		nil)
(00000742 10)
(00000743 9 72 1		'Editor-Reactor)
(00000746 9 180 0		'(VL-Reactor))
(00000749 3 240 0		*deftype-hook*)
(0000074C 52 2 1		)
(0000074F 10)
(00000750 9 72 1		'Editor-Reactor)
(00000753 9 146 0		'(standard-class Editor-Reactor :MIXIN :MIXED-PAGE "Class for Editor-Reactor reactors" ((new-instance . Editor-Reactor.new-instance)) nil ((lisplet-reference . T) (index fixnum) (Function-Names list) (user-data . T) (range fixnum)) ((get-Type . Editor-Reactor.get-Type) (get-Notification-Names . Editor-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-unknownCommand :VLR-commandWillStart :VLR-commandEnded :VLR-commandCancelled :VLR-commandFailed :VLR-lispWillStart :VLR-lispEnded :VLR-lispCancelled :VLR-beginClose :VLR-beginDxfIn :VLR-abortDxfIn :VLR-dxfInComplete :VLR-beginDxfOut :VLR-abortDxfOut :VLR-dxfOutComplete :VLR-beginDwgOpen :VLR-endDwgOpen :VLR-dwgFileOpened :VLR-databaseConstructed :VLR-databaseToBeDestroyed :VLR-beginSave :VLR-saveComplete :VLR-sysVarWillChange :VLR-sysVarChanged) (reactor-type . 1))))
(00000756 53 2 238 0 1 32		find-class<-)
(0000075C 10)
(0000075D 9 200 1		'Editor-Reactor-p)
(00000760 26 145 0		Editor-Reactor-p)
(00000763 9 145 0		'Editor-Reactor-p)
(00000766 10)
(00000767 9 199 1		'Editor-Reactor.new-instance)
(0000076A 26 144 0		Editor-Reactor.new-instance)
(0000076D 9 144 0		'Editor-Reactor.new-instance)
(00000770 10)
(00000771 1		nil)
(00000772 10)
(00000773 9 72 1		'Editor-Reactor)
(00000776 9 152 0		"VLR-")
(00000779 9 72 1		'Editor-Reactor)
(0000077C 81 2 151 0 1 0		concat)
(00000782 81 1 150 0 1 0		intern)
(00000788 53 2 149 0 1 32		mk-al-type)
(0000078E 10)
(0000078F 9 85 2		'Editor-Reactor)
(00000792 26 72 1		Editor-Reactor)
(00000795 9 72 1		'Editor-Reactor)
(00000798 10)
(00000799 9 198 1		'Editor-Reactor.get-Type)
(0000079C 26 143 0		Editor-Reactor.get-Type)
(0000079F 9 143 0		'Editor-Reactor.get-Type)
(000007A2 10)
(000007A3 9 197 1		'Editor-Reactor.get-Notification-Names)
(000007A6 26 142 0		Editor-Reactor.get-Notification-Names)
(000007A9 9 142 0		'Editor-Reactor.get-Notification-Names)
(000007AC 10)
(000007AD 1		nil)
(000007AE 10)
(000007AF 9 71 1		'AcDb-Reactor)
(000007B2 9 180 0		'(VL-Reactor))
(000007B5 3 240 0		*deftype-hook*)
(000007B8 52 2 1		)
(000007BB 10)
(000007BC 9 71 1		'AcDb-Reactor)
(000007BF 9 141 0		'(standard-class AcDb-Reactor :MIXIN :MIXED-PAGE "Class for AcDb-Reactor reactors" ((new-instance . AcDb-Reactor.new-instance)) nil ((lisplet-reference . T) (index fixnum) (Function-Names list) (user-data . T) (range fixnum)) ((get-Type . AcDb-Reactor.get-Type) (get-Notification-Names . AcDb-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-objectAppended :VLR-objectUnAppended :VLR-objectReAppended :VLR-objectOpenedForModify :VLR-objectModified :VLR-objectErased :VLR-objectUnErased) (reactor-type . 2))))
(000007C2 53 2 238 0 1 32		find-class<-)
(000007C8 10)
(000007C9 9 196 1		'AcDb-Reactor-p)
(000007CC 26 140 0		AcDb-Reactor-p)
(000007CF 9 140 0		'AcDb-Reactor-p)
(000007D2 10)
(000007D3 9 195 1		'AcDb-Reactor.new-instance)
(000007D6 26 139 0		AcDb-Reactor.new-instance)
(000007D9 9 139 0		'AcDb-Reactor.new-instance)
(000007DC 10)
(000007DD 1		nil)
(000007DE 10)
(000007DF 9 71 1		'AcDb-Reactor)
(000007E2 9 152 0		"VLR-")
(000007E5 9 71 1		'AcDb-Reactor)
(000007E8 81 2 151 0 1 0		concat)
(000007EE 81 1 150 0 1 0		intern)
(000007F4 53 2 149 0 1 32		mk-al-type)
(000007FA 10)
(000007FB 9 84 2		'AcDb-Reactor)
(000007FE 26 71 1		AcDb-Reactor)
(00000801 9 71 1		'AcDb-Reactor)
(00000804 10)
(00000805 9 194 1		'AcDb-Reactor.get-Type)
(00000808 26 138 0		AcDb-Reactor.get-Type)
(0000080B 9 138 0		'AcDb-Reactor.get-Type)
(0000080E 10)
(0000080F 9 193 1		'AcDb-Reactor.get-Notification-Names)
(00000812 26 137 0		AcDb-Reactor.get-Notification-Names)
(00000815 9 137 0		'AcDb-Reactor.get-Notification-Names)
(00000818 10)
(00000819 1		nil)
(0000081A 10)
(0000081B 9 70 1		'DocManager-Reactor)
(0000081E 9 180 0		'(VL-Reactor))
(00000821 3 240 0		*deftype-hook*)
(00000824 52 2 1		)
(00000827 10)
(00000828 9 70 1		'DocManager-Reactor)
(0000082B 9 136 0		'(standard-class DocManager-Reactor :MIXIN :MIXED-PAGE "Class for DocManager-Reactor reactors" ((new-instance . DocManager-Reactor.new-instance)) nil ((lisplet-reference . T) (index fixnum) (Function-Names list) (user-data . T) (range fixnum)) ((get-Type . DocManager-Reactor.get-Type) (get-Notification-Names . DocManager-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-documentCreated :VLR-documentToBeDestroyed :VLR-documentLockModeWillChange :VLR-documentLockModeChangeVetoed :VLR-documentLockModeChanged :VLR-documentBecameCurrent :VLR-documentToBeActivated :VLR-documentToBeDeactivated) (reactor-type . 3))))
(0000082E 53 2 238 0 1 32		find-class<-)
(00000834 10)
(00000835 9 192 1		'DocManager-Reactor-p)
(00000838 26 135 0		DocManager-Reactor-p)
(0000083B 9 135 0		'DocManager-Reactor-p)
(0000083E 10)
(0000083F 9 191 1		'DocManager-Reactor.new-instance)
(00000842 26 134 0		DocManager-Reactor.new-instance)
(00000845 9 134 0		'DocManager-Reactor.new-instance)
(00000848 10)
(00000849 1		nil)
(0000084A 10)
(0000084B 9 70 1		'DocManager-Reactor)
(0000084E 9 152 0		"VLR-")
(00000851 9 70 1		'DocManager-Reactor)
(00000854 81 2 151 0 1 0		concat)
(0000085A 81 1 150 0 1 0		intern)
(00000860 53 2 149 0 1 32		mk-al-type)
(00000866 10)
(00000867 9 83 2		'DocManager-Reactor)
(0000086A 26 70 1		DocManager-Reactor)
(0000086D 9 70 1		'DocManager-Reactor)
(00000870 10)
(00000871 9 190 1		'DocManager-Reactor.get-Type)
(00000874 26 133 0		DocManager-Reactor.get-Type)
(00000877 9 133 0		'DocManager-Reactor.get-Type)
(0000087A 10)
(0000087B 9 189 1		'DocManager-Reactor.get-Notification-Names)
(0000087E 26 132 0		DocManager-Reactor.get-Notification-Names)
(00000881 9 132 0		'DocManager-Reactor.get-Notification-Names)
(00000884 10)
(00000885 1		nil)
(00000886 10)
(00000887 9 69 1		'Command-Reactor)
(0000088A 9 180 0		'(VL-Reactor))
(0000088D 3 240 0		*deftype-hook*)
(00000890 52 2 1		)
(00000893 10)
(00000894 9 69 1		'Command-Reactor)
(00000897 9 131 0		'(standard-class Command-Reactor :MIXIN :MIXED-PAGE "Class for Command-Reactor reactors" ((new-instance . Command-Reactor.new-instance)) nil ((lisplet-reference . T) (index fixnum) (Function-Names list) (user-data . T) (range fixnum)) ((get-Type . Command-Reactor.get-Type) (get-Notification-Names . Command-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-unknownCommand :VLR-commandWillStart :VLR-commandEnded :VLR-commandCancelled :VLR-commandFailed) (reactor-type . 4))))
(0000089A 53 2 238 0 1 32		find-class<-)
(000008A0 10)
(000008A1 9 188 1		'Command-Reactor-p)
(000008A4 26 130 0		Command-Reactor-p)
(000008A7 9 130 0		'Command-Reactor-p)
(000008AA 10)
(000008AB 9 187 1		'Command-Reactor.new-instance)
(000008AE 26 129 0		Command-Reactor.new-instance)
(000008B1 9 129 0		'Command-Reactor.new-instance)
(000008B4 10)
(000008B5 1		nil)
(000008B6 10)
(000008B7 9 69 1		'Command-Reactor)
(000008BA 9 152 0		"VLR-")
(000008BD 9 69 1		'Command-Reactor)
(000008C0 81 2 151 0 1 0		concat)
(000008C6 81 1 150 0 1 0		intern)
(000008CC 53 2 149 0 1 32		mk-al-type)
(000008D2 10)
(000008D3 9 82 2		'Command-Reactor)
(000008D6 26 69 1		Command-Reactor)
(000008D9 9 69 1		'Command-Reactor)
(000008DC 10)
(000008DD 9 186 1		'Command-Reactor.get-Type)
(000008E0 26 128 0		Command-Reactor.get-Type)
(000008E3 9 128 0		'Command-Reactor.get-Type)
(000008E6 10)
(000008E7 9 185 1		'Command-Reactor.get-Notification-Names)
(000008EA 26 127 0		Command-Reactor.get-Notification-Names)
(000008ED 9 127 0		'Command-Reactor.get-Notification-Names)
(000008F0 10)
(000008F1 1		nil)
(000008F2 10)
(000008F3 9 68 1		'Lisp-Reactor)
(000008F6 9 180 0		'(VL-Reactor))
(000008F9 3 240 0		*deftype-hook*)
(000008FC 52 2 1		)
(000008FF 10)
(00000900 9 68 1		'Lisp-Reactor)
(00000903 9 126 0		'(standard-class Lisp-Reactor :MIXIN :MIXED-PAGE "Class for Lisp-Reactor reactors" ((new-instance . Lisp-Reactor.new-instance)) nil ((lisplet-reference . T) (index fixnum) (Function-Names list) (user-data . T) (range fixnum)) ((get-Type . Lisp-Reactor.get-Type) (get-Notification-Names . Lisp-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-lispWillStart :VLR-lispEnded :VLR-lispCancelled) (reactor-type . 5))))
(00000906 53 2 238 0 1 32		find-class<-)
(0000090C 10)
(0000090D 9 184 1		'Lisp-Reactor-p)
(00000910 26 125 0		Lisp-Reactor-p)
(00000913 9 125 0		'Lisp-Reactor-p)
(00000916 10)
(00000917 9 183 1		'Lisp-Reactor.new-instance)
(0000091A 26 124 0		Lisp-Reactor.new-instance)
(0000091D 9 124 0		'Lisp-Reactor.new-instance)
(00000920 10)
(00000921 1		nil)
(00000922 10)
(00000923 9 68 1		'Lisp-Reactor)
(00000926 9 152 0		"VLR-")
(00000929 9 68 1		'Lisp-Reactor)
(0000092C 81 2 151 0 1 0		concat)
(00000932 81 1 150 0 1 0		intern)
(00000938 53 2 149 0 1 32		mk-al-type)
(0000093E 10)
(0000093F 9 81 2		'Lisp-Reactor)
(00000942 26 68 1		Lisp-Reactor)
(00000945 9 68 1		'Lisp-Reactor)
(00000948 10)
(00000949 9 182 1		'Lisp-Reactor.get-Type)
(0000094C 26 123 0		Lisp-Reactor.get-Type)
(0000094F 9 123 0		'Lisp-Reactor.get-Type)
(00000952 10)
(00000953 9 181 1		'Lisp-Reactor.get-Notification-Names)
(00000956 26 122 0		Lisp-Reactor.get-Notification-Names)
(00000959 9 122 0		'Lisp-Reactor.get-Notification-Names)
(0000095C 10)
(0000095D 1		nil)
(0000095E 10)
(0000095F 9 67 1		'DXF-Reactor)
(00000962 9 180 0		'(VL-Reactor))
(00000965 3 240 0		*deftype-hook*)
(00000968 52 2 1		)
(0000096B 10)
(0000096C 9 67 1		'DXF-Reactor)
(0000096F 9 121 0		'(standard-class DXF-Reactor :MIXIN :MIXED-PAGE "Class for DXF-Reactor reactors" ((new-instance . DXF-Reactor.new-instance)) nil ((lisplet-reference . T) (index fixnum) (Function-Names list) (user-data . T) (range fixnum)) ((get-Type . DXF-Reactor.get-Type) (get-Notification-Names . DXF-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-beginDxfIn :VLR-abortDxfIn :VLR-dxfInComplete :VLR-beginDxfOut :VLR-abortDxfOut :VLR-dxfOutComplete) (reactor-type . 6))))
(00000972 53 2 238 0 1 32		find-class<-)
(00000978 10)
(00000979 9 180 1		'DXF-Reactor-p)
(0000097C 26 120 0		DXF-Reactor-p)
(0000097F 9 120 0		'DXF-Reactor-p)
(00000982 10)
(00000983 9 179 1		'DXF-Reactor.new-instance)
(00000986 26 119 0		DXF-Reactor.new-instance)
(00000989 9 119 0		'DXF-Reactor.new-instance)
(0000098C 10)
(0000098D 1		nil)
(0000098E 10)
(0000098F 9 67 1		'DXF-Reactor)
(00000992 9 152 0		"VLR-")
(00000995 9 67 1		'DXF-Reactor)
(00000998 81 2 151 0 1 0		concat)
(0000099E 81 1 150 0 1 0		intern)
(000009A4 53 2 149 0 1 32		mk-al-type)
(000009AA 10)
(000009AB 9 80 2		'DXF-Reactor)
(000009AE 26 67 1		DXF-Reactor)
(000009B1 9 67 1		'DXF-Reactor)
(000009B4 10)
(000009B5 9 178 1		'DXF-Reactor.get-Type)
(000009B8 26 118 0		DXF-Reactor.get-Type)
(000009BB 9 118 0		'DXF-Reactor.get-Type)
(000009BE 10)
(000009BF 9 177 1		'DXF-Reactor.get-Notification-Names)
(000009C2 26 117 0		DXF-Reactor.get-Notification-Names)
(000009C5 9 117 0		'DXF-Reactor.get-Notification-Names)
(000009C8 10)
(000009C9 1		nil)
(000009CA 10)
(000009CB 9 66 1		'DWG-Reactor)
(000009CE 9 180 0		'(VL-Reactor))
(000009D1 3 240 0		*deftype-hook*)
(000009D4 52 2 1		)
(000009D7 10)
(000009D8 9 66 1		'DWG-Reactor)
(000009DB 9 116 0		'(standard-class DWG-Reactor :MIXIN :MIXED-PAGE "Class for DWG-Reactor reactors" ((new-instance . DWG-Reactor.new-instance)) nil ((lisplet-reference . T) (index fixnum) (Function-Names list) (user-data . T) (range fixnum)) ((get-Type . DWG-Reactor.get-Type) (get-Notification-Names . DWG-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-beginDwgOpen :VLR-endDwgOpen :VLR-dwgFileOpened :VLR-databaseConstructed :VLR-databaseToBeDestroyed :VLR-beginSave :VLR-saveComplete :VLR-beginClose) (reactor-type . 7))))
(000009DE 53 2 238 0 1 32		find-class<-)
(000009E4 10)
(000009E5 9 176 1		'DWG-Reactor-p)
(000009E8 26 115 0		DWG-Reactor-p)
(000009EB 9 115 0		'DWG-Reactor-p)
(000009EE 10)
(000009EF 9 175 1		'DWG-Reactor.new-instance)
(000009F2 26 114 0		DWG-Reactor.new-instance)
(000009F5 9 114 0		'DWG-Reactor.new-instance)
(000009F8 10)
(000009F9 1		nil)
(000009FA 10)
(000009FB 9 66 1		'DWG-Reactor)
(000009FE 9 152 0		"VLR-")
(00000A01 9 66 1		'DWG-Reactor)
(00000A04 81 2 151 0 1 0		concat)
(00000A0A 81 1 150 0 1 0		intern)
(00000A10 53 2 149 0 1 32		mk-al-type)
(00000A16 10)
(00000A17 9 79 2		'DWG-Reactor)
(00000A1A 26 66 1		DWG-Reactor)
(00000A1D 9 66 1		'DWG-Reactor)
(00000A20 10)
(00000A21 9 174 1		'DWG-Reactor.get-Type)
(00000A24 26 113 0		DWG-Reactor.get-Type)
(00000A27 9 113 0		'DWG-Reactor.get-Type)
(00000A2A 10)
(00000A2B 9 173 1		'DWG-Reactor.get-Notification-Names)
(00000A2E 26 112 0		DWG-Reactor.get-Notification-Names)
(00000A31 9 112 0		'DWG-Reactor.get-Notification-Names)
(00000A34 10)
(00000A35 1		nil)
(00000A36 10)
(00000A37 9 63 1		'SysVar-Reactor)
(00000A3A 9 180 0		'(VL-Reactor))
(00000A3D 3 240 0		*deftype-hook*)
(00000A40 52 2 1		)
(00000A43 10)
(00000A44 9 63 1		'SysVar-Reactor)
(00000A47 9 111 0		'(standard-class SysVar-Reactor :MIXIN :MIXED-PAGE "Class for SysVar-Reactor reactors" ((new-instance . SysVar-Reactor.new-instance)) nil ((lisplet-reference . T) (index fixnum) (Function-Names list) (user-data . T) (range fixnum)) ((get-Type . SysVar-Reactor.get-Type) (get-Notification-Names . SysVar-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-sysVarWillChange :VLR-sysVarChanged) (reactor-type . 10))))
(00000A4A 53 2 238 0 1 32		find-class<-)
(00000A50 10)
(00000A51 9 172 1		'SysVar-Reactor-p)
(00000A54 26 110 0		SysVar-Reactor-p)
(00000A57 9 110 0		'SysVar-Reactor-p)
(00000A5A 10)
(00000A5B 9 171 1		'SysVar-Reactor.new-instance)
(00000A5E 26 109 0		SysVar-Reactor.new-instance)
(00000A61 9 109 0		'SysVar-Reactor.new-instance)
(00000A64 10)
(00000A65 1		nil)
(00000A66 10)
(00000A67 9 63 1		'SysVar-Reactor)
(00000A6A 9 152 0		"VLR-")
(00000A6D 9 63 1		'SysVar-Reactor)
(00000A70 81 2 151 0 1 0		concat)
(00000A76 81 1 150 0 1 0		intern)
(00000A7C 53 2 149 0 1 32		mk-al-type)
(00000A82 10)
(00000A83 9 76 2		'SysVar-Reactor)
(00000A86 26 63 1		SysVar-Reactor)
(00000A89 9 63 1		'SysVar-Reactor)
(00000A8C 10)
(00000A8D 9 170 1		'SysVar-Reactor.get-Type)
(00000A90 26 108 0		SysVar-Reactor.get-Type)
(00000A93 9 108 0		'SysVar-Reactor.get-Type)
(00000A96 10)
(00000A97 9 169 1		'SysVar-Reactor.get-Notification-Names)
(00000A9A 26 107 0		SysVar-Reactor.get-Notification-Names)
(00000A9D 9 107 0		'SysVar-Reactor.get-Notification-Names)
(00000AA0 10)
(00000AA1 1		nil)
(00000AA2 10)
(00000AA3 9 65 1		'Insert-Reactor)
(00000AA6 9 180 0		'(VL-Reactor))
(00000AA9 3 240 0		*deftype-hook*)
(00000AAC 52 2 1		)
(00000AAF 10)
(00000AB0 9 65 1		'Insert-Reactor)
(00000AB3 9 106 0		'(standard-class Insert-Reactor :MIXIN :MIXED-PAGE "Class for Insert-Reactor reactors" ((new-instance . Insert-Reactor.new-instance)) nil ((lisplet-reference . T) (index fixnum) (Function-Names list) (user-data . T) (range fixnum)) ((get-Type . Insert-Reactor.get-Type) (get-Notification-Names . Insert-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-beginInsert :VLR-beginInsertM :VLR-otherInsert :VLR-abortInsert :VLR-endInsert) (reactor-type . 8))))
(00000AB6 53 2 238 0 1 32		find-class<-)
(00000ABC 10)
(00000ABD 9 168 1		'Insert-Reactor-p)
(00000AC0 26 105 0		Insert-Reactor-p)
(00000AC3 9 105 0		'Insert-Reactor-p)
(00000AC6 10)
(00000AC7 9 167 1		'Insert-Reactor.new-instance)
(00000ACA 26 104 0		Insert-Reactor.new-instance)
(00000ACD 9 104 0		'Insert-Reactor.new-instance)
(00000AD0 10)
(00000AD1 1		nil)
(00000AD2 10)
(00000AD3 9 65 1		'Insert-Reactor)
(00000AD6 9 152 0		"VLR-")
(00000AD9 9 65 1		'Insert-Reactor)
(00000ADC 81 2 151 0 1 0		concat)
(00000AE2 81 1 150 0 1 0		intern)
(00000AE8 53 2 149 0 1 32		mk-al-type)
(00000AEE 10)
(00000AEF 9 78 2		'Insert-Reactor)
(00000AF2 26 65 1		Insert-Reactor)
(00000AF5 9 65 1		'Insert-Reactor)
(00000AF8 10)
(00000AF9 9 166 1		'Insert-Reactor.get-Type)
(00000AFC 26 103 0		Insert-Reactor.get-Type)
(00000AFF 9 103 0		'Insert-Reactor.get-Type)
(00000B02 10)
(00000B03 9 165 1		'Insert-Reactor.get-Notification-Names)
(00000B06 26 102 0		Insert-Reactor.get-Notification-Names)
(00000B09 9 102 0		'Insert-Reactor.get-Notification-Names)
(00000B0C 10)
(00000B0D 1		nil)
(00000B0E 10)
(00000B0F 9 64 1		'Wblock-Reactor)
(00000B12 9 180 0		'(VL-Reactor))
(00000B15 3 240 0		*deftype-hook*)
(00000B18 52 2 1		)
(00000B1B 10)
(00000B1C 9 64 1		'Wblock-Reactor)
(00000B1F 9 101 0		'(standard-class Wblock-Reactor :MIXIN :MIXED-PAGE "Class for Wblock-Reactor reactors" ((new-instance . Wblock-Reactor.new-instance)) nil ((lisplet-reference . T) (index fixnum) (Function-Names list) (user-data . T) (range fixnum)) ((get-Type . Wblock-Reactor.get-Type) (get-Notification-Names . Wblock-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-wblockNotice :VLR-beginWblockPt :VLR-beginWblockId :VLR-beginWblock :VLR-otherWblock :VLR-abortWblock :VLR-endWblock :VLR-beginWblockObjects) (reactor-type . 9))))
(00000B22 53 2 238 0 1 32		find-class<-)
(00000B28 10)
(00000B29 9 164 1		'Wblock-Reactor-p)
(00000B2C 26 100 0		Wblock-Reactor-p)
(00000B2F 9 100 0		'Wblock-Reactor-p)
(00000B32 10)
(00000B33 9 163 1		'Wblock-Reactor.new-instance)
(00000B36 26 99 0		Wblock-Reactor.new-instance)
(00000B39 9 99 0		'Wblock-Reactor.new-instance)
(00000B3C 10)
(00000B3D 1		nil)
(00000B3E 10)
(00000B3F 9 64 1		'Wblock-Reactor)
(00000B42 9 152 0		"VLR-")
(00000B45 9 64 1		'Wblock-Reactor)
(00000B48 81 2 151 0 1 0		concat)
(00000B4E 81 1 150 0 1 0		intern)
(00000B54 53 2 149 0 1 32		mk-al-type)
(00000B5A 10)
(00000B5B 9 77 2		'Wblock-Reactor)
(00000B5E 26 64 1		Wblock-Reactor)
(00000B61 9 64 1		'Wblock-Reactor)
(00000B64 10)
(00000B65 9 162 1		'Wblock-Reactor.get-Type)
(00000B68 26 98 0		Wblock-Reactor.get-Type)
(00000B6B 9 98 0		'Wblock-Reactor.get-Type)
(00000B6E 10)
(00000B6F 9 161 1		'Wblock-Reactor.get-Notification-Names)
(00000B72 26 97 0		Wblock-Reactor.get-Notification-Names)
(00000B75 9 97 0		'Wblock-Reactor.get-Notification-Names)
(00000B78 10)
(00000B79 1		nil)
(00000B7A 10)
(00000B7B 9 62 1		'DeepClone-Reactor)
(00000B7E 9 180 0		'(VL-Reactor))
(00000B81 3 240 0		*deftype-hook*)
(00000B84 52 2 1		)
(00000B87 10)
(00000B88 9 62 1		'DeepClone-Reactor)
(00000B8B 9 96 0		'(standard-class DeepClone-Reactor :MIXIN :MIXED-PAGE "Class for DeepClone-Reactor reactors" ((new-instance . DeepClone-Reactor.new-instance)) nil ((lisplet-reference . T) (index fixnum) (Function-Names list) (user-data . T) (range fixnum)) ((get-Type . DeepClone-Reactor.get-Type) (get-Notification-Names . DeepClone-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-beginDeepClone :VLR-beginDeepCloneXlation :VLR-abortDeepClone :VLR-endDeepClone) (reactor-type . 11))))
(00000B8E 53 2 238 0 1 32		find-class<-)
(00000B94 10)
(00000B95 9 160 1		'DeepClone-Reactor-p)
(00000B98 26 95 0		DeepClone-Reactor-p)
(00000B9B 9 95 0		'DeepClone-Reactor-p)
(00000B9E 10)
(00000B9F 9 159 1		'DeepClone-Reactor.new-instance)
(00000BA2 26 94 0		DeepClone-Reactor.new-instance)
(00000BA5 9 94 0		'DeepClone-Reactor.new-instance)
(00000BA8 10)
(00000BA9 1		nil)
(00000BAA 10)
(00000BAB 9 62 1		'DeepClone-Reactor)
(00000BAE 9 152 0		"VLR-")
(00000BB1 9 62 1		'DeepClone-Reactor)
(00000BB4 81 2 151 0 1 0		concat)
(00000BBA 81 1 150 0 1 0		intern)
(00000BC0 53 2 149 0 1 32		mk-al-type)
(00000BC6 10)
(00000BC7 9 75 2		'DeepClone-Reactor)
(00000BCA 26 62 1		DeepClone-Reactor)
(00000BCD 9 62 1		'DeepClone-Reactor)
(00000BD0 10)
(00000BD1 9 158 1		'DeepClone-Reactor.get-Type)
(00000BD4 26 93 0		DeepClone-Reactor.get-Type)
(00000BD7 9 93 0		'DeepClone-Reactor.get-Type)
(00000BDA 10)
(00000BDB 9 157 1		'DeepClone-Reactor.get-Notification-Names)
(00000BDE 26 92 0		DeepClone-Reactor.get-Notification-Names)
(00000BE1 9 92 0		'DeepClone-Reactor.get-Notification-Names)
(00000BE4 10)
(00000BE5 1		nil)
(00000BE6 10)
(00000BE7 9 61 1		'XREF-Reactor)
(00000BEA 9 180 0		'(VL-Reactor))
(00000BED 3 240 0		*deftype-hook*)
(00000BF0 52 2 1		)
(00000BF3 10)
(00000BF4 9 61 1		'XREF-Reactor)
(00000BF7 9 91 0		'(standard-class XREF-Reactor :MIXIN :MIXED-PAGE "Class for XREF-Reactor reactors" ((new-instance . XREF-Reactor.new-instance)) nil ((lisplet-reference . T) (index fixnum) (Function-Names list) (user-data . T) (range fixnum)) ((get-Type . XREF-Reactor.get-Type) (get-Notification-Names . XREF-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-beginAttach :VLR-otherAttach :VLR-abortAttach :VLR-endAttach :VLR-redirected :VLR-comandeered :VLR-beginRestore :VLR-abortRestore :VLR-endRestore :VLR-xrefSubcommandBindItem :VLR-xrefSubcommandAttachItem :VLR-xrefSubcommandOverlayItem :VLR-xrefSubcommandDetachItem :VLR-xrefSubcommandPathItem :VLR-xrefSubcommandReloadItem :VLR-xrefSubcommandUnloadItem) (reactor-type . 12))))
(00000BFA 53 2 238 0 1 32		find-class<-)
(00000C00 10)
(00000C01 9 156 1		'XREF-Reactor-p)
(00000C04 26 90 0		XREF-Reactor-p)
(00000C07 9 90 0		'XREF-Reactor-p)
(00000C0A 10)
(00000C0B 9 155 1		'XREF-Reactor.new-instance)
(00000C0E 26 89 0		XREF-Reactor.new-instance)
(00000C11 9 89 0		'XREF-Reactor.new-instance)
(00000C14 10)
(00000C15 1		nil)
(00000C16 10)
(00000C17 9 61 1		'XREF-Reactor)
(00000C1A 9 152 0		"VLR-")
(00000C1D 9 61 1		'XREF-Reactor)
(00000C20 81 2 151 0 1 0		concat)
(00000C26 81 1 150 0 1 0		intern)
(00000C2C 53 2 149 0 1 32		mk-al-type)
(00000C32 10)
(00000C33 9 74 2		'XREF-Reactor)
(00000C36 26 61 1		XREF-Reactor)
(00000C39 9 61 1		'XREF-Reactor)
(00000C3C 10)
(00000C3D 9 154 1		'XREF-Reactor.get-Type)
(00000C40 26 88 0		XREF-Reactor.get-Type)
(00000C43 9 88 0		'XREF-Reactor.get-Type)
(00000C46 10)
(00000C47 9 153 1		'XREF-Reactor.get-Notification-Names)
(00000C4A 26 87 0		XREF-Reactor.get-Notification-Names)
(00000C4D 9 87 0		'XREF-Reactor.get-Notification-Names)
(00000C50 10)
(00000C51 1		nil)
(00000C52 10)
(00000C53 9 60 1		'Undo-Reactor)
(00000C56 9 180 0		'(VL-Reactor))
(00000C59 3 240 0		*deftype-hook*)
(00000C5C 52 2 1		)
(00000C5F 10)
(00000C60 9 60 1		'Undo-Reactor)
(00000C63 9 86 0		'(standard-class Undo-Reactor :MIXIN :MIXED-PAGE "Class for Undo-Reactor reactors" ((new-instance . Undo-Reactor.new-instance)) nil ((lisplet-reference . T) (index fixnum) (Function-Names list) (user-data . T) (range fixnum)) ((get-Type . Undo-Reactor.get-Type) (get-Notification-Names . Undo-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-undoSubcommandAuto :VLR-undoSubcommandControl :VLR-undoSubcommandBegin :VLR-undoSubcommandEnd :VLR-undoSubcommandMark :VLR-undoSubcommandBack :VLR-undoSubcommandNumber) (reactor-type . 13))))
(00000C66 53 2 238 0 1 32		find-class<-)
(00000C6C 10)
(00000C6D 9 152 1		'Undo-Reactor-p)
(00000C70 26 85 0		Undo-Reactor-p)
(00000C73 9 85 0		'Undo-Reactor-p)
(00000C76 10)
(00000C77 9 151 1		'Undo-Reactor.new-instance)
(00000C7A 26 84 0		Undo-Reactor.new-instance)
(00000C7D 9 84 0		'Undo-Reactor.new-instance)
(00000C80 10)
(00000C81 1		nil)
(00000C82 10)
(00000C83 9 60 1		'Undo-Reactor)
(00000C86 9 152 0		"VLR-")
(00000C89 9 60 1		'Undo-Reactor)
(00000C8C 81 2 151 0 1 0		concat)
(00000C92 81 1 150 0 1 0		intern)
(00000C98 53 2 149 0 1 32		mk-al-type)
(00000C9E 10)
(00000C9F 9 73 2		'Undo-Reactor)
(00000CA2 26 60 1		Undo-Reactor)
(00000CA5 9 60 1		'Undo-Reactor)
(00000CA8 10)
(00000CA9 9 150 1		'Undo-Reactor.get-Type)
(00000CAC 26 83 0		Undo-Reactor.get-Type)
(00000CAF 9 83 0		'Undo-Reactor.get-Type)
(00000CB2 10)
(00000CB3 9 149 1		'Undo-Reactor.get-Notification-Names)
(00000CB6 26 82 0		Undo-Reactor.get-Notification-Names)
(00000CB9 9 82 0		'Undo-Reactor.get-Notification-Names)
(00000CBC 10)
(00000CBD 1		nil)
(00000CBE 10)
(00000CBF 9 58 1		'Toolbar-Reactor)
(00000CC2 9 180 0		'(VL-Reactor))
(00000CC5 3 240 0		*deftype-hook*)
(00000CC8 52 2 1		)
(00000CCB 10)
(00000CCC 9 58 1		'Toolbar-Reactor)
(00000CCF 9 81 0		'(standard-class Toolbar-Reactor :MIXIN :MIXED-PAGE "Class for Toolbar-Reactor reactors" ((new-instance . Toolbar-Reactor.new-instance)) nil ((lisplet-reference . T) (index fixnum) (Function-Names list) (user-data . T) (range fixnum)) ((get-Type . Toolbar-Reactor.get-Type) (get-Notification-Names . Toolbar-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-toolbarBitmapSizeWillChange :VLR-toolbarBitmapSizeChanged) (reactor-type . 15))))
(00000CD2 53 2 238 0 1 32		find-class<-)
(00000CD8 10)
(00000CD9 9 148 1		'Toolbar-Reactor-p)
(00000CDC 26 80 0		Toolbar-Reactor-p)
(00000CDF 9 80 0		'Toolbar-Reactor-p)
(00000CE2 10)
(00000CE3 9 147 1		'Toolbar-Reactor.new-instance)
(00000CE6 26 79 0		Toolbar-Reactor.new-instance)
(00000CE9 9 79 0		'Toolbar-Reactor.new-instance)
(00000CEC 10)
(00000CED 1		nil)
(00000CEE 10)
(00000CEF 9 58 1		'Toolbar-Reactor)
(00000CF2 9 152 0		"VLR-")
(00000CF5 9 58 1		'Toolbar-Reactor)
(00000CF8 81 2 151 0 1 0		concat)
(00000CFE 81 1 150 0 1 0		intern)
(00000D04 53 2 149 0 1 32		mk-al-type)
(00000D0A 10)
(00000D0B 9 71 2		'Toolbar-Reactor)
(00000D0E 26 58 1		Toolbar-Reactor)
(00000D11 9 58 1		'Toolbar-Reactor)
(00000D14 10)
(00000D15 9 146 1		'Toolbar-Reactor.get-Type)
(00000D18 26 78 0		Toolbar-Reactor.get-Type)
(00000D1B 9 78 0		'Toolbar-Reactor.get-Type)
(00000D1E 10)
(00000D1F 9 145 1		'Toolbar-Reactor.get-Notification-Names)
(00000D22 26 77 0		Toolbar-Reactor.get-Notification-Names)
(00000D25 9 77 0		'Toolbar-Reactor.get-Notification-Names)
(00000D28 10)
(00000D29 1		nil)
(00000D2A 10)
(00000D2B 9 57 1		'Mouse-Reactor)
(00000D2E 9 180 0		'(VL-Reactor))
(00000D31 3 240 0		*deftype-hook*)
(00000D34 52 2 1		)
(00000D37 10)
(00000D38 9 57 1		'Mouse-Reactor)
(00000D3B 9 76 0		'(standard-class Mouse-Reactor :MIXIN :MIXED-PAGE "Class for Mouse-Reactor reactors" ((new-instance . Mouse-Reactor.new-instance)) nil ((lisplet-reference . T) (index fixnum) (Function-Names list) (user-data . T) (range fixnum)) ((get-Type . Mouse-Reactor.get-Type) (get-Notification-Names . Mouse-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-beginDoubleClick :VLR-beginRightClick) (reactor-type . 16))))
(00000D3E 53 2 238 0 1 32		find-class<-)
(00000D44 10)
(00000D45 9 144 1		'Mouse-Reactor-p)
(00000D48 26 75 0		Mouse-Reactor-p)
(00000D4B 9 75 0		'Mouse-Reactor-p)
(00000D4E 10)
(00000D4F 9 143 1		'Mouse-Reactor.new-instance)
(00000D52 26 74 0		Mouse-Reactor.new-instance)
(00000D55 9 74 0		'Mouse-Reactor.new-instance)
(00000D58 10)
(00000D59 1		nil)
(00000D5A 10)
(00000D5B 9 57 1		'Mouse-Reactor)
(00000D5E 9 152 0		"VLR-")
(00000D61 9 57 1		'Mouse-Reactor)
(00000D64 81 2 151 0 1 0		concat)
(00000D6A 81 1 150 0 1 0		intern)
(00000D70 53 2 149 0 1 32		mk-al-type)
(00000D76 10)
(00000D77 9 70 2		'Mouse-Reactor)
(00000D7A 26 57 1		Mouse-Reactor)
(00000D7D 9 57 1		'Mouse-Reactor)
(00000D80 10)
(00000D81 9 142 1		'Mouse-Reactor.get-Type)
(00000D84 26 73 0		Mouse-Reactor.get-Type)
(00000D87 9 73 0		'Mouse-Reactor.get-Type)
(00000D8A 10)
(00000D8B 9 141 1		'Mouse-Reactor.get-Notification-Names)
(00000D8E 26 72 0		Mouse-Reactor.get-Notification-Names)
(00000D91 9 72 0		'Mouse-Reactor.get-Notification-Names)
(00000D94 10)
(00000D95 1		nil)
(00000D96 10)
(00000D97 9 59 1		'Window-Reactor)
(00000D9A 9 180 0		'(VL-Reactor))
(00000D9D 3 240 0		*deftype-hook*)
(00000DA0 52 2 1		)
(00000DA3 10)
(00000DA4 9 59 1		'Window-Reactor)
(00000DA7 9 71 0		'(standard-class Window-Reactor :MIXIN :MIXED-PAGE "Class for Window-Reactor reactors" ((new-instance . Window-Reactor.new-instance)) nil ((lisplet-reference . T) (index fixnum) (Function-Names list) (user-data . T) (range fixnum)) ((get-Type . Window-Reactor.get-Type) (get-Notification-Names . Window-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-docFrameMovedOrResized :VLR-mainFrameMovedOrResized) (reactor-type . 14))))
(00000DAA 53 2 238 0 1 32		find-class<-)
(00000DB0 10)
(00000DB1 9 140 1		'Window-Reactor-p)
(00000DB4 26 70 0		Window-Reactor-p)
(00000DB7 9 70 0		'Window-Reactor-p)
(00000DBA 10)
(00000DBB 9 139 1		'Window-Reactor.new-instance)
(00000DBE 26 69 0		Window-Reactor.new-instance)
(00000DC1 9 69 0		'Window-Reactor.new-instance)
(00000DC4 10)
(00000DC5 1		nil)
(00000DC6 10)
(00000DC7 9 59 1		'Window-Reactor)
(00000DCA 9 152 0		"VLR-")
(00000DCD 9 59 1		'Window-Reactor)
(00000DD0 81 2 151 0 1 0		concat)
(00000DD6 81 1 150 0 1 0		intern)
(00000DDC 53 2 149 0 1 32		mk-al-type)
(00000DE2 10)
(00000DE3 9 72 2		'Window-Reactor)
(00000DE6 26 59 1		Window-Reactor)
(00000DE9 9 59 1		'Window-Reactor)
(00000DEC 10)
(00000DED 9 138 1		'Window-Reactor.get-Type)
(00000DF0 26 68 0		Window-Reactor.get-Type)
(00000DF3 9 68 0		'Window-Reactor.get-Type)
(00000DF6 10)
(00000DF7 9 137 1		'Window-Reactor.get-Notification-Names)
(00000DFA 26 67 0		Window-Reactor.get-Notification-Names)
(00000DFD 9 67 0		'Window-Reactor.get-Notification-Names)
(00000E00 10)
(00000E01 1		nil)
(00000E02 10)
(00000E03 9 56 1		'Miscellaneous-Reactor)
(00000E06 9 180 0		'(VL-Reactor))
(00000E09 3 240 0		*deftype-hook*)
(00000E0C 52 2 1		)
(00000E0F 10)
(00000E10 9 56 1		'Miscellaneous-Reactor)
(00000E13 9 66 0		'(standard-class Miscellaneous-Reactor :MIXIN :MIXED-PAGE "Class for Miscellaneous-Reactor reactors" ((new-instance . Miscellaneous-Reactor.new-instance)) nil ((lisplet-reference . T) (index fixnum) (Function-Names list) (user-data . T) (range fixnum)) ((get-Type . Miscellaneous-Reactor.get-Type) (get-Notification-Names . Miscellaneous-Reactor.get-Notification-Names) (axvlo-dump . VL-Reactor.axvlo-dump) (axvlo-restore . VL-Reactor.axvlo-restore) (Reactor-apply . VL-Reactor.Reactor-apply) (add-reactor . VL-Reactor.add-reactor) (remove-Reactor . VL-Reactor.remove-Reactor) (Sync-LISP->CPP . VL-Reactor.Sync-LISP->CPP) (print-object . VL-Reactor.print-object) (inspect-object . VL-Reactor.inspect-object) (Notification-Names :VLR-pickfirstModified :VLR-layoutSwitched) (reactor-type . 17))))
(00000E16 53 2 238 0 1 32		find-class<-)
(00000E1C 10)
(00000E1D 9 136 1		'Miscellaneous-Reactor-p)
(00000E20 26 65 0		Miscellaneous-Reactor-p)
(00000E23 9 65 0		'Miscellaneous-Reactor-p)
(00000E26 10)
(00000E27 9 135 1		'Miscellaneous-Reactor.new-instance)
(00000E2A 26 64 0		Miscellaneous-Reactor.new-instance)
(00000E2D 9 64 0		'Miscellaneous-Reactor.new-instance)
(00000E30 10)
(00000E31 1		nil)
(00000E32 10)
(00000E33 9 56 1		'Miscellaneous-Reactor)
(00000E36 9 152 0		"VLR-")
(00000E39 9 56 1		'Miscellaneous-Reactor)
(00000E3C 81 2 151 0 1 0		concat)
(00000E42 81 1 150 0 1 0		intern)
(00000E48 53 2 149 0 1 32		mk-al-type)
(00000E4E 10)
(00000E4F 9 69 2		'Miscellaneous-Reactor)
(00000E52 26 56 1		Miscellaneous-Reactor)
(00000E55 9 56 1		'Miscellaneous-Reactor)
(00000E58 10)
(00000E59 9 134 1		'Miscellaneous-Reactor.get-Type)
(00000E5C 26 63 0		Miscellaneous-Reactor.get-Type)
(00000E5F 9 63 0		'Miscellaneous-Reactor.get-Type)
(00000E62 10)
(00000E63 9 133 1		'Miscellaneous-Reactor.get-Notification-Names)
(00000E66 26 62 0		Miscellaneous-Reactor.get-Notification-Names)
(00000E69 9 62 0		'Miscellaneous-Reactor.get-Notification-Names)
(00000E6C 10)
(00000E6D 1		nil)
(00000E6E 10)
(00000E6F 9 55 1		'Object-Reactor)
(00000E72 9 61 0		'(VL-Object-Reactor))
(00000E75 3 240 0		*deftype-hook*)
(00000E78 52 2 1		)
(00000E7B 10)
(00000E7C 9 55 1		'Object-Reactor)
(00000E7F 9 60 0		'(standard-class Object-Reactor :MIXIN :MIXED-PAGE "Class for Object-Reactor reactors" ((new-instance . Object-Reactor.new-instance)) nil ((lisplet-reference . T) (index fixnum) (Function-Names list) (user-data . T) (range fixnum) (reactor-owners . T)) ((get-Type . Object-Reactor.get-Type) (get-Notification-Names . Object-Reactor.get-Notification-Names) (axvlo-dump . VL-Object-Reactor.axvlo-dump) (axvlo-restore . VL-Object-Reactor.axvlo-restore) (Reactor-apply . VL-Object-Reactor.Reactor-apply) (add-reactor . VL-Object-Reactor.add-reactor) (remove-Reactor . VL-Object-Reactor.remove-Reactor) (Sync-LISP->CPP . VL-Object-Reactor.Sync-LISP->CPP) (print-object . VL-Reactor.print-object) (inspect-object . VL-Object-Reactor.inspect-object) (Notification-Names :VLR-cancelled :VLR-copied :VLR-erased :VLR-unerased :VLR-goodbye :VLR-openedForModify :VLR-modified :VLR-subObjModified :VLR-modifyUndone :VLR-modifiedXData :VLR-unappended :VLR-reappended :VLR-objectClosed) (reactor-type . 18))))
(00000E82 53 2 238 0 1 32		find-class<-)
(00000E88 10)
(00000E89 9 132 1		'Object-Reactor-p)
(00000E8C 26 59 0		Object-Reactor-p)
(00000E8F 9 59 0		'Object-Reactor-p)
(00000E92 10)
(00000E93 9 131 1		'Object-Reactor.new-instance)
(00000E96 26 58 0		Object-Reactor.new-instance)
(00000E99 9 58 0		'Object-Reactor.new-instance)
(00000E9C 10)
(00000E9D 1		nil)
(00000E9E 10)
(00000E9F 9 55 1		'Object-Reactor)
(00000EA2 9 152 0		"VLR-")
(00000EA5 9 55 1		'Object-Reactor)
(00000EA8 81 2 151 0 1 0		concat)
(00000EAE 81 1 150 0 1 0		intern)
(00000EB4 53 2 149 0 1 32		mk-al-type)
(00000EBA 10)
(00000EBB 9 68 2		'Object-Reactor)
(00000EBE 26 55 1		Object-Reactor)
(00000EC1 9 55 1		'Object-Reactor)
(00000EC4 10)
(00000EC5 9 130 1		'Object-Reactor.get-Type)
(00000EC8 26 57 0		Object-Reactor.get-Type)
(00000ECB 9 57 0		'Object-Reactor.get-Type)
(00000ECE 10)
(00000ECF 9 129 1		'Object-Reactor.get-Notification-Names)
(00000ED2 26 56 0		Object-Reactor.get-Notification-Names)
(00000ED5 9 56 0		'Object-Reactor.get-Notification-Names)
(00000ED8 10)
(00000ED9 1		nil)
(00000EDA 28		[ret])
(00000EDB 20 0 0 0 0)
(00000EE0 1		nil)
(00000EE1 10)
(00000EE2 1		nil)
(00000EE3 10)
(00000EE4 9 128 1		'_vl-acdb-cleanup)
(00000EE7 26 55 0		_vl-acdb-cleanup)
(00000EEA 9 55 0		'_vl-acdb-cleanup)
(00000EED 10)
(00000EEE 53 0 72 1 1 32		Editor-Reactor)
(00000EF4 26 54 0		*vlr-er*)
(00000EF7 9 54 0		'*vlr-er*)
(00000EFA 10)
(00000EFB 3 54 0		*vlr-er*)
(00000EFE 9 53 0		':VLR-databaseToBeDestroyed)
(00000F01 9 128 1		'_vl-acdb-cleanup)
(00000F04 53 3 212 0 1 32		VL-Reactor.Set-Slot)
(00000F0A 10)
(00000F0B 9 127 1		'_vlr-object-reactors-clear)
(00000F0E 26 52 0		_vlr-object-reactors-clear)
(00000F11 9 52 0		'_vlr-object-reactors-clear)
(00000F14 10)
(00000F15 9 126 1		'_vlr-global-reactors-clear)
(00000F18 26 51 0		_vlr-global-reactors-clear)
(00000F1B 9 51 0		'_vlr-global-reactors-clear)
(00000F1E 10)
(00000F1F 9 34 1		':VLR-Object-Reactor)
(00000F22 3 33 1		*VLAReactor-Class-Names-Vector*)
(00000F25 81 2 50 0 1 0		vector-position)
(00000F2B 26 49 0		*VLR-Object-Reactor-index*)
(00000F2E 9 49 0		'*VLR-Object-Reactor-index*)
(00000F31 10)
(00000F32 9 125 1		'_clear-saved-global-reactors)
(00000F35 26 48 0		_clear-saved-global-reactors)
(00000F38 9 48 0		'_clear-saved-global-reactors)
(00000F3B 28		[ret])
(00000F3C 20 0 0 0 0)
(00000F41 1		nil)
(00000F42 10)
(00000F43 9 47 0		'vlacdoc)
(00000F46 81 1 80 1 1 0		provide)
(00000F4C 10)
(00000F4D 9 46 0		'((0 . :vlAcDoc-kNone) (1 . :vlAcDoc-kAutoWrite) (2 . :vlAcDoc-kNotLocked) (4 . :vlAcDoc-kWrite) (8 . :vlAcDoc-kRead) (16 . :vlAcDoc-kXWrite)))
(00000F50 26 45 0		*enum-DocLockMode*)
(00000F53 9 45 0		'*enum-DocLockMode*)
(00000F56 10)
(00000F57 1		nil)
(00000F58 10)
(00000F59 1		nil)
(00000F5A 10)
(00000F5B 9 124 1		'vlAcDoc-lockMode)
(00000F5E 26 44 0		vlAcDoc-lockMode)
(00000F61 9 44 0		'vlAcDoc-lockMode)
(00000F64 10)
(00000F65 9 123 1		'vlAcDoc-myLockMode)
(00000F68 26 43 0		vlAcDoc-myLockMode)
(00000F6B 9 43 0		'vlAcDoc-myLockMode)
(00000F6E 28		[ret])
(00000F6F 20 0 0 0 0)
(00000F74 1		nil)
(00000F75 10)
(00000F76 1		nil)
(00000F77 10)
(00000F78 1		nil)
(00000F79 10)
(00000F7A 1		nil)
(00000F7B 10)
(00000F7C 9 122 1		'Idisp/ent->id)
(00000F7F 26 42 0		Idisp/ent->id)
(00000F82 9 42 0		'Idisp/ent->id)
(00000F85 10)
(00000F86 9 121 1		'vlax-write-enabled-p)
(00000F89 26 41 0		vlax-write-enabled-p)
(00000F8C 9 41 0		'vlax-write-enabled-p)
(00000F8F 10)
(00000F90 9 120 1		'vlax-read-enabled-p)
(00000F93 26 40 0		vlax-read-enabled-p)
(00000F96 9 40 0		'vlax-read-enabled-p)
(00000F99 10)
(00000F9A 9 119 1		'vlax-erased-p)
(00000F9D 26 39 0		vlax-erased-p)
(00000FA0 9 39 0		'vlax-erased-p)
(00000FA3 10)
(00000FA4 9 118 1		'check-ent/dict-arg)
(00000FA7 26 38 0		check-ent/dict-arg)
(00000FAA 9 38 0		'check-ent/dict-arg)
(00000FAD 10)
(00000FAE 9 117 1		'check-dictId)
(00000FB1 26 37 0		check-dictId)
(00000FB4 9 37 0		'check-dictId)
(00000FB7 10)
(00000FB8 9 116 1		'vlax-ldata-put)
(00000FBB 26 36 0		vlax-ldata-put)
(00000FBE 9 36 0		'vlax-ldata-put)
(00000FC1 10)
(00000FC2 9 115 1		'vlax-ldata-get)
(00000FC5 26 35 0		vlax-ldata-get)
(00000FC8 9 35 0		'vlax-ldata-get)
(00000FCB 10)
(00000FCC 9 114 1		'vlax-ldata-delete)
(00000FCF 26 34 0		vlax-ldata-delete)
(00000FD2 9 34 0		'vlax-ldata-delete)
(00000FD5 10)
(00000FD6 9 113 1		'vlax-ldata-list)
(00000FD9 26 33 0		vlax-ldata-list)
(00000FDC 9 33 0		'vlax-ldata-list)
(00000FDF 10)
(00000FE0 1		nil)
(00000FE1 10)
(00000FE2 12 112 1		'vlax-ldata-test)
(00000FE5 26 32 0		vlax-ldata-test)
(00000FE8 9 32 0		'vlax-ldata-test)
(00000FEB 10)
(00000FEC 9 31 0		"VL-REACTORS")
(00000FEF 26 30 0		*VLR-DICT-NAME*)
(00000FF2 9 30 0		'*VLR-DICT-NAME*)
(00000FF5 10)
(00000FF6 9 111 1		'vlr-pers-DictName)
(00000FF9 26 29 0		vlr-pers-DictName)
(00000FFC 9 29 0		'vlr-pers-DictName)
(00000FFF 10)
(00001000 9 110 1		'vlr-pers)
(00001003 26 28 0		vlr-pers)
(00001006 9 28 0		'vlr-pers)
(00001009 10)
(0000100A 9 109 1		'vl-pers-list)
(0000100D 26 27 0		vl-pers-list)
(00001010 9 27 0		'vl-pers-list)
(00001013 10)
(00001014 9 108 1		'vlr-pers-list)
(00001017 26 26 0		vlr-pers-list)
(0000101A 9 26 0		'vlr-pers-list)
(0000101D 10)
(0000101E 9 107 1		'vlr-pers-activate)
(00001021 26 25 0		vlr-pers-activate)
(00001024 9 25 0		'vlr-pers-activate)
(00001027 10)
(00001028 9 106 1		'vlr-pers-release)
(0000102B 26 24 0		vlr-pers-release)
(0000102E 9 24 0		'vlr-pers-release)
(00001031 10)
(00001032 9 105 1		'vlr-pers-p)
(00001035 26 23 0		vlr-pers-p)
(00001038 9 23 0		'vlr-pers-p)
(0000103B 10)
(0000103C 1		nil)
(0000103D 10)
(0000103E 9 104 1		'vlax-vla-object->ename)
(00001041 26 22 0		vlax-vla-object->ename)
(00001044 9 22 0		'vlax-vla-object->ename)
(00001047 10)
(00001048 9 103 1		'vlax-ename->vla-object)
(0000104B 26 21 0		vlax-ename->vla-object)
(0000104E 9 21 0		'vlax-ename->vla-object)
(00001051 10)
(00001052 1		nil)
(00001053 10)
(00001054 9 102 1		'IDisp?->Id)
(00001057 26 20 0		IDisp?->Id)
(0000105A 9 20 0		'IDisp?->Id)
(0000105D 10)
(0000105E 9 101 1		'vlax-curve-getArea)
(00001061 26 19 0		vlax-curve-getArea)
(00001064 9 19 0		'vlax-curve-getArea)
(00001067 10)
(00001068 9 100 1		'vlax-curve-getDistAtParam)
(0000106B 26 18 0		vlax-curve-getDistAtParam)
(0000106E 9 18 0		'vlax-curve-getDistAtParam)
(00001071 10)
(00001072 9 99 1		'vlax-curve-getDistAtPoint)
(00001075 26 17 0		vlax-curve-getDistAtPoint)
(00001078 9 17 0		'vlax-curve-getDistAtPoint)
(0000107B 10)
(0000107C 9 98 1		'vlax-curve-getEndParam)
(0000107F 26 16 0		vlax-curve-getEndParam)
(00001082 9 16 0		'vlax-curve-getEndParam)
(00001085 10)
(00001086 9 97 1		'vlax-curve-getEndPoint)
(00001089 26 15 0		vlax-curve-getEndPoint)
(0000108C 9 15 0		'vlax-curve-getEndPoint)
(0000108F 10)
(00001090 9 96 1		'vlax-curve-getParamAtDist)
(00001093 26 14 0		vlax-curve-getParamAtDist)
(00001096 9 14 0		'vlax-curve-getParamAtDist)
(00001099 10)
(0000109A 9 95 1		'vlax-curve-getParamAtPoint)
(0000109D 26 13 0		vlax-curve-getParamAtPoint)
(000010A0 9 13 0		'vlax-curve-getParamAtPoint)
(000010A3 10)
(000010A4 9 94 1		'vlax-curve-getPointAtDist)
(000010A7 26 12 0		vlax-curve-getPointAtDist)
(000010AA 9 12 0		'vlax-curve-getPointAtDist)
(000010AD 10)
(000010AE 9 93 1		'vlax-curve-getPointAtParam)
(000010B1 26 11 0		vlax-curve-getPointAtParam)
(000010B4 9 11 0		'vlax-curve-getPointAtParam)
(000010B7 10)
(000010B8 9 92 1		'vlax-curve-getStartParam)
(000010BB 26 10 0		vlax-curve-getStartParam)
(000010BE 9 10 0		'vlax-curve-getStartParam)
(000010C1 10)
(000010C2 9 91 1		'vlax-curve-getStartPoint)
(000010C5 26 9 0		vlax-curve-getStartPoint)
(000010C8 9 9 0		'vlax-curve-getStartPoint)
(000010CB 10)
(000010CC 9 90 1		'vlax-curve-isClosed)
(000010CF 26 8 0		vlax-curve-isClosed)
(000010D2 9 8 0		'vlax-curve-isClosed)
(000010D5 10)
(000010D6 9 89 1		'vlax-curve-isPeriodic)
(000010D9 26 7 0		vlax-curve-isPeriodic)
(000010DC 9 7 0		'vlax-curve-isPeriodic)
(000010DF 10)
(000010E0 9 88 1		'vlax-curve-isPlanar)
(000010E3 26 6 0		vlax-curve-isPlanar)
(000010E6 9 6 0		'vlax-curve-isPlanar)
(000010E9 10)
(000010EA 9 87 1		'vlax-curve-getClosestPointTo)
(000010ED 26 5 0		vlax-curve-getClosestPointTo)
(000010F0 9 5 0		'vlax-curve-getClosestPointTo)
(000010F3 10)
(000010F4 9 86 1		'vlax-curve-getClosestPointToProjection)
(000010F7 26 4 0		vlax-curve-getClosestPointToProjection)
(000010FA 9 4 0		'vlax-curve-getClosestPointToProjection)
(000010FD 10)
(000010FE 9 85 1		'vlax-curve-getFirstDeriv)
(00001101 26 3 0		vlax-curve-getFirstDeriv)
(00001104 9 3 0		'vlax-curve-getFirstDeriv)
(00001107 10)
(00001108 9 84 1		'vlax-curve-getSecondDeriv)
(0000110B 26 2 0		vlax-curve-getSecondDeriv)
(0000110E 9 2 0		'vlax-curve-getSecondDeriv)
(00001111 10)
(00001112 3 1 0		as:*noval*)
(00001115 22		ret)
