;;;==========SubFunction==========
;;;def create-host-spouse 2
(00000002 20 4 1 1 1)
(00000007 5 0		UnVar0)
(00000009 8 2		UnVar2)
(0000000B 100 3		UNVar3)
(0000000D 9 205 1		'create-host-spouse)
(00000010 5 2		UnVar2)
(00000012 81 2 204 1 1 0		compute-applicable-methods)
(00000018 8 3		UnVar3)
(0000001A 5 3		UnVar3)
(0000001C 37 2		consp)
(0000001E 13 17 0		nil->JMP 00000032)
(00000021 5 3		UnVar3)
(00000023 40		car)
(00000024 5 3		UnVar3)
(00000026 41		cdr)
(00000027 5 2		UnVar2)
(00000029 5 1		UnVar1)
(0000002B 81 3 203 1 1 0		list*)
(00000031 84		apply+ret)
(00000032 9 202 1		'no-applicable-method)
(00000035 9 205 1		'create-host-spouse)
(00000038 5 2		UnVar2)
(0000003A 5 1		UnVar1)
(0000003C 81 3 203 1 1 0		list*)
(00000042 84		apply+ret)
;;;def update-host-spouse 67
(00000043 20 4 1 1 1)
(00000048 5 0		UnVar0)
(0000004A 8 2		UnVar2)
(0000004C 100 3		UNVar3)
(0000004E 9 201 1		'update-host-spouse)
(00000051 5 2		UnVar2)
(00000053 81 2 204 1 1 0		compute-applicable-methods)
(00000059 8 3		UnVar3)
(0000005B 5 3		UnVar3)
(0000005D 37 2		consp)
(0000005F 13 17 0		nil->JMP 00000073)
(00000062 5 3		UnVar3)
(00000064 40		car)
(00000065 5 3		UnVar3)
(00000067 41		cdr)
(00000068 5 2		UnVar2)
(0000006A 5 1		UnVar1)
(0000006C 81 3 203 1 1 0		list*)
(00000072 84		apply+ret)
(00000073 9 202 1		'no-applicable-method)
(00000076 9 201 1		'update-host-spouse)
(00000079 5 2		UnVar2)
(0000007B 5 1		UnVar1)
(0000007D 81 3 203 1 1 0		list*)
(00000083 84		apply+ret)
;;;def update-los-spouse 132
(00000084 20 4 1 1 1)
(00000089 5 0		UnVar0)
(0000008B 8 2		UnVar2)
(0000008D 100 3		UNVar3)
(0000008F 9 200 1		'update-los-spouse)
(00000092 5 2		UnVar2)
(00000094 81 2 204 1 1 0		compute-applicable-methods)
(0000009A 8 3		UnVar3)
(0000009C 5 3		UnVar3)
(0000009E 37 2		consp)
(000000A0 13 17 0		nil->JMP 000000B4)
(000000A3 5 3		UnVar3)
(000000A5 40		car)
(000000A6 5 3		UnVar3)
(000000A8 41		cdr)
(000000A9 5 2		UnVar2)
(000000AB 5 1		UnVar1)
(000000AD 81 3 203 1 1 0		list*)
(000000B3 84		apply+ret)
(000000B4 9 202 1		'no-applicable-method)
(000000B7 9 200 1		'update-los-spouse)
(000000BA 5 2		UnVar2)
(000000BC 5 1		UnVar1)
(000000BE 81 3 203 1 1 0		list*)
(000000C4 84		apply+ret)
;;;def destroy-host-spouse 197
(000000C5 20 3 1 1 0)
(000000CA 5 0		UnVar0)
(000000CC 8 1		UnVar1)
(000000CE 100 2		UNVar2)
(000000D0 9 199 1		'destroy-host-spouse)
(000000D3 5 1		UnVar1)
(000000D5 81 2 204 1 1 0		compute-applicable-methods)
(000000DB 8 2		UnVar2)
(000000DD 5 2		UnVar2)
(000000DF 37 2		consp)
(000000E1 13 10 0		nil->JMP 000000EE)
(000000E4 5 2		UnVar2)
(000000E6 41		cdr)
(000000E7 5 1		UnVar1)
(000000E9 5 2		UnVar2)
(000000EB 40		car)
(000000EC 46 2		invoke+ret)
(000000EE 9 199 1		'destroy-host-spouse)
(000000F1 5 1		UnVar1)
(000000F3 81 2 202 1 1 0		no-applicable-method)
(000000F9 22		ret)
;;;def host-spouse-exists-p 250
(000000FA 20 3 1 1 0)
(000000FF 5 0		UnVar0)
(00000101 8 1		UnVar1)
(00000103 100 2		UNVar2)
(00000105 9 198 1		'host-spouse-exists-p)
(00000108 5 1		UnVar1)
(0000010A 81 2 204 1 1 0		compute-applicable-methods)
(00000110 8 2		UnVar2)
(00000112 5 2		UnVar2)
(00000114 37 2		consp)
(00000116 13 10 0		nil->JMP 00000123)
(00000119 5 2		UnVar2)
(0000011B 41		cdr)
(0000011C 5 1		UnVar1)
(0000011E 5 2		UnVar2)
(00000120 40		car)
(00000121 46 2		invoke+ret)
(00000123 9 198 1		'host-spouse-exists-p)
(00000126 5 1		UnVar1)
(00000128 81 2 202 1 1 0		no-applicable-method)
(0000012E 22		ret)
;;;def nil 303
(0000012F 20 3 2 3 0)
(00000134 5 1		UnVar1)
(00000136 13 71 0		nil->JMP 00000180)
(00000139 5 0		UnVar0)
(0000013B 5 1		UnVar1)
(0000013D 41		cdr)
(0000013E 40		car)
(0000013F 81 2 197 1 1 0		string-search)
(00000145 13 29 0		nil->JMP 00000165)
(00000148 5 1		UnVar1)
(0000014A 40		car)
(0000014B 5 1		UnVar1)
(0000014D 41		cdr)
(0000014E 40		car)
(0000014F 57 2 0		list)
(00000152 5 2		UnVar2)
(00000154 81 1 196 1 1 0		nreverse)
(0000015A 5 1		UnVar1)
(0000015C 41		cdr)
(0000015D 41		cdr)
(0000015E 81 3 195 1 1 0		nconc)
(00000164 22		ret)
(00000165 5 0		UnVar0)
(00000167 5 1		UnVar1)
(00000169 41		cdr)
(0000016A 41		cdr)
(0000016B 5 1		UnVar1)
(0000016D 41		cdr)
(0000016E 40		car)
(0000016F 5 1		UnVar1)
(00000171 40		car)
(00000172 5 2		UnVar2)
(00000174 81 3 203 1 1 0		list*)
(0000017A 97 3 52 1 0 0		offset 00000134)
(00000180 9 194 1		"VLMSG.DLL")
(00000183 51 136 119 0 0		30600)
(00000188 81 2 193 1 1 0		string-resource)
(0000018E 5 0		UnVar0)
(00000190 81 1 192 1 1 0		string)
(00000196 81 2 191 1 1 0		_win-format-message)
(0000019C 5 0		UnVar0)
(0000019E 5 2		UnVar2)
(000001A0 81 1 196 1 1 0		nreverse)
(000001A6 81 3 203 1 1 0		list*)
(000001AC 22		ret)
;;;def nil 429
(000001AD 20 2 2 2 0)
(000001B2 5 1		UnVar1)
(000001B4 13 30 0		nil->JMP 000001D5)
(000001B7 5 0		UnVar0)
(000001B9 5 1		UnVar1)
(000001BB 41		cdr)
(000001BC 40		car)
(000001BD 81 2 197 1 1 0		string-search)
(000001C3 13 3 0		nil->JMP 000001C9)
(000001C6 5 1		UnVar1)
(000001C8 22		ret)
(000001C9 5 0		UnVar0)
(000001CB 5 1		UnVar1)
(000001CD 41		cdr)
(000001CE 41		cdr)
(000001CF 97 2 178 1 0 0		offset 000001B2)
(000001D5 1		nil)
(000001D6 22		ret)
;;;def add-source-file-ext-filter 471
(000001D7 20 1 1 1 0)
(000001DC 5 0		UnVar0)
(000001DE 81 1 190 1 1 0		filename-extension)
(000001E4 11)
(000001E5 8 0		UnVar0)
(000001E7 63		nil->ret)
(000001E8 9 189 1		"*")
(000001EB 5 0		UnVar0)
(000001ED 81 1 188 1 1 0		nstring-upcase)
(000001F3 81 2 187 1 1 0		concat)
(000001F9 8 0		UnVar0)
(000001FB 5 0		UnVar0)
(000001FD 3 186 1		*source-file-filters*)
(00000200 95 2 173 1 0 0		func 000001AD)
(00000206 14 11 0		T->JMP 00000214)
(00000209 5 0		UnVar0)
(0000020B 3 185 1		*source-file-added-filters*)
(0000020E 81 2 184 1 1 0		member)
(00000214 13 2 0		nil->JMP 00000219)
(00000217 1		nil)
(00000218 22		ret)
(00000219 5 0		UnVar0)
(0000021B 97 1 138 2 0 0		offset 0000028A)
;;;def nil 545
(00000221 20 3 0 0 0)
(00000226 3 186 1		*source-file-filters*)
(00000229 3 185 1		*source-file-added-filters*)
(0000022C 53 1 183 1 1 32		copy-list)
(00000232 9 182 1		'string-lessp)
(00000235 81 2 181 1 1 0		sort)
(0000023B 8 0		UnVar0)
(0000023D 100 1		UNVar1)
(0000023F 15 53 0		JMP 00000277)
(00000242 5 1		UnVar1)
(00000244 5 0		UnVar0)
(00000246 40		car)
(00000247 8 2		UnVar2)
(00000249 9 194 1		"VLMSG.DLL")
(0000024C 51 136 119 0 0		30600)
(00000251 81 2 193 1 1 0		string-resource)
(00000257 5 2		UnVar2)
(00000259 81 1 192 1 1 0		string)
(0000025F 81 2 191 1 1 0		_win-format-message)
(00000265 5 2		UnVar2)
(00000267 57 2 0		list)
(0000026A 81 2 195 1 1 0		nconc)
(00000270 8 1		UnVar1)
(00000272 5 0		UnVar0)
(00000274 41		cdr)
(00000275 8 0		UnVar0)
(00000277 5 0		UnVar0)
(00000279 60 198 255		T->JMP 00000242)
(0000027C 5 1		UnVar1)
(0000027E 81 2 180 1 1 0		append)
(00000284 22		ret)
;;;def nil 645
(00000285 20 1 1 1 0)
(0000028A 5 0		UnVar0)
(0000028C 3 185 1		*source-file-added-filters*)
(0000028F 3 179 1		_*sff-added-limit*)
(00000292 80		1-)
(00000293 53 2 178 1 1 32		ncut)
(00000299 42		cons)
(0000029A 11)
(0000029B 6 185 1		*source-file-added-filters*)
(0000029E 22		ret)
;;;def choose-editor-file-dialog 671
(0000029F 20 7 2 5 0)
(000002A4 100 5		UNVar5)
(000002A6 95 0 33 2 0 0		func 00000221)
(000002AC 8 5		UnVar5)
(000002AE 5 2		UnVar2)
(000002B0 37 4		stringp)
(000002B2 61 32 0		nil->JMP 000002D5)
(000002B5 5 2		UnVar2)
(000002B7 81 1 177 1 1 0		strlen)
(000002BD 50 0		0)
(000002BF 75		>)
(000002C0 61 18 0		nil->JMP 000002D5)
(000002C3 50 46		46)
(000002C5 5 2		UnVar2)
(000002C7 50 0		0)
(000002C9 81 2 176 1 1 0		char)
(000002CF 81 2 175 1 1 0		=&)
(000002D5 13 31 0		nil->JMP 000002F7)
(000002D8 9 189 1		"*")
(000002DB 5 2		UnVar2)
(000002DD 81 1 174 1 1 0		string-upcase)
(000002E3 81 2 187 1 1 0		concat)
(000002E9 8 2		UnVar2)
(000002EB 5 2		UnVar2)
(000002ED 5 5		UnVar5)
(000002EF 95 2 47 1 0 0		func 0000012F)
(000002F5 8 5		UnVar5)
(000002F7 5 1		UnVar1)
(000002F9 5 5		UnVar5)
(000002FB 5 3		UnVar3)
(000002FD 5 0		UnVar0)
(000002FF 5 4		UnVar4)
(00000301 14 8 0		T->JMP 0000030C)
(00000304 5 3		UnVar3)
(00000306 61 3 0		nil->JMP 0000030C)
(00000309 3 173 1		*OFN-OPEN-EDITOR*)
(0000030C 81 5 172 1 1 0		choose-file-dialog)
(00000312 8 0		UnVar0)
(00000314 5 0		UnVar0)
(00000316 63		nil->ret)
(00000317 5 0		UnVar0)
(00000319 37 2		consp)
(0000031B 13 6 0		nil->JMP 00000324)
(0000031E 5 0		UnVar0)
(00000320 40		car)
(00000321 15 2 0		JMP 00000326)
(00000324 5 0		UnVar0)
(00000326 8 6		UnVar6)
(00000328 5 3		UnVar3)
(0000032A 13 32 0		nil->JMP 0000034D)
(0000032D 5 6		UnVar6)
(0000032F 81 1 171 1 1 0		file-readable-p)
(00000335 13 3 0		nil->JMP 0000033B)
(00000338 15 18 0		JMP 0000034D)
(0000033B 5 6		UnVar6)
(0000033D 9 170 1		':OUTPUT)
(00000340 81 2 169 1 1 0		open)
(00000346 81 1 168 1 1 0		close)
(0000034C 10)
(0000034D 5 0		UnVar0)
(0000034F 36		atom)
(00000350 13 3 0		nil->JMP 00000356)
(00000353 5 0		UnVar0)
(00000355 22		ret)
(00000356 50 0		0)
(00000358 5 0		UnVar0)
(0000035A 41		cdr)
(0000035B 50 1		1)
(0000035D 81 2 167 1 1 0		logand)
(00000363 81 2 175 1 1 0		=&)
(00000369 13 4 0		nil->JMP 00000370)
(0000036C 5 0		UnVar0)
(0000036E 40		car)
(0000036F 22		ret)
(00000370 5 0		UnVar0)
(00000372 22		ret)
;;;def _mfiles 883
(00000373 20 4 1 1 0)
(00000378 5 0		UnVar0)
(0000037A 13 78 0		nil->JMP 000003CB)
(0000037D 5 0		UnVar0)
(0000037F 36		atom)
(00000380 13 6 0		nil->JMP 00000389)
(00000383 5 0		UnVar0)
(00000385 57 1 0		list)
(00000388 22		ret)
(00000389 5 0		UnVar0)
(0000038B 40		car)
(0000038C 41		cdr)
(0000038D 13 55 0		nil->JMP 000003C7)
(00000390 5 0		UnVar0)
(00000392 40		car)
(00000393 41		cdr)
(00000394 8 1		UnVar1)
(00000396 100 2		UNVar2)
(00000398 15 30 0		JMP 000003B9)
(0000039B 5 1		UnVar1)
(0000039D 40		car)
(0000039E 8 3		UnVar3)
(000003A0 5 0		UnVar0)
(000003A2 40		car)
(000003A3 40		car)
(000003A4 9 166 1		"\\")
(000003A7 5 3		UnVar3)
(000003A9 81 3 165 1 1 0		strcat)
(000003AF 5 2		UnVar2)
(000003B1 42		cons)
(000003B2 8 2		UnVar2)
(000003B4 5 1		UnVar1)
(000003B6 41		cdr)
(000003B7 8 1		UnVar1)
(000003B9 5 1		UnVar1)
(000003BB 60 221 255		T->JMP 0000039B)
(000003BE 5 2		UnVar2)
(000003C0 81 1 196 1 1 0		nreverse)
(000003C6 22		ret)
(000003C7 5 0		UnVar0)
(000003C9 40		car)
(000003CA 22		ret)
(000003CB 5 0		UnVar0)
(000003CD 22		ret)
;;;def backup-filename 974
(000003CE 20 1 1 1 0)
(000003D3 5 0		UnVar0)
(000003D5 81 1 164 1 1 0		filename-non-extension)
(000003DB 9 163 1		"._")
(000003DE 5 0		UnVar0)
(000003E0 81 1 190 1 1 0		filename-extension)
(000003E6 14 3 0		T->JMP 000003EC)
(000003E9 9 162 1		".")
(000003EC 50 1		1)
(000003EE 50 2		2)
(000003F0 81 3 161 1 1 0		substr)
(000003F6 81 3 187 1 1 0		concat)
(000003FC 22		ret)
;;;def file-backup 1021
(000003FD 20 4 1 3 0)
(00000402 100 3		UNVar3)
(00000404 5 0		UnVar0)
(00000406 95 1 206 3 0 0		backup-filename)
(0000040C 8 3		UnVar3)
(0000040E 5 0		UnVar0)
(00000410 81 1 171 1 1 0		file-readable-p)
(00000416 13 205 0		nil->JMP 000004E6)
(00000419 5 3		UnVar3)
(0000041B 81 1 160 1 1 0		file-directory-p)
(00000421 13 33 0		nil->JMP 00000445)
(00000424 5 2		UnVar2)
(00000426 60 26 0		T->JMP 00000443)
(00000429 3 159 1		*warning-alert*)
(0000042C 9 194 1		"VLMSG.DLL")
(0000042F 51 80 95 0 0		24400)
(00000434 81 2 193 1 1 0		string-resource)
(0000043A 5 3		UnVar3)
(0000043C 95 3 2 40 0 0		alert)
(00000442 10)
(00000443 1		nil)
(00000444 22		ret)
(00000445 5 3		UnVar3)
(00000447 81 1 171 1 1 0		file-readable-p)
(0000044D 61 9 0		nil->JMP 00000459)
(00000450 5 3		UnVar3)
(00000452 81 1 158 1 1 0		file-delete)
(00000458 35		not)
(00000459 13 33 0		nil->JMP 0000047D)
(0000045C 5 2		UnVar2)
(0000045E 60 26 0		T->JMP 0000047B)
(00000461 3 159 1		*warning-alert*)
(00000464 9 194 1		"VLMSG.DLL")
(00000467 51 90 95 0 0		24410)
(0000046C 81 2 193 1 1 0		string-resource)
(00000472 5 3		UnVar3)
(00000474 95 3 2 40 0 0		alert)
(0000047A 10)
(0000047B 1		nil)
(0000047C 22		ret)
(0000047D 5 1		UnVar1)
(0000047F 13 13 0		nil->JMP 0000048F)
(00000482 5 0		UnVar0)
(00000484 5 3		UnVar3)
(00000486 53 2 157 1 1 32		file-copy)
(0000048C 15 10 0		JMP 00000499)
(0000048F 5 0		UnVar0)
(00000491 5 3		UnVar3)
(00000493 81 2 156 1 1 0		file-rename)
(00000499 13 3 0		nil->JMP 0000049F)
(0000049C 5 3		UnVar3)
(0000049E 22		ret)
(0000049F 5 2		UnVar2)
(000004A1 60 64 0		T->JMP 000004E4)
(000004A4 3 159 1		*warning-alert*)
(000004A7 9 194 1		"VLMSG.DLL")
(000004AA 51 100 95 0 0		24420)
(000004AF 81 2 193 1 1 0		string-resource)
(000004B5 5 1		UnVar1)
(000004B7 13 17 0		nil->JMP 000004CB)
(000004BA 9 194 1		"VLMSG.DLL")
(000004BD 51 110 95 0 0		24430)
(000004C2 81 2 193 1 1 0		string-resource)
(000004C8 15 14 0		JMP 000004D9)
(000004CB 9 194 1		"VLMSG.DLL")
(000004CE 51 100 115 0 0		29540)
(000004D3 81 2 193 1 1 0		string-resource)
(000004D9 5 0		UnVar0)
(000004DB 5 3		UnVar3)
(000004DD 95 5 2 40 0 0		alert)
(000004E3 10)
(000004E4 1		nil)
(000004E5 22		ret)
(000004E6 1		nil)
(000004E7 22		ret)
;;;def _W-BORDER 1256
(000004E8 20 0 0 0 0)
(000004ED 50 32		32)
(000004EF 81 1 155 1 1 0		get-system-metrics)
(000004F5 22		ret)
;;;def _W-BORDER-SIZE 1270
(000004F6 20 0 0 0 0)
(000004FB 50 2		2)
(000004FD 50 5		5)
(000004FF 81 1 155 1 1 0		get-system-metrics)
(00000505 95 0 232 4 0 0		_W-BORDER)
(0000050B 81 3 154 1 1 0		+)
(00000511 22		ret)
;;;def _W-ICON_SPACE 1298
(00000512 20 0 0 0 0)
(00000517 81 0 153 1 1 0		_mswin-platform)
(0000051D 50 3		3)
(0000051F 77		>=)
(00000520 13 9 0		nil->JMP 0000052C)
(00000523 50 58		58)
(00000525 81 1 155 1 1 0		get-system-metrics)
(0000052B 22		ret)
(0000052C 50 39		39)
(0000052E 81 1 155 1 1 0		get-system-metrics)
(00000534 22		ret)
;;;def _W-CAPTION_WIDTH 1333
(00000535 20 0 0 0 0)
(0000053A 50 4		4)
(0000053C 81 1 155 1 1 0		get-system-metrics)
(00000542 50 32		32)
(00000544 81 1 155 1 1 0		get-system-metrics)
(0000054A 81 0 153 1 1 0		_mswin-platform)
(00000550 50 3		3)
(00000552 77		>=)
(00000553 13 5 0		nil->JMP 0000055B)
(00000556 50 1		1)
(00000558 15 2 0		JMP 0000055D)
(0000055B 50 2		2)
(0000055D 50 5		5)
(0000055F 81 1 155 1 1 0		get-system-metrics)
(00000565 81 2 152 1 1 0		*)
(0000056B 81 2 151 1 1 0		-)
(00000571 70		+)
(00000572 22		ret)
;;;def _W-WINDOW_HEIGHT 1395
(00000573 20 0 0 0 0)
(00000578 50 2		2)
(0000057A 50 2		2)
(0000057C 81 1 155 1 1 0		get-system-metrics)
(00000582 95 0 53 5 0 0		_W-CAPTION_WIDTH)
(00000588 70		+)
(00000589 72		*)
(0000058A 22		ret)
;;;def _W-DIALOG-XMIN 1419
(0000058B 20 0 0 0 0)
(00000590 50 28		28)
(00000592 81 1 155 1 1 0		get-system-metrics)
(00000598 22		ret)
;;;def _W-DIALOG-YMIN 1433
(00000599 20 0 0 0 0)
(0000059E 50 29		29)
(000005A0 81 1 155 1 1 0		get-system-metrics)
(000005A6 22		ret)
;;;def run-fast 1447
(000005A7 21 6 1 3 0)
(000005AC 100 3		UNVar3)
(000005AE 100 4		UNVar4)
(000005B0 100 5		UNVar5)
(000005B2 9 194 1		"VLMSG.DLL")
(000005B5 51 146 119 0 0		30610)
(000005BA 81 2 193 1 1 0		string-resource)
(000005C0 5 1		UnVar1)
(000005C2 14 3 0		T->JMP 000005C8)
(000005C5 9 150 1		"")
(000005C8 81 1 192 1 1 0		string)
(000005CE 81 2 191 1 1 0		_win-format-message)
(000005D4 81 1 149 1 1 0		ales-prompt-msg)
(000005DA 10)
(000005DB 5 2		UnVar2)
(000005DD 14 6 0		T->JMP 000005E6)
(000005E0 53 0 148 1 1 32		alesmaint?)
(000005E6 8 2		UnVar2)
(000005E8 5 2		UnVar2)
(000005EA 13 3 0		nil->JMP 000005F0)
(000005ED 15 18 0		JMP 00000602)
(000005F0 2		T)
(000005F1 81 1 147 1 1 0		fast-link)
(000005F7 8 5		UnVar5)
(000005F9 1		nil)
(000005FA 81 1 146 1 1 0		_sys-trace)
(00000600 8 4		UnVar4)
(00000602 5 0		UnVar0)
(00000604 81 1 145 1 1 0		box)
(0000060A 8 3		UnVar3)
(0000060C 15 41 0		JMP 00000638)
(0000060F 20 0 0 0 0)
(00000614 1		nil)
(00000615 81 1 149 1 1 0		ales-prompt-msg)
(0000061B 10)
(0000061C 4 1 2		UpVar1-2)
(0000061F 13 2 0		nil->JMP 00000624)
(00000622 1		nil)
(00000623 22		ret)
(00000624 4 1 5		UpVar1-5)
(00000627 81 1 147 1 1 0		fast-link)
(0000062D 10)
(0000062E 4 1 4		UpVar1-4)
(00000631 81 1 146 1 1 0		_sys-trace)
(00000637 22		ret)
(00000638 12 22 2		'(1551 -unwind-cleanup-))
(0000063B 15 228 0		JMP 00000722)
(0000063E 20 0 0 0 0)
(00000643 9 144 1		'_%sys-error-hook%)
(00000646 15 94 0		JMP 000006A7)
(00000649 20 1 1 1 0)
(0000064E 3 143 1		*stop-alert*)
(00000651 9 194 1		"VLMSG.DLL")
(00000654 51 130 95 0 0		24450)
(00000659 81 2 193 1 1 0		string-resource)
(0000065F 4 2 1		UpVar2-1)
(00000662 13 15 0		nil->JMP 00000674)
(00000665 4 2 1		UpVar2-1)
(00000668 9 142 1		"\n")
(0000066B 81 2 187 1 1 0		concat)
(00000671 15 3 0		JMP 00000677)
(00000674 9 150 1		"")
(00000677 5 0		UnVar0)
(00000679 95 4 2 40 0 0		alert)
(0000067F 10)
(00000680 3 141 1		*error-output*)
(00000683 9 194 1		"VLMSG.DLL")
(00000686 51 140 95 0 0		24460)
(0000068B 81 2 193 1 1 0		string-resource)
(00000691 5 0		UnVar0)
(00000693 53 3 140 1 1 32		prinf)
(00000699 10)
(0000069A 4 2 3		UpVar2-3)
(0000069D 9 139 1		':ERROR)
(000006A0 81 2 138 1 1 0		throw)
(000006A6 22		ret)
(000006A7 12 21 2		'(1609 nil))
(000006AA 9 137 1		'*xsubr-trace-hook*)
(000006AD 1		nil)
(000006AE 9 136 1		'_%kbd-break-hook%)
(000006B1 15 59 0		JMP 000006EF)
(000006B4 20 0 0 0 0)
(000006B9 9 194 1		"VLMSG.DLL")
(000006BC 51 150 95 0 0		24470)
(000006C1 81 2 193 1 1 0		string-resource)
(000006C7 4 2 1		UpVar2-1)
(000006CA 14 14 0		T->JMP 000006DB)
(000006CD 9 194 1		"VLMSG.DLL")
(000006D0 51 160 95 0 0		24480)
(000006D5 81 2 193 1 1 0		string-resource)
(000006DB 95 2 228 40 0 0		yes-or-no-p)
(000006E1 63		nil->ret)
(000006E2 4 2 3		UpVar2-3)
(000006E5 9 139 1		':ERROR)
(000006E8 81 2 138 1 1 0		throw)
(000006EE 22		ret)
(000006EF 12 20 2		'(1716 nil))
(000006F2 9 135 1		'*mark-console-message*)
(000006F5 1		nil)
(000006F6 9 134 1		'*error-trace-stack*)
(000006F9 4 1 2		UpVar1-2)
(000006FC 61 3 0		nil->JMP 00000702)
(000006FF 3 134 1		*error-trace-stack*)
(00000702 24 10 0)
(00000705 4 1 3		UpVar1-3)
(00000708 57 1 0		list)
(0000070B 9 133 1		'_protected-apply)
(0000070E 9 139 1		':ERROR)
(00000711 4 1 0		UpVar1-0)
(00000714 1		nil)
(00000715 57 3 0		list)
(00000718 81 3 132 1 1 0		_catched-apply)
(0000071E 25 5 0)
(00000721 22		ret)
(00000722 12 19 2		'(1598 -unwind-protect-))
(00000725 1		nil)
(00000726 81 3 131 1 1 0		_unwinded-apply)
(0000072C 22		ret)
;;;def font-pitch-str->list 1837
(0000072D 20 1 1 1 0)
(00000732 9 130 1		"[\n")
(00000735 5 0		UnVar0)
(00000737 9 129 1		"\n]")
(0000073A 81 3 165 1 1 0		strcat)
(00000740 1		nil)
(00000741 1		nil)
(00000742 81 3 128 1 1 0		read-from-string)
(00000748 40		car)
(00000749 8 0		UnVar0)
(0000074B 5 0		UnVar0)
(0000074D 5 0		UnVar0)
(0000074F 40		car)
(00000750 81 1 192 1 1 0		string)
(00000756 81 2 127 1 1 0		setcar)
(0000075C 10)
(0000075D 5 0		UnVar0)
(0000075F 22		ret)
;;;def nil 1888
(00000760 20 4 3 3 0)
(00000765 5 0		UnVar0)
(00000767 8 3		UnVar3)
(00000769 5 3		UnVar3)
(0000076B 9 126 1		':CONTEXT)
(0000076E 38		=)
(0000076F 13 30 0		nil->JMP 00000790)
(00000772 5 2		UnVar2)
(00000774 81 1 125 1 1 0		fixnump)
(0000077A 60 12 0		T->JMP 00000789)
(0000077D 9 124 1		"fixnump:")
(00000780 5 2		UnVar2)
(00000782 81 2 123 1 1 0		_bat-err)
(00000788 10)
(00000789 50 1		1)
(0000078B 8 0		UnVar0)
(0000078D 15 64 1		JMP 000008D0)
(00000790 5 3		UnVar3)
(00000792 9 122 1		':QUIT)
(00000795 38		=)
(00000796 13 7 0		nil->JMP 000007A0)
(00000799 50 2		2)
(0000079B 8 0		UnVar0)
(0000079D 15 48 1		JMP 000008D0)
(000007A0 5 3		UnVar3)
(000007A2 9 121 1		'(:CONTENTS :INDEX))
(000007A5 81 2 120 1 1 0		memq)
(000007AB 13 7 0		nil->JMP 000007B5)
(000007AE 50 3		3)
(000007B0 8 0		UnVar0)
(000007B2 15 27 1		JMP 000008D0)
(000007B5 5 3		UnVar3)
(000007B7 9 119 1		'(:HELP-ON-HELP :HELPONHELP))
(000007BA 81 2 120 1 1 0		memq)
(000007C0 13 7 0		nil->JMP 000007CA)
(000007C3 50 4		4)
(000007C5 8 0		UnVar0)
(000007C7 15 6 1		JMP 000008D0)
(000007CA 5 3		UnVar3)
(000007CC 9 118 1		'(:SETCONTENTS :SETINDEX))
(000007CF 81 2 120 1 1 0		memq)
(000007D5 13 30 0		nil->JMP 000007F6)
(000007D8 5 2		UnVar2)
(000007DA 81 1 125 1 1 0		fixnump)
(000007E0 60 12 0		T->JMP 000007EF)
(000007E3 9 124 1		"fixnump:")
(000007E6 5 2		UnVar2)
(000007E8 81 2 123 1 1 0		_bat-err)
(000007EE 10)
(000007EF 50 5		5)
(000007F1 8 0		UnVar0)
(000007F3 15 218 0		JMP 000008D0)
(000007F6 5 3		UnVar3)
(000007F8 9 117 1		':CONTEXTPOPUP)
(000007FB 38		=)
(000007FC 13 30 0		nil->JMP 0000081D)
(000007FF 5 2		UnVar2)
(00000801 81 1 125 1 1 0		fixnump)
(00000807 60 12 0		T->JMP 00000816)
(0000080A 9 124 1		"fixnump:")
(0000080D 5 2		UnVar2)
(0000080F 81 2 123 1 1 0		_bat-err)
(00000815 10)
(00000816 50 8		8)
(00000818 8 0		UnVar0)
(0000081A 15 179 0		JMP 000008D0)
(0000081D 5 3		UnVar3)
(0000081F 9 116 1		'(:FORCE-FILE :FORCEFILE))
(00000822 81 2 120 1 1 0		memq)
(00000828 13 7 0		nil->JMP 00000832)
(0000082B 50 9		9)
(0000082D 8 0		UnVar0)
(0000082F 15 158 0		JMP 000008D0)
(00000832 5 3		UnVar3)
(00000834 9 115 1		':FINDER)
(00000837 38		=)
(00000838 13 7 0		nil->JMP 00000842)
(0000083B 50 11		11)
(0000083D 8 0		UnVar0)
(0000083F 15 142 0		JMP 000008D0)
(00000842 5 3		UnVar3)
(00000844 9 114 1		':KEY)
(00000847 38		=)
(00000848 13 29 0		nil->JMP 00000868)
(0000084B 5 2		UnVar2)
(0000084D 37 4		stringp)
(0000084F 60 12 0		T->JMP 0000085E)
(00000852 9 113 1		"stringp:")
(00000855 5 2		UnVar2)
(00000857 81 2 123 1 1 0		_bat-err)
(0000085D 10)
(0000085E 51 1 1 0 0		257)
(00000863 8 0		UnVar0)
(00000865 15 104 0		JMP 000008D0)
(00000868 5 3		UnVar3)
(0000086A 9 112 1		':COMMAND)
(0000086D 38		=)
(0000086E 13 29 0		nil->JMP 0000088E)
(00000871 5 2		UnVar2)
(00000873 37 4		stringp)
(00000875 60 12 0		T->JMP 00000884)
(00000878 9 113 1		"stringp:")
(0000087B 5 2		UnVar2)
(0000087D 81 2 123 1 1 0		_bat-err)
(00000883 10)
(00000884 51 2 1 0 0		258)
(00000889 8 0		UnVar0)
(0000088B 15 66 0		JMP 000008D0)
(0000088E 5 3		UnVar3)
(00000890 9 111 1		'(:PARTIAL-KEY :PARTIALKEY))
(00000893 81 2 120 1 1 0		memq)
(00000899 13 29 0		nil->JMP 000008B9)
(0000089C 5 2		UnVar2)
(0000089E 37 4		stringp)
(000008A0 60 12 0		T->JMP 000008AF)
(000008A3 9 113 1		"stringp:")
(000008A6 5 2		UnVar2)
(000008A8 81 2 123 1 1 0		_bat-err)
(000008AE 10)
(000008AF 51 5 1 0 0		261)
(000008B4 8 0		UnVar0)
(000008B6 15 23 0		JMP 000008D0)
(000008B9 9 194 1		"VLMSG.DLL")
(000008BC 51 170 95 0 0		24490)
(000008C1 81 2 193 1 1 0		string-resource)
(000008C7 5 0		UnVar0)
(000008C9 81 2 110 1 1 0		_msg-err)
(000008CF 10)
(000008D0 5 0		UnVar0)
(000008D2 5 1		UnVar1)
(000008D4 5 2		UnVar2)
(000008D6 81 3 109 1 1 0		_mswin-help)
(000008DC 22		ret)
;;;def mswin-help 2269
(000008DD 20 3 1 3 0)
(000008E2 5 0		UnVar0)
(000008E4 81 1 108 1 1 0		keywordp)
(000008EA 13 12 0		nil->JMP 000008F9)
(000008ED 5 0		UnVar0)
(000008EF 5 1		UnVar1)
(000008F1 5 2		UnVar2)
(000008F3 96 3 96 7 0 0		func 00000760)
(000008F9 5 0		UnVar0)
(000008FB 5 1		UnVar1)
(000008FD 5 2		UnVar2)
(000008FF 81 3 109 1 1 0		_mswin-help)
(00000905 22		ret)
;;;def sys-color 2310
(00000906 20 2 1 1 0)
(0000090B 100 1		UNVar1)
(0000090D 5 0		UnVar0)
(0000090F 9 107 1		'(:COLOR_SCROLLBAR :COLOR_BACKGROUND :COLOR_ACTIVECAPTION :COLOR_INACTIVECAPTION :COLOR_MENU :COLOR_WINDOW :COLOR_WINDOWFRAME :COLOR_MENUTEXT :COLOR_WINDOWTEXT :COLOR_CAPTIONTEXT :COLOR_ACTIVEBORDER :COLOR_INACTIVEBORDER :COLOR_APPWORKSPACE :COLOR_HIGHLIGHT :COLOR_HIGHLIGHTTEXT :COLOR_BTNFACE :COLOR_BTNSHADOW :COLOR_GRAYTEXT :COLOR_BTNTEXT :COLOR_INACTIVECAPTIONTEXT :COLOR_BTNHIGHLIGHT))
(00000912 81 2 106 1 1 0		vector-position)
(00000918 8 1		UnVar1)
(0000091A 5 1		UnVar1)
(0000091C 13 3 0		nil->JMP 00000922)
(0000091F 15 23 0		JMP 00000939)
(00000922 9 194 1		"VLMSG.DLL")
(00000925 51 180 95 0 0		24500)
(0000092A 81 2 193 1 1 0		string-resource)
(00000930 5 0		UnVar0)
(00000932 81 2 110 1 1 0		_msg-err)
(00000938 10)
(00000939 5 1		UnVar1)
(0000093B 81 1 105 1 1 0		_mswin-sys-color)
(00000941 22		ret)
;;;def twin.set-sys-colors 2370
(00000942 20 1 1 1 0)
(00000947 5 0		UnVar0)
(00000949 9 104 1		':COLOR_WINDOWTEXT)
(0000094C 95 1 6 9 0 0		sys-color)
(00000952 81 2 103 1 1 0		TWin.fcolor<-)
(00000958 10)
(00000959 5 0		UnVar0)
(0000095B 9 102 1		':COLOR_WINDOW)
(0000095E 95 1 6 9 0 0		sys-color)
(00000964 81 2 101 1 1 0		TWin.bcolor<-)
(0000096A 10)
(0000096B 5 0		UnVar0)
(0000096D 2		T)
(0000096E 96 2 67 0 0 0		update-host-spouse)
;;;def !di-right-mouse-click 2420
(00000974 20 1 1 1 0)
(00000979 1		nil)
(0000097A 22		ret)
;;;def !combo_notif-info 2427
(0000097B 20 1 1 1 0)
(00000980 1		nil)
(00000981 22		ret)
;;;def !dialog-escape 2434
(00000982 20 2 1 1 0)
(00000987 9 100 1		'!dialog-escape)
(0000098A 5 0		UnVar0)
(0000098C 81 2 204 1 1 0		compute-applicable-methods)
(00000992 8 1		UnVar1)
(00000994 5 1		UnVar1)
(00000996 13 3 0		nil->JMP 0000099C)
(00000999 15 12 0		JMP 000009A8)
(0000099C 9 100 1		'!dialog-escape)
(0000099F 5 0		UnVar0)
(000009A1 81 2 202 1 1 0		no-applicable-method)
(000009A7 10)
(000009A8 5 0		UnVar0)
(000009AA 5 1		UnVar1)
(000009AC 46 1		invoke+ret)
;;;def !dialog-size-hook 2478
(000009AE 20 2 1 1 0)
(000009B3 9 99 1		'!dialog-size-hook)
(000009B6 5 0		UnVar0)
(000009B8 81 2 204 1 1 0		compute-applicable-methods)
(000009BE 8 1		UnVar1)
(000009C0 5 1		UnVar1)
(000009C2 13 3 0		nil->JMP 000009C8)
(000009C5 15 12 0		JMP 000009D4)
(000009C8 9 99 1		'!dialog-size-hook)
(000009CB 5 0		UnVar0)
(000009CD 81 2 202 1 1 0		no-applicable-method)
(000009D3 10)
(000009D4 5 0		UnVar0)
(000009D6 5 1		UnVar1)
(000009D8 46 1		invoke+ret)
;;;def fcolor 2522
(000009DA 20 2 1 1 0)
(000009DF 9 98 1		'fcolor)
(000009E2 5 0		UnVar0)
(000009E4 81 2 204 1 1 0		compute-applicable-methods)
(000009EA 8 1		UnVar1)
(000009EC 5 1		UnVar1)
(000009EE 13 3 0		nil->JMP 000009F4)
(000009F1 15 12 0		JMP 00000A00)
(000009F4 9 98 1		'fcolor)
(000009F7 5 0		UnVar0)
(000009F9 81 2 202 1 1 0		no-applicable-method)
(000009FF 10)
(00000A00 5 0		UnVar0)
(00000A02 5 1		UnVar1)
(00000A04 46 1		invoke+ret)
;;;def fcolor<- 2566
(00000A06 20 3 2 2 0)
(00000A0B 9 97 1		'fcolor<-)
(00000A0E 5 0		UnVar0)
(00000A10 81 2 204 1 1 0		compute-applicable-methods)
(00000A16 8 2		UnVar2)
(00000A18 5 2		UnVar2)
(00000A1A 13 3 0		nil->JMP 00000A20)
(00000A1D 15 14 0		JMP 00000A2E)
(00000A20 9 97 1		'fcolor<-)
(00000A23 5 0		UnVar0)
(00000A25 5 1		UnVar1)
(00000A27 81 3 202 1 1 0		no-applicable-method)
(00000A2D 10)
(00000A2E 5 0		UnVar0)
(00000A30 5 1		UnVar1)
(00000A32 5 2		UnVar2)
(00000A34 46 2		invoke+ret)
;;;def bcolor 2614
(00000A36 20 2 1 1 0)
(00000A3B 9 96 1		'bcolor)
(00000A3E 5 0		UnVar0)
(00000A40 81 2 204 1 1 0		compute-applicable-methods)
(00000A46 8 1		UnVar1)
(00000A48 5 1		UnVar1)
(00000A4A 13 3 0		nil->JMP 00000A50)
(00000A4D 15 12 0		JMP 00000A5C)
(00000A50 9 96 1		'bcolor)
(00000A53 5 0		UnVar0)
(00000A55 81 2 202 1 1 0		no-applicable-method)
(00000A5B 10)
(00000A5C 5 0		UnVar0)
(00000A5E 5 1		UnVar1)
(00000A60 46 1		invoke+ret)
;;;def bcolor<- 2658
(00000A62 20 3 2 2 0)
(00000A67 9 95 1		'bcolor<-)
(00000A6A 5 0		UnVar0)
(00000A6C 81 2 204 1 1 0		compute-applicable-methods)
(00000A72 8 2		UnVar2)
(00000A74 5 2		UnVar2)
(00000A76 13 3 0		nil->JMP 00000A7C)
(00000A79 15 14 0		JMP 00000A8A)
(00000A7C 9 95 1		'bcolor<-)
(00000A7F 5 0		UnVar0)
(00000A81 5 1		UnVar1)
(00000A83 81 3 202 1 1 0		no-applicable-method)
(00000A89 10)
(00000A8A 5 0		UnVar0)
(00000A8C 5 1		UnVar1)
(00000A8E 5 2		UnVar2)
(00000A90 46 2		invoke+ret)
;;;def dialog._bcolor 2706
(00000A92 20 1 0 0 1)
(00000A97 9 94 1		'dialog.bcolor)
(00000A9A 5 0		UnVar0)
(00000A9C 84		apply+ret)
;;;def dialog._bcolor<- 2717
(00000A9D 20 1 0 0 1)
(00000AA2 9 93 1		'dialog.bcolor<-)
(00000AA5 5 0		UnVar0)
(00000AA7 84		apply+ret)
;;;def dialog-item._bcolor 2728
(00000AA8 20 1 0 0 1)
(00000AAD 9 92 1		'dialog-item.bcolor)
(00000AB0 5 0		UnVar0)
(00000AB2 84		apply+ret)
;;;def dialog-item._bcolor<- 2739
(00000AB3 20 1 0 0 1)
(00000AB8 9 91 1		'dialog-item.bcolor<-)
(00000ABB 5 0		UnVar0)
(00000ABD 84		apply+ret)
;;;def dialog-item._fcolor 2750
(00000ABE 20 1 0 0 1)
(00000AC3 9 90 1		'dialog-item.fcolor)
(00000AC6 5 0		UnVar0)
(00000AC8 84		apply+ret)
;;;def dialog-item._fcolor<- 2761
(00000AC9 20 1 0 0 1)
(00000ACE 9 89 1		'dialog-item.fcolor<-)
(00000AD1 5 0		UnVar0)
(00000AD3 84		apply+ret)
;;;def _set-bit 2772
(00000AD4 20 3 3 3 0)
(00000AD9 5 2		UnVar2)
(00000ADB 13 11 0		nil->JMP 00000AE9)
(00000ADE 5 0		UnVar0)
(00000AE0 5 1		UnVar1)
(00000AE2 81 2 88 1 1 0		logior)
(00000AE8 22		ret)
(00000AE9 5 0		UnVar0)
(00000AEB 5 1		UnVar1)
(00000AED 81 1 87 1 1 0		lognot)
(00000AF3 81 2 167 1 1 0		logand)
(00000AF9 22		ret)
;;;def dialog-item.disable 2810
(00000AFA 20 1 1 1 0)
(00000AFF 50 0		0)
(00000B01 51 0 0 0 8		134217728)
(00000B06 5 0		UnVar0)
(00000B08 81 1 86 1 1 0		dialog-item._msw-style)
(00000B0E 81 2 167 1 1 0		logand)
(00000B14 81 2 85 1 1 0		/=&)
(00000B1A 22		ret)
;;;def dialog-item.disable<- 2843
(00000B1B 20 3 2 2 0)
(00000B20 100 2		UNVar2)
(00000B22 5 0		UnVar0)
(00000B24 81 1 86 1 1 0		dialog-item._msw-style)
(00000B2A 8 2		UnVar2)
(00000B2C 5 2		UnVar2)
(00000B2E 51 0 0 0 8		134217728)
(00000B33 5 1		UnVar1)
(00000B35 95 3 212 10 0 0		_set-bit)
(00000B3B 8 2		UnVar2)
(00000B3D 5 0		UnVar0)
(00000B3F 5 2		UnVar2)
(00000B41 81 2 84 1 1 0		dialog-item._msw-style<-)
(00000B47 22		ret)
;;;def dialogp 2888
(00000B48 20 1 1 1 0)
(00000B4D 5 0		UnVar0)
(00000B4F 9 83 1		'dialog)
(00000B52 47 2 82 1 32 32		typep)
;;;def dialog.!dialog-size-hook 2904
(00000B58 20 1 1 1 0)
(00000B5D 1		nil)
(00000B5E 22		ret)
;;;def dialog.!dialog-escape 2911
(00000B5F 20 1 1 1 0)
(00000B64 5 0		UnVar0)
(00000B66 81 1 81 1 1 0		dialog._border-style)
(00000B6C 50 64		64)
(00000B6E 81 2 167 1 1 0		logand)
(00000B74 81 1 80 1 1 0		ZEROP)
(00000B7A 13 12 0		nil->JMP 00000B89)
(00000B7D 5 0		UnVar0)
(00000B7F 95 1 197 0 0 0		destroy-host-spouse)
(00000B85 10)
(00000B86 15 10 0		JMP 00000B93)
(00000B89 3 79 1		*active-mdiwindow*)
(00000B8C 81 1 78 1 1 0		mdiwindow-activate)
(00000B92 10)
(00000B93 9 77 1		'identity)
(00000B96 1		nil)
(00000B97 81 2 76 1 1 0		put-command)
(00000B9D 22		ret)
;;;def dialog.new-instance 2974
(00000B9E 20 22 5 5 1)
(00000BA3 5 5		UnVar5)
(00000BA5 8 6		UnVar6)
(00000BA7 5 6		UnVar6)
(00000BA9 9 75 1		':FONT)
(00000BAC 1		nil)
(00000BAD 81 3 74 1 1 0		getf)
(00000BB3 8 7		UnVar7)
(00000BB5 5 6		UnVar6)
(00000BB7 9 73 1		':PITCH)
(00000BBA 1		nil)
(00000BBB 81 3 74 1 1 0		getf)
(00000BC1 8 8		UnVar8)
(00000BC3 5 6		UnVar6)
(00000BC5 9 72 1		':PARENT)
(00000BC8 1		nil)
(00000BC9 81 3 74 1 1 0		getf)
(00000BCF 8 9		UnVar9)
(00000BD1 5 6		UnVar6)
(00000BD3 9 71 1		':DEFAULT-PUSH-BUTTON)
(00000BD6 1		nil)
(00000BD7 81 3 74 1 1 0		getf)
(00000BDD 8 10		UnVar10)
(00000BDF 5 6		UnVar6)
(00000BE1 9 70 1		':CLOSE-BOX-COMMAND)
(00000BE4 1		nil)
(00000BE5 81 3 74 1 1 0		getf)
(00000BEB 8 11		UnVar11)
(00000BED 5 6		UnVar6)
(00000BEF 9 69 1		':STATES)
(00000BF2 1		nil)
(00000BF3 81 3 74 1 1 0		getf)
(00000BF9 8 12		UnVar12)
(00000BFB 5 6		UnVar6)
(00000BFD 9 68 1		':L-CONTEXT)
(00000C00 1		nil)
(00000C01 81 3 74 1 1 0		getf)
(00000C07 8 13		UnVar13)
(00000C09 5 0		UnVar0)
(00000C0B 8 14		UnVar14)
(00000C0D 5 14		UnVar14)
(00000C0F 44 1		IDFun1)
(00000C11 13 13 0		nil->JMP 00000C21)
(00000C14 5 14		UnVar14)
(00000C16 44 1		IDFun1)
(00000C18 81 1 125 1 1 0		fixnump)
(00000C1E 15 1 0		JMP 00000C22)
(00000C21 2		T)
(00000C22 9 67 1		"Bad apex")
(00000C25 5 14		UnVar14)
(00000C27 44 1		IDFun1)
(00000C29 53 3 66 1 1 32		assert)
(00000C2F 10)
(00000C30 5 14		UnVar14)
(00000C32 44 2		IDFun2)
(00000C34 13 13 0		nil->JMP 00000C44)
(00000C37 5 14		UnVar14)
(00000C39 44 2		IDFun2)
(00000C3B 81 1 125 1 1 0		fixnump)
(00000C41 15 1 0		JMP 00000C45)
(00000C44 2		T)
(00000C45 9 65 1		"Bad size")
(00000C48 5 14		UnVar14)
(00000C4A 44 2		IDFun2)
(00000C4C 53 3 66 1 1 32		assert)
(00000C52 10)
(00000C53 5 3		UnVar3)
(00000C55 37 4		stringp)
(00000C57 9 64 1		"Bad caption")
(00000C5A 5 14		UnVar14)
(00000C5C 44 0		IDFun0)
(00000C5E 53 3 66 1 1 32		assert)
(00000C64 10)
(00000C65 5 4		UnVar4)
(00000C67 8 15		UnVar15)
(00000C69 100 16		UNVar16)
(00000C6B 2		T)
(00000C6C 8 16		UnVar16)
(00000C6E 15 5 0		JMP 00000C76)
(00000C71 5 15		UnVar15)
(00000C73 41		cdr)
(00000C74 8 15		UnVar15)
(00000C76 5 15		UnVar15)
(00000C78 61 32 0		nil->JMP 00000C9B)
(00000C7B 5 15		UnVar15)
(00000C7D 40		car)
(00000C7E 8 17		UnVar17)
(00000C80 5 17		UnVar17)
(00000C82 40		car)
(00000C83 9 63 1		'dialog-item)
(00000C86 53 2 82 1 1 32		typep)
(00000C8C 61 9 0		nil->JMP 00000C98)
(00000C8F 5 17		UnVar17)
(00000C91 41		cdr)
(00000C92 81 1 125 1 1 0		fixnump)
(00000C98 11)
(00000C99 8 16		UnVar16)
(00000C9B 60 211 255		T->JMP 00000C71)
(00000C9E 5 16		UnVar16)
(00000CA0 9 62 1		"Bad item list!")
(00000CA3 53 2 66 1 1 32		assert)
(00000CA9 10)
(00000CAA 5 2		UnVar2)
(00000CAC 13 13 0		nil->JMP 00000CBC)
(00000CAF 5 2		UnVar2)
(00000CB1 50 0		0)
(00000CB3 81 2 175 1 1 0		=&)
(00000CB9 15 1 0		JMP 00000CBD)
(00000CBC 2		T)
(00000CBD 13 151 0		nil->JMP 00000D57)
(00000CC0 50 0		0)
(00000CC2 8 15		UnVar15)
(00000CC4 50 0		0)
(00000CC6 8 16		UnVar16)
(00000CC8 100 17		UNVar17)
(00000CCA 100 18		UNVar18)
(00000CCC 100 19		UNVar19)
(00000CCE 5 4		UnVar4)
(00000CD0 8 20		UnVar20)
(00000CD2 100 21		UNVar21)
(00000CD4 15 75 0		JMP 00000D22)
(00000CD7 5 20		UnVar20)
(00000CD9 40		car)
(00000CDA 8 21		UnVar21)
(00000CDC 5 20		UnVar20)
(00000CDE 41		cdr)
(00000CDF 8 20		UnVar20)
(00000CE1 5 21		UnVar21)
(00000CE3 40		car)
(00000CE4 9 61 1		'size)
(00000CE7 81 2 60 1 1 0		slot-value)
(00000CED 5 21		UnVar21)
(00000CEF 41		cdr)
(00000CF0 81 2 59 1 1 0		add-ipoints)
(00000CF6 8 17		UnVar17)
(00000CF8 5 17		UnVar17)
(00000CFA 81 1 58 1 1 0		ipoint-h)
(00000D00 11)
(00000D01 8 18		UnVar18)
(00000D03 5 15		UnVar15)
(00000D05 75		>)
(00000D06 13 4 0		nil->JMP 00000D0D)
(00000D09 5 18		UnVar18)
(00000D0B 8 15		UnVar15)
(00000D0D 5 17		UnVar17)
(00000D0F 81 1 57 1 1 0		ipoint-v)
(00000D15 11)
(00000D16 8 19		UnVar19)
(00000D18 5 16		UnVar16)
(00000D1A 75		>)
(00000D1B 13 4 0		nil->JMP 00000D22)
(00000D1E 5 19		UnVar19)
(00000D20 8 16		UnVar16)
(00000D22 5 20		UnVar20)
(00000D24 60 176 255		T->JMP 00000CD7)
(00000D27 5 15		UnVar15)
(00000D29 50 0		0)
(00000D2B 81 2 175 1 1 0		=&)
(00000D31 13 5 0		nil->JMP 00000D39)
(00000D34 3 56 1		*dflt-dialog-width*)
(00000D37 8 15		UnVar15)
(00000D39 5 16		UnVar16)
(00000D3B 50 0		0)
(00000D3D 81 2 175 1 1 0		=&)
(00000D43 13 5 0		nil->JMP 00000D4B)
(00000D46 3 55 1		*dflt-dialog-heigth*)
(00000D49 8 16		UnVar16)
(00000D4B 5 15		UnVar15)
(00000D4D 5 16		UnVar16)
(00000D4F 81 2 54 1 1 0		make-ipoint)
(00000D55 8 2		UnVar2)
(00000D57 5 1		UnVar1)
(00000D59 5 14		UnVar14)
(00000D5B 45 1		IDFun1)
(00000D5D 10)
(00000D5E 5 2		UnVar2)
(00000D60 5 14		UnVar14)
(00000D62 45 2		IDFun2)
(00000D64 10)
(00000D65 5 3		UnVar3)
(00000D67 5 14		UnVar14)
(00000D69 45 0		IDFun0)
(00000D6B 10)
(00000D6C 5 4		UnVar4)
(00000D6E 5 14		UnVar14)
(00000D70 45 5		IDFun5)
(00000D72 10)
(00000D73 5 12		UnVar12)
(00000D75 5 14		UnVar14)
(00000D77 45 9		IDFun9)
(00000D79 10)
(00000D7A 5 7		UnVar7)
(00000D7C 13 7 0		nil->JMP 00000D86)
(00000D7F 5 7		UnVar7)
(00000D81 5 14		UnVar14)
(00000D83 45 3		IDFun3)
(00000D85 10)
(00000D86 5 8		UnVar8)
(00000D88 13 7 0		nil->JMP 00000D92)
(00000D8B 5 8		UnVar8)
(00000D8D 5 14		UnVar14)
(00000D8F 45 4		IDFun4)
(00000D91 10)
(00000D92 5 9		UnVar9)
(00000D94 13 7 0		nil->JMP 00000D9E)
(00000D97 5 9		UnVar9)
(00000D99 5 14		UnVar14)
(00000D9B 45 6		IDFun6)
(00000D9D 10)
(00000D9E 5 10		UnVar10)
(00000DA0 13 7 0		nil->JMP 00000DAA)
(00000DA3 5 10		UnVar10)
(00000DA5 5 14		UnVar14)
(00000DA7 45 7		IDFun7)
(00000DA9 10)
(00000DAA 5 11		UnVar11)
(00000DAC 13 7 0		nil->JMP 00000DB6)
(00000DAF 5 11		UnVar11)
(00000DB1 5 14		UnVar14)
(00000DB3 45 8		IDFun8)
(00000DB5 10)
(00000DB6 5 13		UnVar13)
(00000DB8 13 10 0		nil->JMP 00000DC5)
(00000DBB 5 13		UnVar13)
(00000DBD 5 14		UnVar14)
(00000DBF 45 10		IDFun10)
(00000DC1 10)
(00000DC2 15 21 0		JMP 00000DDA)
(00000DC5 5 9		UnVar9)
(00000DC7 13 16 0		nil->JMP 00000DDA)
(00000DCA 5 9		UnVar9)
(00000DCC 9 53 1		'l-context)
(00000DCF 81 2 60 1 1 0		slot-value)
(00000DD5 5 14		UnVar14)
(00000DD7 45 10		IDFun10)
(00000DD9 10)
(00000DDA 5 0		UnVar0)
(00000DDC 22		ret)
;;;def dialog 3549
(00000DDD 20 1 0 0 1)
(00000DE2 9 18 2		'(2974 dialog.new-instance))
(00000DE5 9 83 1		'dialog)
(00000DE8 53 1 52 1 1 32		allocate-instance)
(00000DEE 5 0		UnVar0)
(00000DF0 42		cons)
(00000DF1 84		apply+ret)
;;;def dialog.print-object 3570
(00000DF2 20 3 1 2 0)
(00000DF7 5 0		UnVar0)
(00000DF9 8 2		UnVar2)
(00000DFB 5 1		UnVar1)
(00000DFD 9 51 1		"#<~@x ~s>")
(00000E00 5 0		UnVar0)
(00000E02 5 2		UnVar2)
(00000E04 44 0		IDFun0)
(00000E06 53 4 140 1 1 32		prinf)
(00000E0C 10)
(00000E0D 5 0		UnVar0)
(00000E0F 22		ret)
;;;def sync-up 3600
(00000E10 20 3 1 1 0)
(00000E15 5 0		UnVar0)
(00000E17 8 1		UnVar1)
(00000E19 100 2		UNVar2)
(00000E1B 9 50 1		'sync-up)
(00000E1E 5 1		UnVar1)
(00000E20 81 2 204 1 1 0		compute-applicable-methods)
(00000E26 8 2		UnVar2)
(00000E28 5 2		UnVar2)
(00000E2A 37 2		consp)
(00000E2C 13 10 0		nil->JMP 00000E39)
(00000E2F 5 2		UnVar2)
(00000E31 41		cdr)
(00000E32 5 1		UnVar1)
(00000E34 5 2		UnVar2)
(00000E36 40		car)
(00000E37 46 2		invoke+ret)
(00000E39 9 50 1		'sync-up)
(00000E3C 5 1		UnVar1)
(00000E3E 81 2 202 1 1 0		no-applicable-method)
(00000E44 22		ret)
;;;def dialog.sync-up 3653
(00000E45 20 5 2 2 0)
(00000E4A 5 1		UnVar1)
(00000E4C 8 2		UnVar2)
(00000E4E 5 2		UnVar2)
(00000E50 44 5		IDFun5)
(00000E52 8 3		UnVar3)
(00000E54 100 4		UNVar4)
(00000E56 15 20 0		JMP 00000E6D)
(00000E59 5 3		UnVar3)
(00000E5B 40		car)
(00000E5C 8 4		UnVar4)
(00000E5E 5 3		UnVar3)
(00000E60 41		cdr)
(00000E61 8 3		UnVar3)
(00000E63 5 4		UnVar4)
(00000E65 40		car)
(00000E66 95 1 16 14 0 0		sync-up)
(00000E6C 10)
(00000E6D 5 3		UnVar3)
(00000E6F 60 231 255		T->JMP 00000E59)
(00000E72 1		nil)
(00000E73 22		ret)
;;;def sync-down 3700
(00000E74 20 3 1 1 0)
(00000E79 5 0		UnVar0)
(00000E7B 8 1		UnVar1)
(00000E7D 100 2		UNVar2)
(00000E7F 9 49 1		'sync-down)
(00000E82 5 1		UnVar1)
(00000E84 81 2 204 1 1 0		compute-applicable-methods)
(00000E8A 8 2		UnVar2)
(00000E8C 5 2		UnVar2)
(00000E8E 37 2		consp)
(00000E90 13 10 0		nil->JMP 00000E9D)
(00000E93 5 2		UnVar2)
(00000E95 41		cdr)
(00000E96 5 1		UnVar1)
(00000E98 5 2		UnVar2)
(00000E9A 40		car)
(00000E9B 46 2		invoke+ret)
(00000E9D 9 49 1		'sync-down)
(00000EA0 5 1		UnVar1)
(00000EA2 81 2 202 1 1 0		no-applicable-method)
(00000EA8 22		ret)
;;;def dialog.sync-down 3753
(00000EA9 20 5 2 2 0)
(00000EAE 5 1		UnVar1)
(00000EB0 8 2		UnVar2)
(00000EB2 5 2		UnVar2)
(00000EB4 44 5		IDFun5)
(00000EB6 8 3		UnVar3)
(00000EB8 100 4		UNVar4)
(00000EBA 15 20 0		JMP 00000ED1)
(00000EBD 5 3		UnVar3)
(00000EBF 40		car)
(00000EC0 8 4		UnVar4)
(00000EC2 5 3		UnVar3)
(00000EC4 41		cdr)
(00000EC5 8 3		UnVar3)
(00000EC7 5 4		UnVar4)
(00000EC9 40		car)
(00000ECA 95 1 116 14 0 0		sync-down)
(00000ED0 10)
(00000ED1 5 3		UnVar3)
(00000ED3 60 231 255		T->JMP 00000EBD)
(00000ED6 1		nil)
(00000ED7 22		ret)
;;;def dialog-item.new-instance 3800
(00000ED8 20 5 3 4 0)
(00000EDD 5 0		UnVar0)
(00000EDF 8 4		UnVar4)
(00000EE1 5 1		UnVar1)
(00000EE3 5 4		UnVar4)
(00000EE5 45 1		IDFun1)
(00000EE7 10)
(00000EE8 5 2		UnVar2)
(00000EEA 5 4		UnVar4)
(00000EEC 45 0		IDFun0)
(00000EEE 10)
(00000EEF 5 3		UnVar3)
(00000EF1 5 4		UnVar4)
(00000EF3 45 2		IDFun2)
(00000EF5 10)
(00000EF6 5 0		UnVar0)
(00000EF8 22		ret)
;;;def dialog-item.host-spouse-exists-p 3833
(00000EF9 20 2 2 2 0)
(00000EFE 5 1		UnVar1)
(00000F00 96 1 67 0 0 0		update-host-spouse)
;;;def dialog-item.sync-up 3846
(00000F06 20 2 2 2 0)
(00000F0B 1		nil)
(00000F0C 22		ret)
;;;def dialog-item.sync-down 3853
(00000F0D 20 2 2 2 0)
(00000F12 1		nil)
(00000F13 22		ret)
;;;def dialog-item._untabstop 3860
(00000F14 20 2 1 1 0)
(00000F19 100 1		UNVar1)
(00000F1B 5 0		UnVar0)
(00000F1D 81 1 86 1 1 0		dialog-item._msw-style)
(00000F23 8 1		UnVar1)
(00000F25 5 0		UnVar0)
(00000F27 5 1		UnVar1)
(00000F29 51 0 0 1 0		65536)
(00000F2E 81 1 87 1 1 0		lognot)
(00000F34 81 2 167 1 1 0		logand)
(00000F3A 81 2 84 1 1 0		dialog-item._msw-style<-)
(00000F40 10)
(00000F41 5 0		UnVar0)
(00000F43 22		ret)
;;;def editable-text.new-instance 3908
(00000F44 20 6 2 5 0)
(00000F49 5 0		UnVar0)
(00000F4B 8 5		UnVar5)
(00000F4D 5 0		UnVar0)
(00000F4F 5 1		UnVar1)
(00000F51 5 2		UnVar2)
(00000F53 14 3 0		T->JMP 00000F59)
(00000F56 9 150 1		"")
(00000F59 5 4		UnVar4)
(00000F5B 95 4 216 14 0 0		dialog-item.new-instance)
(00000F61 10)
(00000F62 5 3		UnVar3)
(00000F64 5 5		UnVar5)
(00000F66 45 3		IDFun3)
(00000F68 10)
(00000F69 5 0		UnVar0)
(00000F6B 22		ret)
;;;def editable-text 3948
(00000F6C 20 1 0 0 1)
(00000F71 9 17 2		'(3908 editable-text.new-instance))
(00000F74 9 48 1		'editable-text)
(00000F77 53 1 52 1 1 32		allocate-instance)
(00000F7D 5 0		UnVar0)
(00000F7F 42		cons)
(00000F80 84		apply+ret)
;;;def static-text.new-instance 3969
(00000F81 20 9 2 4 1)
(00000F86 5 4		UnVar4)
(00000F88 8 5		UnVar5)
(00000F8A 5 5		UnVar5)
(00000F8C 9 47 1		':BCOLOR)
(00000F8F 1		nil)
(00000F90 81 3 74 1 1 0		getf)
(00000F96 8 6		UnVar6)
(00000F98 5 5		UnVar5)
(00000F9A 9 46 1		':FCOLOR)
(00000F9D 1		nil)
(00000F9E 81 3 74 1 1 0		getf)
(00000FA4 8 7		UnVar7)
(00000FA6 5 0		UnVar0)
(00000FA8 8 8		UnVar8)
(00000FAA 5 3		UnVar3)
(00000FAC 5 8		UnVar8)
(00000FAE 45 3		IDFun3)
(00000FB0 10)
(00000FB1 5 0		UnVar0)
(00000FB3 5 1		UnVar1)
(00000FB5 5 2		UnVar2)
(00000FB7 14 3 0		T->JMP 00000FBD)
(00000FBA 9 150 1		"")
(00000FBD 95 3 216 14 0 0		dialog-item.new-instance)
(00000FC3 10)
(00000FC4 5 7		UnVar7)
(00000FC6 13 11 0		nil->JMP 00000FD4)
(00000FC9 5 0		UnVar0)
(00000FCB 5 7		UnVar7)
(00000FCD 81 2 89 1 1 0		dialog-item.fcolor<-)
(00000FD3 10)
(00000FD4 5 6		UnVar6)
(00000FD6 13 14 0		nil->JMP 00000FE7)
(00000FD9 5 0		UnVar0)
(00000FDB 5 6		UnVar6)
(00000FDD 81 2 91 1 1 0		dialog-item.bcolor<-)
(00000FE3 10)
(00000FE4 2		T)
(00000FE5 8 7		UnVar7)
(00000FE7 5 7		UnVar7)
(00000FE9 13 10 0		nil->JMP 00000FF6)
(00000FEC 5 0		UnVar0)
(00000FEE 2		T)
(00000FEF 81 2 45 1 1 0		dialog-item.color-enabled<-)
(00000FF5 10)
(00000FF6 5 0		UnVar0)
(00000FF8 22		ret)
;;;def static-text 4089
(00000FF9 20 1 0 0 1)
(00000FFE 9 16 2		'(3969 static-text.new-instance))
(00001001 9 44 1		'static-text)
(00001004 53 1 52 1 1 32		allocate-instance)
(0000100A 5 0		UnVar0)
(0000100C 42		cons)
(0000100D 84		apply+ret)
;;;def icon.new-instance 4110
(0000100E 20 4 2 2 0)
(00001013 100 2		UNVar2)
(00001015 5 0		UnVar0)
(00001017 8 3		UnVar3)
(00001019 5 1		UnVar1)
(0000101B 37 4		stringp)
(0000101D 13 24 0		nil->JMP 00001038)
(00001020 9 43 1		"(icon <string>)")
(00001023 9 42 1		"(icon <resource>)")
(00001026 53 2 41 1 1 32		warn-obsolete)
(0000102C 10)
(0000102D 2		T)
(0000102E 5 1		UnVar1)
(00001030 81 2 40 1 1 0		icon-resource)
(00001036 8 1		UnVar1)
(00001038 5 1		UnVar1)
(0000103A 81 1 39 1 1 0		resource-type)
(00001040 9 38 1		':ICON)
(00001043 38		=)
(00001044 60 23 0		T->JMP 0000105E)
(00001047 9 194 1		"VLMSG.DLL")
(0000104A 51 236 94 0 0		24300)
(0000104F 81 2 193 1 1 0		string-resource)
(00001055 5 1		UnVar1)
(00001057 81 2 123 1 1 0		_bat-err)
(0000105D 10)
(0000105E 5 1		UnVar1)
(00001060 81 1 37 1 1 0		resource-id)
(00001066 8 2		UnVar2)
(00001068 5 2		UnVar2)
(0000106A 81 1 125 1 1 0		fixnump)
(00001070 13 19 0		nil->JMP 00001086)
(00001073 9 36 1		"#")
(00001076 5 2		UnVar2)
(00001078 81 1 35 1 1 0		itoa)
(0000107E 81 2 165 1 1 0		strcat)
(00001084 8 2		UnVar2)
(00001086 5 0		UnVar0)
(00001088 50 0		0)
(0000108A 5 2		UnVar2)
(0000108C 95 3 216 14 0 0		dialog-item.new-instance)
(00001092 10)
(00001093 5 1		UnVar1)
(00001095 5 3		UnVar3)
(00001097 45 3		IDFun3)
(00001099 10)
(0000109A 5 0		UnVar0)
(0000109C 22		ret)
;;;def icon 4253
(0000109D 20 1 1 1 0)
(000010A2 9 34 1		'icon)
(000010A5 53 1 52 1 1 32		allocate-instance)
(000010AB 5 0		UnVar0)
(000010AD 96 2 14 16 0 0		icon.new-instance)
;;;def bitmap-push-button.new-instance 4275
(000010B3 20 7 4 6 0)
(000010B8 5 0		UnVar0)
(000010BA 8 6		UnVar6)
(000010BC 5 4		UnVar4)
(000010BE 95 1 172 17 0 0		bitmap-push-button._chk-bitmaps)
(000010C4 9 33 1		"not a bitmap in bmp-push-button")
(000010C7 53 2 66 1 1 32		assert)
(000010CD 10)
(000010CE 5 0		UnVar0)
(000010D0 5 1		UnVar1)
(000010D2 5 2		UnVar2)
(000010D4 5 3		UnVar3)
(000010D6 95 4 216 14 0 0		dialog-item.new-instance)
(000010DC 10)
(000010DD 5 4		UnVar4)
(000010DF 5 6		UnVar6)
(000010E1 45 4		IDFun4)
(000010E3 10)
(000010E4 5 5		UnVar5)
(000010E6 5 6		UnVar6)
(000010E8 45 5		IDFun5)
(000010EA 10)
(000010EB 5 0		UnVar0)
(000010ED 22		ret)
;;;def bitmap-push-button 4334
(000010EE 20 1 0 0 1)
(000010F3 9 15 2		'(4275 bitmap-push-button.new-instance))
(000010F6 9 32 1		'bitmap-push-button)
(000010F9 53 1 52 1 1 32		allocate-instance)
(000010FF 5 0		UnVar0)
(00001101 42		cons)
(00001102 84		apply+ret)
;;;def bmp-push-button 4355
(00001103 20 7 5 6 0)
(00001108 100 6		UNVar6)
(0000110A 5 2		UnVar2)
(0000110C 81 1 58 1 1 0		ipoint-h)
(00001112 8 6		UnVar6)
(00001114 5 6		UnVar6)
(00001116 53 1 31 1 1 32		auto-scale-x)
(0000111C 5 2		UnVar2)
(0000111E 81 1 57 1 1 0		ipoint-v)
(00001124 53 1 30 1 1 32		auto-scale-y)
(0000112A 81 2 54 1 1 0		make-ipoint)
(00001130 9 150 1		"")
(00001133 5 3		UnVar3)
(00001135 5 0		UnVar0)
(00001137 5 1		UnVar1)
(00001139 5 2		UnVar2)
(0000113B 81 3 29 1 1 0		bitmap-resource.clip)
(00001141 5 0		UnVar0)
(00001143 5 1		UnVar1)
(00001145 5 6		UnVar6)
(00001147 50 0		0)
(00001149 81 2 54 1 1 0		make-ipoint)
(0000114F 81 2 59 1 1 0		add-ipoints)
(00001155 5 2		UnVar2)
(00001157 81 3 29 1 1 0		bitmap-resource.clip)
(0000115D 57 2 0		list)
(00001160 5 4		UnVar4)
(00001162 42		cons)
(00001163 57 1 0		list)
(00001166 5 5		UnVar5)
(00001168 96 5 238 16 0 0		bitmap-push-button)
;;;def bitmap-resource-p 4462
(0000116E 20 1 1 1 0)
(00001173 5 0		UnVar0)
(00001175 81 1 28 1 1 0		resourcep)
(0000117B 63		nil->ret)
(0000117C 5 0		UnVar0)
(0000117E 81 1 39 1 1 0		resource-type)
(00001184 9 27 1		':BITMAP)
(00001187 38		=)
(00001188 13 2 0		nil->JMP 0000118D)
(0000118B 2		T)
(0000118C 22		ret)
(0000118D 5 0		UnVar0)
(0000118F 81 1 39 1 1 0		resource-type)
(00001195 11)
(00001196 8 0		UnVar0)
(00001198 81 1 28 1 1 0		resourcep)
(0000119E 63		nil->ret)
(0000119F 5 0		UnVar0)
(000011A1 81 1 39 1 1 0		resource-type)
(000011A7 9 27 1		':BITMAP)
(000011AA 38		=)
(000011AB 22		ret)
;;;def bitmap-push-button._chk-bitmaps 4524
(000011AC 20 6 1 1 0)
(000011B1 5 0		UnVar0)
(000011B3 8 1		UnVar1)
(000011B5 100 2		UNVar2)
(000011B7 2		T)
(000011B8 8 2		UnVar2)
(000011BA 15 5 0		JMP 000011C2)
(000011BD 5 1		UnVar1)
(000011BF 41		cdr)
(000011C0 8 1		UnVar1)
(000011C2 5 1		UnVar1)
(000011C4 61 48 0		nil->JMP 000011F7)
(000011C7 5 1		UnVar1)
(000011C9 40		car)
(000011CA 8 3		UnVar3)
(000011CC 5 3		UnVar3)
(000011CE 40		car)
(000011CF 8 4		UnVar4)
(000011D1 100 5		UNVar5)
(000011D3 2		T)
(000011D4 8 5		UnVar5)
(000011D6 15 5 0		JMP 000011DE)
(000011D9 5 4		UnVar4)
(000011DB 41		cdr)
(000011DC 8 4		UnVar4)
(000011DE 5 4		UnVar4)
(000011E0 61 12 0		nil->JMP 000011EF)
(000011E3 5 4		UnVar4)
(000011E5 40		car)
(000011E6 95 1 110 17 0 0		bitmap-resource-p)
(000011EC 11)
(000011ED 8 5		UnVar5)
(000011EF 60 231 255		T->JMP 000011D9)
(000011F2 5 5		UnVar5)
(000011F4 11)
(000011F5 8 2		UnVar2)
(000011F7 60 195 255		T->JMP 000011BD)
(000011FA 5 2		UnVar2)
(000011FC 22		ret)
;;;def push-button.new-instance 4605
(000011FD 20 7 4 6 0)
(00001202 5 0		UnVar0)
(00001204 8 6		UnVar6)
(00001206 5 0		UnVar0)
(00001208 5 1		UnVar1)
(0000120A 5 2		UnVar2)
(0000120C 5 3		UnVar3)
(0000120E 95 4 216 14 0 0		dialog-item.new-instance)
(00001214 10)
(00001215 5 4		UnVar4)
(00001217 5 6		UnVar6)
(00001219 45 3		IDFun3)
(0000121B 10)
(0000121C 5 5		UnVar5)
(0000121E 13 8 0		nil->JMP 00001229)
(00001221 5 0		UnVar0)
(00001223 97 1 25 15 0 0		offset 00000F19)
(00001229 5 0		UnVar0)
(0000122B 22		ret)
;;;def push-button 4652
(0000122C 20 1 0 0 1)
(00001231 9 14 2		'(4605 push-button.new-instance))
(00001234 9 26 1		'push-button)
(00001237 53 1 52 1 1 32		allocate-instance)
(0000123D 5 0		UnVar0)
(0000123F 42		cons)
(00001240 84		apply+ret)
;;;def radio-button.new-instance 4673
(00001241 20 7 4 6 0)
(00001246 5 0		UnVar0)
(00001248 8 6		UnVar6)
(0000124A 5 0		UnVar0)
(0000124C 5 1		UnVar1)
(0000124E 5 2		UnVar2)
(00001250 5 3		UnVar3)
(00001252 95 4 216 14 0 0		dialog-item.new-instance)
(00001258 10)
(00001259 5 4		UnVar4)
(0000125B 5 6		UnVar6)
(0000125D 45 5		IDFun5)
(0000125F 10)
(00001260 5 5		UnVar5)
(00001262 5 6		UnVar6)
(00001264 45 3		IDFun3)
(00001266 10)
(00001267 5 0		UnVar0)
(00001269 22		ret)
;;;def radio-button 4714
(0000126A 20 1 0 0 1)
(0000126F 9 13 2		'(4673 radio-button.new-instance))
(00001272 9 25 1		'radio-button)
(00001275 53 1 52 1 1 32		allocate-instance)
(0000127B 5 0		UnVar0)
(0000127D 42		cons)
(0000127E 84		apply+ret)
;;;def check-box.new-instance 4735
(0000127F 20 7 3 6 0)
(00001284 5 0		UnVar0)
(00001286 8 6		UnVar6)
(00001288 5 0		UnVar0)
(0000128A 5 1		UnVar1)
(0000128C 5 2		UnVar2)
(0000128E 5 3		UnVar3)
(00001290 95 4 216 14 0 0		dialog-item.new-instance)
(00001296 10)
(00001297 5 4		UnVar4)
(00001299 5 6		UnVar6)
(0000129B 45 5		IDFun5)
(0000129D 10)
(0000129E 5 5		UnVar5)
(000012A0 5 6		UnVar6)
(000012A2 45 3		IDFun3)
(000012A4 10)
(000012A5 5 0		UnVar0)
(000012A7 22		ret)
;;;def check-box 4776
(000012A8 20 1 0 0 1)
(000012AD 9 12 2		'(4735 check-box.new-instance))
(000012B0 9 24 1		'check-box)
(000012B3 53 1 52 1 1 32		allocate-instance)
(000012B9 5 0		UnVar0)
(000012BB 42		cons)
(000012BC 84		apply+ret)
;;;def group-box.new-instance 4797
(000012BD 20 3 3 3 0)
(000012C2 5 0		UnVar0)
(000012C4 5 1		UnVar1)
(000012C6 5 2		UnVar2)
(000012C8 96 3 216 14 0 0		dialog-item.new-instance)
;;;def group-box 4814
(000012CE 20 2 2 2 0)
(000012D3 9 23 1		'group-box)
(000012D6 53 1 52 1 1 32		allocate-instance)
(000012DC 5 0		UnVar0)
(000012DE 5 1		UnVar1)
(000012E0 96 3 189 18 0 0		group-box.new-instance)
;;;def list-box.new-instance 4838
(000012E6 20 8 2 7 0)
(000012EB 5 0		UnVar0)
(000012ED 8 7		UnVar7)
(000012EF 5 0		UnVar0)
(000012F1 5 1		UnVar1)
(000012F3 9 150 1		"")
(000012F6 5 4		UnVar4)
(000012F8 95 4 216 14 0 0		dialog-item.new-instance)
(000012FE 10)
(000012FF 5 2		UnVar2)
(00001301 5 7		UnVar7)
(00001303 45 4		IDFun4)
(00001305 10)
(00001306 5 3		UnVar3)
(00001308 5 7		UnVar7)
(0000130A 45 5		IDFun5)
(0000130C 10)
(0000130D 5 5		UnVar5)
(0000130F 5 7		UnVar7)
(00001311 45 6		IDFun6)
(00001313 10)
(00001314 5 6		UnVar6)
(00001316 5 7		UnVar7)
(00001318 45 3		IDFun3)
(0000131A 10)
(0000131B 5 0		UnVar0)
(0000131D 22		ret)
;;;def list-box 4894
(0000131E 20 1 0 0 1)
(00001323 9 11 2		'(4838 list-box.new-instance))
(00001326 9 22 1		'list-box)
(00001329 53 1 52 1 1 32		allocate-instance)
(0000132F 5 0		UnVar0)
(00001331 42		cons)
(00001332 84		apply+ret)
;;;def list-box.selection-index 4915
(00001333 20 4 1 1 0)
(00001338 5 0		UnVar0)
(0000133A 8 1		UnVar1)
(0000133C 50 0		0)
(0000133E 8 2		UnVar2)
(00001340 5 1		UnVar1)
(00001342 44 4		IDFun4)
(00001344 8 3		UnVar3)
(00001346 15 10 0		JMP 00001353)
(00001349 5 2		UnVar2)
(0000134B 79		1+)
(0000134C 8 2		UnVar2)
(0000134E 5 3		UnVar3)
(00001350 41		cdr)
(00001351 8 3		UnVar3)
(00001353 5 3		UnVar3)
(00001355 13 7 0		nil->JMP 0000135F)
(00001358 5 3		UnVar3)
(0000135A 40		car)
(0000135B 41		cdr)
(0000135C 15 1 0		JMP 00001360)
(0000135F 2		T)
(00001360 35		not)
(00001361 60 229 255		T->JMP 00001349)
(00001364 5 3		UnVar3)
(00001366 63		nil->ret)
(00001367 5 2		UnVar2)
(00001369 22		ret)
;;;def drop-down-list-box.new-instance 4970
(0000136A 20 7 2 6 0)
(0000136F 5 0		UnVar0)
(00001371 8 6		UnVar6)
(00001373 5 0		UnVar0)
(00001375 5 1		UnVar1)
(00001377 9 150 1		"")
(0000137A 5 3		UnVar3)
(0000137C 95 4 216 14 0 0		dialog-item.new-instance)
(00001382 10)
(00001383 5 2		UnVar2)
(00001385 5 6		UnVar6)
(00001387 45 4		IDFun4)
(00001389 10)
(0000138A 5 4		UnVar4)
(0000138C 5 6		UnVar6)
(0000138E 45 5		IDFun5)
(00001390 10)
(00001391 5 5		UnVar5)
(00001393 5 6		UnVar6)
(00001395 45 3		IDFun3)
(00001397 10)
(00001398 5 0		UnVar0)
(0000139A 22		ret)
;;;def drop-down-list-box 5019
(0000139B 20 1 0 0 1)
(000013A0 9 10 2		'(4970 drop-down-list-box.new-instance))
(000013A3 9 21 1		'drop-down-list-box)
(000013A6 53 1 52 1 1 32		allocate-instance)
(000013AC 5 0		UnVar0)
(000013AE 42		cons)
(000013AF 84		apply+ret)
;;;def color-selector.new-instance 5040
(000013B0 20 6 2 5 0)
(000013B5 5 0		UnVar0)
(000013B7 8 5		UnVar5)
(000013B9 5 0		UnVar0)
(000013BB 5 1		UnVar1)
(000013BD 9 150 1		"")
(000013C0 5 2		UnVar2)
(000013C2 95 4 216 14 0 0		dialog-item.new-instance)
(000013C8 10)
(000013C9 5 4		UnVar4)
(000013CB 81 1 125 1 1 0		fixnump)
(000013D1 61 2 0		nil->JMP 000013D6)
(000013D4 5 4		UnVar4)
(000013D6 5 5		UnVar5)
(000013D8 45 4		IDFun4)
(000013DA 10)
(000013DB 5 4		UnVar4)
(000013DD 81 1 20 1 1 0		listp)
(000013E3 61 22 0		nil->JMP 000013FC)
(000013E6 5 4		UnVar4)
(000013E8 81 1 19 1 1 0		list-length)
(000013EE 50 3		3)
(000013F0 38		=)
(000013F1 61 8 0		nil->JMP 000013FC)
(000013F4 5 4		UnVar4)
(000013F6 81 1 18 1 1 0		list->RGB)
(000013FC 5 5		UnVar5)
(000013FE 45 5		IDFun5)
(00001400 10)
(00001401 5 3		UnVar3)
(00001403 5 5		UnVar5)
(00001405 45 3		IDFun3)
(00001407 10)
(00001408 5 0		UnVar0)
(0000140A 22		ret)
;;;def color-selector 5131
(0000140B 20 1 0 0 1)
(00001410 9 9 2		'(5040 color-selector.new-instance))
(00001413 9 17 1		'color-selector)
(00001416 53 1 52 1 1 32		allocate-instance)
(0000141C 5 0		UnVar0)
(0000141E 42		cons)
(0000141F 84		apply+ret)
;;;def accessed-verify 5152
(00001420 20 2 1 1 0)
(00001425 9 16 1		'accessed-verify)
(00001428 5 0		UnVar0)
(0000142A 81 2 204 1 1 0		compute-applicable-methods)
(00001430 8 1		UnVar1)
(00001432 5 1		UnVar1)
(00001434 13 3 0		nil->JMP 0000143A)
(00001437 15 12 0		JMP 00001446)
(0000143A 9 16 1		'accessed-verify)
(0000143D 5 0		UnVar0)
(0000143F 81 2 202 1 1 0		no-applicable-method)
(00001445 10)
(00001446 5 0		UnVar0)
(00001448 5 1		UnVar1)
(0000144A 46 1		invoke+ret)
;;;def dialog.accessed-verify 5196
(0000144C 20 4 1 1 0)
(00001451 100 1		UNVar1)
(00001453 5 0		UnVar0)
(00001455 8 2		UnVar2)
(00001457 5 2		UnVar2)
(00001459 44 5		IDFun5)
(0000145B 8 1		UnVar1)
(0000145D 15 13 0		JMP 0000146D)
(00001460 5 1		UnVar1)
(00001462 8 3		UnVar3)
(00001464 5 3		UnVar3)
(00001466 41		cdr)
(00001467 8 1		UnVar1)
(00001469 5 3		UnVar3)
(0000146B 40		car)
(0000146C 10)
(0000146D 5 1		UnVar1)
(0000146F 61 27 0		nil->JMP 0000148D)
(00001472 5 1		UnVar1)
(00001474 40		car)
(00001475 40		car)
(00001476 95 1 150 55 0 0		accessed-dialog-item-p)
(0000147C 13 13 0		nil->JMP 0000148C)
(0000147F 5 1		UnVar1)
(00001481 40		car)
(00001482 40		car)
(00001483 95 1 32 20 0 0		accessed-verify)
(00001489 15 1 0		JMP 0000148D)
(0000148C 2		T)
(0000148D 60 208 255		T->JMP 00001460)
(00001490 5 1		UnVar1)
(00001492 13 7 0		nil->JMP 0000149C)
(00001495 5 1		UnVar1)
(00001497 40		car)
(00001498 40		car)
(00001499 6 15 1		_%reinput%)
(0000149C 5 1		UnVar1)
(0000149E 35		not)
(0000149F 22		ret)
;;;def bmp-button.new-instance 5280
(000014A0 20 8 4 7 0)
(000014A5 5 0		UnVar0)
(000014A7 8 7		UnVar7)
(000014A9 5 5		UnVar5)
(000014AB 13 18 0		nil->JMP 000014C0)
(000014AE 5 5		UnVar5)
(000014B0 95 1 110 17 0 0		bitmap-resource-p)
(000014B6 9 33 1		"not a bitmap in bmp-push-button")
(000014B9 53 2 66 1 1 32		assert)
(000014BF 10)
(000014C0 5 0		UnVar0)
(000014C2 5 1		UnVar1)
(000014C4 5 2		UnVar2)
(000014C6 5 3		UnVar3)
(000014C8 95 4 216 14 0 0		dialog-item.new-instance)
(000014CE 10)
(000014CF 5 4		UnVar4)
(000014D1 5 7		UnVar7)
(000014D3 45 3		IDFun3)
(000014D5 10)
(000014D6 5 5		UnVar5)
(000014D8 5 7		UnVar7)
(000014DA 45 4		IDFun4)
(000014DC 10)
(000014DD 5 6		UnVar6)
(000014DF 5 7		UnVar7)
(000014E1 45 5		IDFun5)
(000014E3 10)
(000014E4 5 0		UnVar0)
(000014E6 22		ret)
;;;def bmp-button 5351
(000014E7 20 1 0 0 1)
(000014EC 9 8 2		'(5280 bmp-button.new-instance))
(000014EF 9 14 1		'bmp-button)
(000014F2 53 1 52 1 1 32		allocate-instance)
(000014F8 5 0		UnVar0)
(000014FA 42		cons)
(000014FB 84		apply+ret)
;;;def bmp-push-button1 5372
(000014FC 20 9 5 6 0)
(00001501 100 6		UNVar6)
(00001503 100 7		UNVar7)
(00001505 100 8		UNVar8)
(00001507 5 2		UnVar2)
(00001509 81 1 58 1 1 0		ipoint-h)
(0000150F 50 3		3)
(00001511 70		+)
(00001512 8 8		UnVar8)
(00001514 5 2		UnVar2)
(00001516 81 1 57 1 1 0		ipoint-v)
(0000151C 50 3		3)
(0000151E 70		+)
(0000151F 8 7		UnVar7)
(00001521 5 8		UnVar8)
(00001523 53 1 31 1 1 32		auto-scale-x)
(00001529 5 7		UnVar7)
(0000152B 53 1 30 1 1 32		auto-scale-y)
(00001531 81 2 54 1 1 0		make-ipoint)
(00001537 8 6		UnVar6)
(00001539 5 6		UnVar6)
(0000153B 9 150 1		"")
(0000153E 5 3		UnVar3)
(00001540 5 4		UnVar4)
(00001542 5 0		UnVar0)
(00001544 5 1		UnVar1)
(00001546 5 2		UnVar2)
(00001548 81 3 29 1 1 0		bitmap-resource.clip)
(0000154E 5 5		UnVar5)
(00001550 96 6 231 20 0 0		bmp-button)
;;;def dialog-update-from-res 5462
(00001556 20 6 4 4 0)
(0000155B 5 3		UnVar3)
(0000155D 8 4		UnVar4)
(0000155F 100 5		UNVar5)
(00001561 15 23 0		JMP 0000157B)
(00001564 5 4		UnVar4)
(00001566 40		car)
(00001567 8 5		UnVar5)
(00001569 5 4		UnVar4)
(0000156B 41		cdr)
(0000156C 8 4		UnVar4)
(0000156E 5 5		UnVar5)
(00001570 40		car)
(00001571 5 5		UnVar5)
(00001573 41		cdr)
(00001574 81 2 13 1 1 0		dialog-item.wid<-)
(0000157A 10)
(0000157B 5 4		UnVar4)
(0000157D 60 228 255		T->JMP 00001564)
(00001580 5 0		UnVar0)
(00001582 5 1		UnVar1)
(00001584 5 2		UnVar2)
(00001586 81 3 12 1 1 0		dialog.update-from-res)
(0000158C 10)
(0000158D 5 0		UnVar0)
(0000158F 22		ret)
;;;def _frame-margins 5520
(00001590 20 1 0 0 0)
(00001595 100 0		UNVar0)
(00001597 95 0 220 21 0 0		_default-inc)
(0000159D 8 0		UnVar0)
(0000159F 5 0		UnVar0)
(000015A1 5 0		UnVar0)
(000015A3 42		cons)
(000015A4 22		ret)
;;;def _screen-margins 5541
(000015A5 20 0 0 0 0)
(000015AA 95 0 220 21 0 0		_default-inc)
(000015B0 95 0 139 5 0 0		_W-DIALOG-XMIN)
(000015B6 95 0 153 5 0 0		_W-DIALOG-YMIN)
(000015BC 81 2 54 1 1 0		make-ipoint)
(000015C2 42		cons)
(000015C3 22		ret)
;;;def _small-inc 5572
(000015C4 20 0 0 0 0)
(000015C9 95 0 232 4 0 0		_W-BORDER)
(000015CF 95 0 246 4 0 0		_W-BORDER-SIZE)
(000015D5 81 2 54 1 1 0		make-ipoint)
(000015DB 22		ret)
;;;def _default-inc 5596
(000015DC 20 0 0 0 0)
(000015E1 95 0 232 4 0 0		_W-BORDER)
(000015E7 95 0 53 5 0 0		_W-CAPTION_WIDTH)
(000015ED 81 2 54 1 1 0		make-ipoint)
(000015F3 22		ret)
;;;def dcascade 5620
(000015F4 20 9 0 0 1)
(000015F9 5 0		UnVar0)
(000015FB 8 1		UnVar1)
(000015FD 5 1		UnVar1)
(000015FF 9 11 1		':FRAME-MARGINS)
(00001602 9 7 2		'(5520 _frame-margins))
(00001605 81 3 74 1 1 0		getf)
(0000160B 8 2		UnVar2)
(0000160D 5 1		UnVar1)
(0000160F 9 10 1		':HOR-RATIO)
(00001612 50 0		0)
(00001614 81 3 74 1 1 0		getf)
(0000161A 8 3		UnVar3)
(0000161C 5 1		UnVar1)
(0000161E 9 9 1		':VER-RATIO)
(00001621 50 0		0)
(00001623 81 3 74 1 1 0		getf)
(00001629 8 4		UnVar4)
(0000162B 5 1		UnVar1)
(0000162D 9 8 1		':SCREEN-MARGINS)
(00001630 9 6 2		'(5541 _screen-margins))
(00001633 81 3 74 1 1 0		getf)
(00001639 8 5		UnVar5)
(0000163B 5 1		UnVar1)
(0000163D 9 7 1		':INC)
(00001640 9 5 2		'(5596 _default-inc))
(00001643 81 3 74 1 1 0		getf)
(00001649 8 6		UnVar6)
(0000164B 5 1		UnVar1)
(0000164D 9 6 1		':LIMIT)
(00001650 50 12		12)
(00001652 81 3 74 1 1 0		getf)
(00001658 8 7		UnVar7)
(0000165A 5 1		UnVar1)
(0000165C 9 5 1		':CHECK-DIALOG-SIZE?)
(0000165F 1		nil)
(00001660 81 3 74 1 1 0		getf)
(00001666 8 8		UnVar8)
(00001668 5 2		UnVar2)
(0000166A 5 3		UnVar3)
(0000166C 5 4		UnVar4)
(0000166E 5 5		UnVar5)
(00001670 5 6		UnVar6)
(00001672 5 7		UnVar7)
(00001674 5 8		UnVar8)
(00001676 1		nil)
(00001677 1		nil)
(00001678 1		nil)
(00001679 81 10 4 1 1 0		vector)
(0000167F 22		ret)
;;;def dcascade.frame-margins 5760
(00001680 20 1 1 1 0)
(00001685 5 0		UnVar0)
(00001687 50 0		0)
(00001689 81 2 3 1 1 0		aref)
(0000168F 22		ret)
;;;def dcascade.hor-ratio 5776
(00001690 20 1 1 1 0)
(00001695 5 0		UnVar0)
(00001697 50 1		1)
(00001699 81 2 3 1 1 0		aref)
(0000169F 22		ret)
;;;def dcascade.ver-ratio 5792
(000016A0 20 1 1 1 0)
(000016A5 5 0		UnVar0)
(000016A7 50 2		2)
(000016A9 81 2 3 1 1 0		aref)
(000016AF 22		ret)
;;;def dcascade.screen-margins 5808
(000016B0 20 1 1 1 0)
(000016B5 5 0		UnVar0)
(000016B7 50 3		3)
(000016B9 81 2 3 1 1 0		aref)
(000016BF 22		ret)
;;;def dcascade.inc 5824
(000016C0 20 1 1 1 0)
(000016C5 5 0		UnVar0)
(000016C7 50 4		4)
(000016C9 81 2 3 1 1 0		aref)
(000016CF 22		ret)
;;;def dcascade.limit 5840
(000016D0 20 1 1 1 0)
(000016D5 5 0		UnVar0)
(000016D7 50 5		5)
(000016D9 81 2 3 1 1 0		aref)
(000016DF 22		ret)
;;;def dcascade.check-dialog-size-p 5856
(000016E0 20 1 1 1 0)
(000016E5 5 0		UnVar0)
(000016E7 50 6		6)
(000016E9 81 2 3 1 1 0		aref)
(000016EF 22		ret)
;;;def dcascade.init-apex 5872
(000016F0 20 1 1 1 0)
(000016F5 5 0		UnVar0)
(000016F7 50 7		7)
(000016F9 81 2 3 1 1 0		aref)
(000016FF 22		ret)
;;;def dcascade.init-apex<- 5888
(00001700 20 2 2 2 0)
(00001705 5 0		UnVar0)
(00001707 5 1		UnVar1)
(00001709 50 7		7)
(0000170B 81 3 2 1 1 0		aref<-)
(00001711 22		ret)
;;;def dcascade.winframe 5906
(00001712 20 1 1 1 0)
(00001717 5 0		UnVar0)
(00001719 50 8		8)
(0000171B 81 2 3 1 1 0		aref)
(00001721 22		ret)
;;;def dcascade.winframe<- 5922
(00001722 20 2 2 2 0)
(00001727 5 0		UnVar0)
(00001729 5 1		UnVar1)
(0000172B 50 8		8)
(0000172D 81 3 2 1 1 0		aref<-)
(00001733 22		ret)
;;;def dcascade.apex 5940
(00001734 20 1 1 1 0)
(00001739 5 0		UnVar0)
(0000173B 50 9		9)
(0000173D 81 2 3 1 1 0		aref)
(00001743 22		ret)
;;;def dcascade.apex<- 5956
(00001744 20 2 2 2 0)
(00001749 5 0		UnVar0)
(0000174B 5 1		UnVar1)
(0000174D 50 9		9)
(0000174F 81 3 2 1 1 0		aref<-)
(00001755 22		ret)
;;;def dcascade-apex 5974
(00001756 20 2 1 1 0)
(0000175B 5 0		UnVar0)
(0000175D 8 1		UnVar1)
(0000175F 5 1		UnVar1)
(00001761 50 8		8)
(00001763 81 2 3 1 1 0		aref)
(00001769 81 0 1 1 1 0		_mdiclient.apex-and-size)
(0000176F 81 2 0 1 1 0		equal)
(00001775 13 15 0		nil->JMP 00001787)
(00001778 5 0		UnVar0)
(0000177A 8 1		UnVar1)
(0000177C 5 1		UnVar1)
(0000177E 50 9		9)
(00001780 81 2 3 1 1 0		aref)
(00001786 22		ret)
(00001787 5 0		UnVar0)
(00001789 96 1 143 23 0 0		dcascade.init)
;;;def dcascade.init 6031
(0000178F 20 26 1 2 0)
(00001794 5 1		UnVar1)
(00001796 13 3 0		nil->JMP 0000179C)
(00001799 15 8 0		JMP 000017A4)
(0000179C 81 0 1 1 1 0		_mdiclient.apex-and-size)
(000017A2 8 1		UnVar1)
(000017A4 5 0		UnVar0)
(000017A6 95 1 128 22 0 0		dcascade.frame-margins)
(000017AC 52 0 1		)
(000017AF 8 2		UnVar2)
(000017B1 5 0		UnVar0)
(000017B3 95 1 176 22 0 0		dcascade.screen-margins)
(000017B9 52 0 1		)
(000017BC 8 3		UnVar3)
(000017BE 5 0		UnVar0)
(000017C0 95 1 144 22 0 0		dcascade.hor-ratio)
(000017C6 8 4		UnVar4)
(000017C8 5 0		UnVar0)
(000017CA 95 1 160 22 0 0		dcascade.ver-ratio)
(000017D0 8 5		UnVar5)
(000017D2 5 0		UnVar0)
(000017D4 95 1 192 22 0 0		dcascade.inc)
(000017DA 52 0 1		)
(000017DD 8 6		UnVar6)
(000017DF 81 0 255 0 1 0		_screen-size)
(000017E5 8 7		UnVar7)
(000017E7 5 0		UnVar0)
(000017E9 8 8		UnVar8)
(000017EB 5 1		UnVar1)
(000017ED 8 9		UnVar9)
(000017EF 5 8		UnVar8)
(000017F1 5 9		UnVar9)
(000017F3 50 8		8)
(000017F5 81 3 2 1 1 0		aref<-)
(000017FB 10)
(000017FC 5 1		UnVar1)
(000017FE 40		car)
(000017FF 37 3		symbolp)
(00001801 13 7 0		nil->JMP 0000180B)
(00001804 50 0		0)
(00001806 5 7		UnVar7)
(00001808 42		cons)
(00001809 8 1		UnVar1)
(0000180B 5 2		UnVar2)
(0000180D 40		car)
(0000180E 81 1 58 1 1 0		ipoint-h)
(00001814 8 8		UnVar8)
(00001816 5 2		UnVar2)
(00001818 40		car)
(00001819 81 1 57 1 1 0		ipoint-v)
(0000181F 8 9		UnVar9)
(00001821 5 2		UnVar2)
(00001823 41		cdr)
(00001824 81 1 58 1 1 0		ipoint-h)
(0000182A 8 10		UnVar10)
(0000182C 5 2		UnVar2)
(0000182E 41		cdr)
(0000182F 81 1 57 1 1 0		ipoint-v)
(00001835 8 11		UnVar11)
(00001837 5 3		UnVar3)
(00001839 40		car)
(0000183A 81 1 58 1 1 0		ipoint-h)
(00001840 8 12		UnVar12)
(00001842 5 3		UnVar3)
(00001844 40		car)
(00001845 81 1 57 1 1 0		ipoint-v)
(0000184B 8 13		UnVar13)
(0000184D 5 3		UnVar3)
(0000184F 41		cdr)
(00001850 81 1 58 1 1 0		ipoint-h)
(00001856 8 14		UnVar14)
(00001858 5 3		UnVar3)
(0000185A 41		cdr)
(0000185B 81 1 57 1 1 0		ipoint-v)
(00001861 8 15		UnVar15)
(00001863 5 1		UnVar1)
(00001865 40		car)
(00001866 81 1 58 1 1 0		ipoint-h)
(0000186C 8 16		UnVar16)
(0000186E 5 1		UnVar1)
(00001870 40		car)
(00001871 81 1 57 1 1 0		ipoint-v)
(00001877 8 17		UnVar17)
(00001879 5 7		UnVar7)
(0000187B 81 1 58 1 1 0		ipoint-h)
(00001881 8 18		UnVar18)
(00001883 5 7		UnVar7)
(00001885 81 1 57 1 1 0		ipoint-v)
(0000188B 8 19		UnVar19)
(0000188D 100 20		UNVar20)
(0000188F 100 21		UNVar21)
(00001891 100 22		UNVar22)
(00001893 100 23		UNVar23)
(00001895 5 16		UnVar16)
(00001897 5 1		UnVar1)
(00001899 41		cdr)
(0000189A 81 1 58 1 1 0		ipoint-h)
(000018A0 70		+)
(000018A1 8 20		UnVar20)
(000018A3 5 17		UnVar17)
(000018A5 5 1		UnVar1)
(000018A7 41		cdr)
(000018A8 81 1 57 1 1 0		ipoint-v)
(000018AE 70		+)
(000018AF 8 21		UnVar21)
(000018B1 5 16		UnVar16)
(000018B3 5 20		UnVar20)
(000018B5 5 16		UnVar16)
(000018B7 81 2 151 1 1 0		-)
(000018BD 5 4		UnVar4)
(000018BF 81 2 152 1 1 0		*)
(000018C5 81 1 254 0 1 0		FIX)
(000018CB 70		+)
(000018CC 8 22		UnVar22)
(000018CE 5 22		UnVar22)
(000018D0 5 16		UnVar16)
(000018D2 5 8		UnVar8)
(000018D4 70		+)
(000018D5 76		<)
(000018D6 13 7 0		nil->JMP 000018E0)
(000018D9 5 16		UnVar16)
(000018DB 5 8		UnVar8)
(000018DD 70		+)
(000018DE 8 22		UnVar22)
(000018E0 5 22		UnVar22)
(000018E2 5 20		UnVar20)
(000018E4 5 10		UnVar10)
(000018E6 71		-)
(000018E7 75		>)
(000018E8 13 7 0		nil->JMP 000018F2)
(000018EB 5 20		UnVar20)
(000018ED 5 10		UnVar10)
(000018EF 71		-)
(000018F0 8 22		UnVar22)
(000018F2 5 17		UnVar17)
(000018F4 5 21		UnVar21)
(000018F6 5 17		UnVar17)
(000018F8 81 2 151 1 1 0		-)
(000018FE 5 5		UnVar5)
(00001900 81 2 152 1 1 0		*)
(00001906 81 1 254 0 1 0		FIX)
(0000190C 70		+)
(0000190D 8 23		UnVar23)
(0000190F 5 23		UnVar23)
(00001911 5 17		UnVar17)
(00001913 5 9		UnVar9)
(00001915 70		+)
(00001916 76		<)
(00001917 13 7 0		nil->JMP 00001921)
(0000191A 5 17		UnVar17)
(0000191C 5 9		UnVar9)
(0000191E 70		+)
(0000191F 8 23		UnVar23)
(00001921 5 23		UnVar23)
(00001923 5 21		UnVar21)
(00001925 5 11		UnVar11)
(00001927 71		-)
(00001928 75		>)
(00001929 13 7 0		nil->JMP 00001933)
(0000192C 5 20		UnVar20)
(0000192E 5 11		UnVar11)
(00001930 71		-)
(00001931 8 23		UnVar23)
(00001933 5 6		UnVar6)
(00001935 13 36 0		nil->JMP 0000195C)
(00001938 5 14		UnVar14)
(0000193A 5 6		UnVar6)
(0000193C 81 1 58 1 1 0		ipoint-h)
(00001942 81 2 154 1 1 0		+)
(00001948 8 14		UnVar14)
(0000194A 5 15		UnVar15)
(0000194C 5 6		UnVar6)
(0000194E 81 1 57 1 1 0		ipoint-v)
(00001954 81 2 154 1 1 0		+)
(0000195A 8 15		UnVar15)
(0000195C 5 22		UnVar22)
(0000195E 5 12		UnVar12)
(00001960 76		<)
(00001961 13 4 0		nil->JMP 00001968)
(00001964 5 12		UnVar12)
(00001966 8 22		UnVar22)
(00001968 5 22		UnVar22)
(0000196A 5 18		UnVar18)
(0000196C 5 14		UnVar14)
(0000196E 71		-)
(0000196F 75		>)
(00001970 13 7 0		nil->JMP 0000197A)
(00001973 5 18		UnVar18)
(00001975 5 14		UnVar14)
(00001977 71		-)
(00001978 8 22		UnVar22)
(0000197A 5 23		UnVar23)
(0000197C 5 13		UnVar13)
(0000197E 76		<)
(0000197F 13 4 0		nil->JMP 00001986)
(00001982 5 13		UnVar13)
(00001984 8 23		UnVar23)
(00001986 5 23		UnVar23)
(00001988 5 19		UnVar19)
(0000198A 5 15		UnVar15)
(0000198C 71		-)
(0000198D 75		>)
(0000198E 13 7 0		nil->JMP 00001998)
(00001991 5 19		UnVar19)
(00001993 5 15		UnVar15)
(00001995 71		-)
(00001996 8 23		UnVar23)
(00001998 5 0		UnVar0)
(0000199A 8 24		UnVar24)
(0000199C 5 22		UnVar22)
(0000199E 5 23		UnVar23)
(000019A0 81 2 54 1 1 0		make-ipoint)
(000019A6 8 25		UnVar25)
(000019A8 5 24		UnVar24)
(000019AA 5 25		UnVar25)
(000019AC 50 7		7)
(000019AE 81 3 2 1 1 0		aref<-)
(000019B4 10)
(000019B5 5 0		UnVar0)
(000019B7 8 24		UnVar24)
(000019B9 5 22		UnVar22)
(000019BB 5 23		UnVar23)
(000019BD 81 2 54 1 1 0		make-ipoint)
(000019C3 8 25		UnVar25)
(000019C5 5 24		UnVar24)
(000019C7 5 25		UnVar25)
(000019C9 50 9		9)
(000019CB 81 3 2 1 1 0		aref<-)
(000019D1 22		ret)
;;;def dcascade.next-apex 6610
(000019D2 20 8 1 1 0)
(000019D7 100 1		UNVar1)
(000019D9 100 2		UNVar2)
(000019DB 100 3		UNVar3)
(000019DD 100 4		UNVar4)
(000019DF 100 5		UNVar5)
(000019E1 100 6		UNVar6)
(000019E3 5 0		UnVar0)
(000019E5 95 1 192 22 0 0		dcascade.inc)
(000019EB 9 253 0		"VLisp internal: Cascade has not increment!")
(000019EE 53 2 66 1 1 32		assert)
(000019F4 10)
(000019F5 5 0		UnVar0)
(000019F7 95 1 192 22 0 0		dcascade.inc)
(000019FD 52 0 1		)
(00001A00 8 6		UnVar6)
(00001A02 81 0 1 1 1 0		_mdiclient.apex-and-size)
(00001A08 8 1		UnVar1)
(00001A0A 5 1		UnVar1)
(00001A0C 40		car)
(00001A0D 37 3		symbolp)
(00001A0F 14 22 0		T->JMP 00001A28)
(00001A12 5 0		UnVar0)
(00001A14 8 7		UnVar7)
(00001A16 5 7		UnVar7)
(00001A18 50 8		8)
(00001A1A 81 2 3 1 1 0		aref)
(00001A20 5 1		UnVar1)
(00001A22 81 2 0 1 1 0		equal)
(00001A28 13 12 1		nil->JMP 00001B37)
(00001A2B 5 0		UnVar0)
(00001A2D 8 7		UnVar7)
(00001A2F 5 7		UnVar7)
(00001A31 50 9		9)
(00001A33 81 2 3 1 1 0		aref)
(00001A39 5 6		UnVar6)
(00001A3B 81 2 59 1 1 0		add-ipoints)
(00001A41 8 5		UnVar5)
(00001A43 5 0		UnVar0)
(00001A45 8 7		UnVar7)
(00001A47 5 7		UnVar7)
(00001A49 50 7		7)
(00001A4B 81 2 3 1 1 0		aref)
(00001A51 81 1 58 1 1 0		ipoint-h)
(00001A57 5 0		UnVar0)
(00001A59 95 1 208 22 0 0		dcascade.limit)
(00001A5F 5 6		UnVar6)
(00001A61 81 1 58 1 1 0		ipoint-h)
(00001A67 81 2 152 1 1 0		*)
(00001A6D 81 2 154 1 1 0		+)
(00001A73 8 4		UnVar4)
(00001A75 5 0		UnVar0)
(00001A77 8 7		UnVar7)
(00001A79 5 7		UnVar7)
(00001A7B 50 7		7)
(00001A7D 81 2 3 1 1 0		aref)
(00001A83 81 1 57 1 1 0		ipoint-v)
(00001A89 5 0		UnVar0)
(00001A8B 95 1 208 22 0 0		dcascade.limit)
(00001A91 5 6		UnVar6)
(00001A93 81 1 57 1 1 0		ipoint-v)
(00001A99 81 2 152 1 1 0		*)
(00001A9F 81 2 154 1 1 0		+)
(00001AA5 8 3		UnVar3)
(00001AA7 81 0 255 0 1 0		_screen-size)
(00001AAD 5 0		UnVar0)
(00001AAF 95 1 176 22 0 0		dcascade.screen-margins)
(00001AB5 52 0 1		)
(00001AB8 41		cdr)
(00001AB9 81 2 252 0 1 0		subtract-ipoints)
(00001ABF 8 2		UnVar2)
(00001AC1 5 5		UnVar5)
(00001AC3 81 1 58 1 1 0		ipoint-h)
(00001AC9 5 4		UnVar4)
(00001ACB 76		<)
(00001ACC 61 51 0		nil->JMP 00001B02)
(00001ACF 5 5		UnVar5)
(00001AD1 81 1 57 1 1 0		ipoint-v)
(00001AD7 5 3		UnVar3)
(00001AD9 76		<)
(00001ADA 61 37 0		nil->JMP 00001B02)
(00001ADD 5 5		UnVar5)
(00001ADF 81 1 58 1 1 0		ipoint-h)
(00001AE5 5 2		UnVar2)
(00001AE7 81 1 58 1 1 0		ipoint-h)
(00001AED 76		<)
(00001AEE 61 17 0		nil->JMP 00001B02)
(00001AF1 5 5		UnVar5)
(00001AF3 81 1 57 1 1 0		ipoint-v)
(00001AF9 5 2		UnVar2)
(00001AFB 81 1 57 1 1 0		ipoint-v)
(00001B01 76		<)
(00001B02 14 29 0		T->JMP 00001B22)
(00001B05 5 0		UnVar0)
(00001B07 8 7		UnVar7)
(00001B09 5 7		UnVar7)
(00001B0B 50 9		9)
(00001B0D 81 2 3 1 1 0		aref)
(00001B13 5 0		UnVar0)
(00001B15 8 7		UnVar7)
(00001B17 5 7		UnVar7)
(00001B19 50 7		7)
(00001B1B 81 2 3 1 1 0		aref)
(00001B21 38		=)
(00001B22 13 3 0		nil->JMP 00001B28)
(00001B25 5 5		UnVar5)
(00001B27 22		ret)
(00001B28 5 0		UnVar0)
(00001B2A 8 7		UnVar7)
(00001B2C 5 7		UnVar7)
(00001B2E 50 7		7)
(00001B30 81 2 3 1 1 0		aref)
(00001B36 22		ret)
(00001B37 5 0		UnVar0)
(00001B39 5 1		UnVar1)
(00001B3B 96 2 143 23 0 0		dcascade.init)
;;;def dcascade.next 6977
(00001B41 20 7 2 2 0)
(00001B46 81 0 255 0 1 0		_screen-size)
(00001B4C 8 2		UnVar2)
(00001B4E 5 0		UnVar0)
(00001B50 95 1 210 25 0 0		dcascade.next-apex)
(00001B56 8 3		UnVar3)
(00001B58 5 0		UnVar0)
(00001B5A 95 1 224 22 0 0		dcascade.check-dialog-size-p)
(00001B60 13 81 0		nil->JMP 00001BB4)
(00001B63 5 1		UnVar1)
(00001B65 81 1 251 0 1 0		dialog._apex-and-size)
(00001B6B 41		cdr)
(00001B6C 8 4		UnVar4)
(00001B6E 5 3		UnVar3)
(00001B70 5 4		UnVar4)
(00001B72 81 2 59 1 1 0		add-ipoints)
(00001B78 8 5		UnVar5)
(00001B7A 5 5		UnVar5)
(00001B7C 81 1 58 1 1 0		ipoint-h)
(00001B82 5 2		UnVar2)
(00001B84 81 1 58 1 1 0		ipoint-h)
(00001B8A 77		>=)
(00001B8B 14 17 0		T->JMP 00001B9F)
(00001B8E 5 5		UnVar5)
(00001B90 81 1 57 1 1 0		ipoint-v)
(00001B96 5 2		UnVar2)
(00001B98 81 1 57 1 1 0		ipoint-v)
(00001B9E 77		>=)
(00001B9F 13 15 0		nil->JMP 00001BB1)
(00001BA2 5 0		UnVar0)
(00001BA4 8 6		UnVar6)
(00001BA6 5 6		UnVar6)
(00001BA8 50 7		7)
(00001BAA 81 2 3 1 1 0		aref)
(00001BB0 22		ret)
(00001BB1 5 3		UnVar3)
(00001BB3 22		ret)
(00001BB4 5 3		UnVar3)
(00001BB6 22		ret)
;;;def dialog.apex-by-cascade 7095
(00001BB7 20 6 2 2 0)
(00001BBC 100 2		UNVar2)
(00001BBE 5 0		UnVar0)
(00001BC0 8 3		UnVar3)
(00001BC2 5 1		UnVar1)
(00001BC4 5 0		UnVar0)
(00001BC6 95 2 65 27 0 0		dcascade.next)
(00001BCC 8 2		UnVar2)
(00001BCE 5 2		UnVar2)
(00001BD0 5 3		UnVar3)
(00001BD2 45 1		IDFun1)
(00001BD4 10)
(00001BD5 5 1		UnVar1)
(00001BD7 8 4		UnVar4)
(00001BD9 5 2		UnVar2)
(00001BDB 8 5		UnVar5)
(00001BDD 5 4		UnVar4)
(00001BDF 5 5		UnVar5)
(00001BE1 50 9		9)
(00001BE3 81 3 2 1 1 0		aref<-)
(00001BE9 22		ret)
;;;def list-true-dialogs-with-host-spouse 7146
(00001BEA 20 0 0 0 0)
(00001BEF 15 30 0		JMP 00001C10)
(00001BF2 20 1 1 1 0)
(00001BF7 5 0		UnVar0)
(00001BF9 81 1 81 1 1 0		dialog._border-style)
(00001BFF 50 64		64)
(00001C01 81 2 167 1 1 0		logand)
(00001C07 50 0		0)
(00001C09 81 2 85 1 1 0		/=&)
(00001C0F 22		ret)
(00001C10 9 4 2		'(7154 nil))
(00001C13 81 0 250 0 1 0		list-dialogs-with-host-spouse)
(00001C19 81 2 249 0 1 0		remove-if)
(00001C1F 22		ret)
;;;def close-modal-dialogs 7200
(00001C20 20 2 0 0 0)
(00001C25 81 0 250 0 1 0		list-dialogs-with-host-spouse)
(00001C2B 8 0		UnVar0)
(00001C2D 100 1		UNVar1)
(00001C2F 15 30 0		JMP 00001C50)
(00001C32 5 0		UnVar0)
(00001C34 40		car)
(00001C35 8 1		UnVar1)
(00001C37 5 0		UnVar0)
(00001C39 41		cdr)
(00001C3A 8 0		UnVar0)
(00001C3C 5 1		UnVar1)
(00001C3E 81 1 248 0 1 0		dialog.modalp)
(00001C44 13 9 0		nil->JMP 00001C50)
(00001C47 5 1		UnVar1)
(00001C49 95 1 197 0 0 0		destroy-host-spouse)
(00001C4F 10)
(00001C50 5 0		UnVar0)
(00001C52 60 221 255		T->JMP 00001C32)
(00001C55 1		nil)
(00001C56 22		ret)
;;;def _kill-dialogs 7255
(00001C57 20 7 1 2 0)
(00001C5C 95 0 234 27 0 0		list-true-dialogs-with-host-spouse)
(00001C62 8 2		UnVar2)
(00001C64 100 3		UNVar3)
(00001C66 15 112 0		JMP 00001CD9)
(00001C69 5 2		UnVar2)
(00001C6B 40		car)
(00001C6C 8 3		UnVar3)
(00001C6E 5 2		UnVar2)
(00001C70 41		cdr)
(00001C71 8 2		UnVar2)
(00001C73 5 0		UnVar0)
(00001C75 5 3		UnVar3)
(00001C77 9 53 1		'l-context)
(00001C7A 81 2 60 1 1 0		slot-value)
(00001C80 53 1 247 0 1 32		object-id)
(00001C86 38		=)
(00001C87 61 67 0		nil->JMP 00001CCD)
(00001C8A 5 3		UnVar3)
(00001C8C 81 1 246 0 1 0		type-of)
(00001C92 53 1 245 0 1 32		circle-list)
(00001C98 8 4		UnVar4)
(00001C9A 5 1		UnVar1)
(00001C9C 8 5		UnVar5)
(00001C9E 100 6		UNVar6)
(00001CA0 15 10 0		JMP 00001CAD)
(00001CA3 5 4		UnVar4)
(00001CA5 41		cdr)
(00001CA6 8 4		UnVar4)
(00001CA8 5 5		UnVar5)
(00001CAA 41		cdr)
(00001CAB 8 5		UnVar5)
(00001CAD 5 4		UnVar4)
(00001CAF 61 21 0		nil->JMP 00001CC7)
(00001CB2 5 5		UnVar5)
(00001CB4 61 16 0		nil->JMP 00001CC7)
(00001CB7 5 4		UnVar4)
(00001CB9 40		car)
(00001CBA 5 5		UnVar5)
(00001CBC 40		car)
(00001CBD 53 2 244 0 1 32		subtypep)
(00001CC3 11)
(00001CC4 8 6		UnVar6)
(00001CC6 35		not)
(00001CC7 60 217 255		T->JMP 00001CA3)
(00001CCA 5 6		UnVar6)
(00001CCC 35		not)
(00001CCD 13 9 0		nil->JMP 00001CD9)
(00001CD0 5 3		UnVar3)
(00001CD2 95 1 197 0 0 0		destroy-host-spouse)
(00001CD8 10)
(00001CD9 5 2		UnVar2)
(00001CDB 60 139 255		T->JMP 00001C69)
(00001CDE 1		nil)
(00001CDF 22		ret)
;;;def nil 7392
(00001CE0 20 0 0 0 0)
(00001CE5 3 144 1		_%sys-error-hook%)
(00001CE8 3 243 0		_%sys-break-hook%)
(00001CEB 3 137 1		*xsubr-trace-hook*)
(00001CEE 3 136 1		_%kbd-break-hook%)
(00001CF1 3 242 0		_%ubrk-allowed%)
(00001CF4 57 5 0		list)
(00001CF7 22		ret)
;;;def _restore-env 7416
(00001CF8 20 5 5 5 0)
(00001CFD 5 0		UnVar0)
(00001CFF 6 144 1		_%sys-error-hook%)
(00001D02 5 1		UnVar1)
(00001D04 6 243 0		_%sys-break-hook%)
(00001D07 5 2		UnVar2)
(00001D09 6 137 1		*xsubr-trace-hook*)
(00001D0C 5 3		UnVar3)
(00001D0E 6 136 1		_%kbd-break-hook%)
(00001D11 5 4		UnVar4)
(00001D13 11)
(00001D14 6 242 0		_%ubrk-allowed%)
(00001D17 22		ret)
;;;def modal-dialog!! 7448
(00001D18 21 6 1 3 0)
(00001D1D 100 3		UNVar3)
(00001D1F 100 4		UNVar4)
(00001D21 100 5		UNVar5)
(00001D23 5 2		UnVar2)
(00001D25 13 3 0		nil->JMP 00001D2B)
(00001D28 15 9 0		JMP 00001D34)
(00001D2B 5 0		UnVar0)
(00001D2D 95 1 16 14 0 0		sync-up)
(00001D33 10)
(00001D34 5 0		UnVar0)
(00001D36 9 241 0		'apex)
(00001D39 81 2 60 1 1 0		slot-value)
(00001D3F 13 3 0		nil->JMP 00001D45)
(00001D42 15 26 0		JMP 00001D5F)
(00001D45 5 0		UnVar0)
(00001D47 5 1		UnVar1)
(00001D49 14 9 0		T->JMP 00001D55)
(00001D4C 3 240 0		*modals-cascade*)
(00001D4F 95 1 86 23 0 0		dcascade-apex)
(00001D55 9 241 0		'apex)
(00001D58 81 3 239 0 1 0		slot-value<-)
(00001D5E 10)
(00001D5F 95 0 224 28 0 0		func 00001CE0)
(00001D65 8 4		UnVar4)
(00001D67 9 238 0		'_%curr-rep-cntx%)
(00001D6A 5 0		UnVar0)
(00001D6C 9 53 1		'l-context)
(00001D6F 81 2 60 1 1 0		slot-value)
(00001D75 14 3 0		T->JMP 00001D7B)
(00001D78 3 238 0		_%curr-rep-cntx%)
(00001D7B 9 144 1		'_%sys-error-hook%)
(00001D7E 15 33 0		JMP 00001DA2)
(00001D81 20 1 1 1 0)
(00001D86 95 0 32 28 0 0		close-modal-dialogs)
(00001D8C 10)
(00001D8D 4 1 4		UpVar1-4)
(00001D90 40		car)
(00001D91 63		nil->ret)
(00001D92 9 3 2		'(7416 _restore-env))
(00001D95 4 1 4		UpVar1-4)
(00001D98 83		apply)
(00001D99 10)
(00001D9A 5 0		UnVar0)
(00001D9C 4 1 4		UpVar1-4)
(00001D9F 40		car)
(00001DA0 46 1		invoke+ret)
(00001DA2 12 2 2		'(7553 nil))
(00001DA5 9 243 0		'_%sys-break-hook%)
(00001DA8 15 34 0		JMP 00001DCD)
(00001DAB 20 1 0 0 1)
(00001DB0 95 0 32 28 0 0		close-modal-dialogs)
(00001DB6 10)
(00001DB7 9 3 2		'(7416 _restore-env))
(00001DBA 4 1 4		UpVar1-4)
(00001DBD 83		apply)
(00001DBE 10)
(00001DBF 4 1 4		UpVar1-4)
(00001DC2 41		cdr)
(00001DC3 40		car)
(00001DC4 63		nil->ret)
(00001DC5 4 1 4		UpVar1-4)
(00001DC8 41		cdr)
(00001DC9 40		car)
(00001DCA 5 0		UnVar0)
(00001DCC 84		apply+ret)
(00001DCD 12 1 2		'(7595 nil))
(00001DD0 9 137 1		'*xsubr-trace-hook*)
(00001DD3 1		nil)
(00001DD4 9 242 0		'_%ubrk-allowed%)
(00001DD7 2		T)
(00001DD8 9 136 1		'_%kbd-break-hook%)
(00001DDB 15 26 0		JMP 00001DF8)
(00001DDE 20 1 0 0 1)
(00001DE3 9 194 1		"VLMSG.DLL")
(00001DE6 51 190 95 0 0		24510)
(00001DEB 81 2 193 1 1 0		string-resource)
(00001DF1 81 1 110 1 1 0		_msg-err)
(00001DF7 22		ret)
(00001DF8 9 0 2		'(7646 nil))
(00001DFB 24 12 0)
(00001DFE 5 0		UnVar0)
(00001E00 2		T)
(00001E01 95 2 2 0 0 0		create-host-spouse)
(00001E07 10)
(00001E08 1		nil)
(00001E09 57 1 0		list)
(00001E0C 8 3		UnVar3)
(00001E0E 15 16 0		JMP 00001E21)
(00001E11 5 3		UnVar3)
(00001E13 81 1 237 0 1 0		get-command)
(00001E19 81 1 236 0 1 0		execute-command)
(00001E1F 8 5		UnVar5)
(00001E21 5 0		UnVar0)
(00001E23 95 1 250 0 0 0		host-spouse-exists-p)
(00001E29 60 229 255		T->JMP 00001E11)
(00001E2C 25 6 0)
(00001E2F 5 5		UnVar5)
(00001E31 22		ret)
;;;def modal-dialog-sheet!! 7730
(00001E32 21 17 1 1 1)
(00001E37 5 1		UnVar1)
(00001E39 8 2		UnVar2)
(00001E3B 5 2		UnVar2)
(00001E3D 9 235 0		':APEX)
(00001E40 1		nil)
(00001E41 81 3 74 1 1 0		getf)
(00001E47 8 3		UnVar3)
(00001E49 5 2		UnVar2)
(00001E4B 9 234 0		':CAPTION)
(00001E4E 1		nil)
(00001E4F 81 3 74 1 1 0		getf)
(00001E55 8 4		UnVar4)
(00001E57 5 2		UnVar2)
(00001E59 9 233 0		':no-sync?)
(00001E5C 1		nil)
(00001E5D 81 3 74 1 1 0		getf)
(00001E63 8 5		UnVar5)
(00001E65 5 2		UnVar2)
(00001E67 9 232 0		':OK)
(00001E6A 1		nil)
(00001E6B 81 3 74 1 1 0		getf)
(00001E71 8 6		UnVar6)
(00001E73 5 2		UnVar2)
(00001E75 9 231 0		':apply-fn)
(00001E78 1		nil)
(00001E79 81 3 74 1 1 0		getf)
(00001E7F 8 7		UnVar7)
(00001E81 100 8		UNVar8)
(00001E83 100 9		UNVar9)
(00001E85 100 10		UNVar10)
(00001E87 5 5		UnVar5)
(00001E89 13 3 0		nil->JMP 00001E8F)
(00001E8C 15 27 0		JMP 00001EAA)
(00001E8F 5 0		UnVar0)
(00001E91 8 11		UnVar11)
(00001E93 15 15 0		JMP 00001EA5)
(00001E96 5 11		UnVar11)
(00001E98 40		car)
(00001E99 95 1 16 14 0 0		sync-up)
(00001E9F 10)
(00001EA0 5 11		UnVar11)
(00001EA2 41		cdr)
(00001EA3 8 11		UnVar11)
(00001EA5 5 11		UnVar11)
(00001EA7 60 236 255		T->JMP 00001E96)
(00001EAA 5 3		UnVar3)
(00001EAC 14 9 0		T->JMP 00001EB8)
(00001EAF 3 240 0		*modals-cascade*)
(00001EB2 95 1 86 23 0 0		dcascade-apex)
(00001EB8 8 3		UnVar3)
(00001EBA 95 0 224 28 0 0		func 00001CE0)
(00001EC0 8 9		UnVar9)
(00001EC2 9 238 0		'_%curr-rep-cntx%)
(00001EC5 5 0		UnVar0)
(00001EC7 40		car)
(00001EC8 9 53 1		'l-context)
(00001ECB 81 2 60 1 1 0		slot-value)
(00001ED1 14 3 0		T->JMP 00001ED7)
(00001ED4 3 238 0		_%curr-rep-cntx%)
(00001ED7 9 137 1		'*xsubr-trace-hook*)
(00001EDA 1		nil)
(00001EDB 9 242 0		'_%ubrk-allowed%)
(00001EDE 2		T)
(00001EDF 9 136 1		'_%kbd-break-hook%)
(00001EE2 15 26 0		JMP 00001EFF)
(00001EE5 20 1 0 0 1)
(00001EEA 9 194 1		"VLMSG.DLL")
(00001EED 51 190 95 0 0		24510)
(00001EF2 81 2 193 1 1 0		string-resource)
(00001EF8 81 1 110 1 1 0		_msg-err)
(00001EFE 22		ret)
(00001EFF 9 255 1		'(7909 nil))
(00001F02 9 230 0		'%prsh_ok%)
(00001F05 5 6		UnVar6)
(00001F07 14 9 0		T->JMP 00001F13)
(00001F0A 9 254 1		'(13079 _protected-tabbed-ok))
(00001F0D 53 1 229 0 1 32		eval)
(00001F13 9 228 0		'%prsh_cancel%)
(00001F16 15 19 0		JMP 00001F2C)
(00001F19 20 1 1 1 0)
(00001F1E 9 77 1		'identity)
(00001F21 9 227 0		':CANCEL)
(00001F24 42		cons)
(00001F25 81 1 76 1 1 0		put-command)
(00001F2B 22		ret)
(00001F2C 9 253 1		'(7961 nil))
(00001F2F 9 226 0		'%prsh_apply%)
(00001F32 15 35 0		JMP 00001F58)
(00001F35 20 1 1 1 0)
(00001F3A 4 1 7		UpVar1-7)
(00001F3D 13 8 0		nil->JMP 00001F48)
(00001F40 5 0		UnVar0)
(00001F42 4 1 7		UpVar1-7)
(00001F45 52 1 0		)
(00001F48 9 77 1		'identity)
(00001F4B 9 232 0		':OK)
(00001F4E 42		cons)
(00001F4F 81 1 76 1 1 0		put-command)
(00001F55 10)
(00001F56 2		T)
(00001F57 22		ret)
(00001F58 12 252 1		'(7989 nil))
(00001F5B 24 14 0)
(00001F5E 15 7 0		JMP 00001F68)
(00001F61 20 1 1 1 0)
(00001F66 1		nil)
(00001F67 22		ret)
(00001F68 9 251 1		'(8033 nil))
(00001F6B 8 10		UnVar10)
(00001F6D 5 0		UnVar0)
(00001F6F 8 11		UnVar11)
(00001F71 100 12		UNVar12)
(00001F73 15 91 0		JMP 00001FD1)
(00001F76 5 11		UnVar11)
(00001F78 40		car)
(00001F79 8 12		UnVar12)
(00001F7B 5 11		UnVar11)
(00001F7D 41		cdr)
(00001F7E 8 11		UnVar11)
(00001F80 5 12		UnVar12)
(00001F82 95 1 0 45 0 0		set-dialog-status)
(00001F88 10)
(00001F89 5 12		UnVar12)
(00001F8B 9 225 0		'items)
(00001F8E 81 2 60 1 1 0		slot-value)
(00001F94 8 13		UnVar13)
(00001F96 100 14		UNVar14)
(00001F98 15 49 0		JMP 00001FCC)
(00001F9B 5 13		UnVar13)
(00001F9D 40		car)
(00001F9E 8 14		UnVar14)
(00001FA0 5 13		UnVar13)
(00001FA2 41		cdr)
(00001FA3 8 13		UnVar13)
(00001FA5 5 14		UnVar14)
(00001FA7 40		car)
(00001FA8 9 224 0		'command)
(00001FAB 81 2 60 1 1 0		slot-value)
(00001FB1 13 3 0		nil->JMP 00001FB7)
(00001FB4 15 21 0		JMP 00001FCC)
(00001FB7 5 14		UnVar14)
(00001FB9 40		car)
(00001FBA 5 10		UnVar10)
(00001FBC 95 1 189 65 0 0		copy-user-function)
(00001FC2 9 224 0		'command)
(00001FC5 81 3 239 0 1 0		slot-value<-)
(00001FCB 10)
(00001FCC 5 13		UnVar13)
(00001FCE 60 202 255		T->JMP 00001F9B)
(00001FD1 5 11		UnVar11)
(00001FD3 60 160 255		T->JMP 00001F76)
(00001FD6 1		nil)
(00001FD7 57 1 0		list)
(00001FDA 8 10		UnVar10)
(00001FDC 5 0		UnVar0)
(00001FDE 5 4		UnVar4)
(00001FE0 5 3		UnVar3)
(00001FE2 81 3 223 0 1 0		prop-sheet)
(00001FE8 10)
(00001FE9 15 16 0		JMP 00001FFC)
(00001FEC 5 10		UnVar10)
(00001FEE 81 1 237 0 1 0		get-command)
(00001FF4 81 1 236 0 1 0		execute-command)
(00001FFA 8 8		UnVar8)
(00001FFC 5 0		UnVar0)
(00001FFE 8 15		UnVar15)
(00002000 100 16		UNVar16)
(00002002 15 5 0		JMP 0000200A)
(00002005 5 15		UnVar15)
(00002007 41		cdr)
(00002008 8 15		UnVar15)
(0000200A 5 15		UnVar15)
(0000200C 61 13 0		nil->JMP 0000201C)
(0000200F 5 15		UnVar15)
(00002011 40		car)
(00002012 95 1 250 0 0 0		host-spouse-exists-p)
(00002018 11)
(00002019 8 16		UnVar16)
(0000201B 35		not)
(0000201C 60 230 255		T->JMP 00002005)
(0000201F 5 16		UnVar16)
(00002021 60 200 255		T->JMP 00001FEC)
(00002024 5 8		UnVar8)
(00002026 25 7 0)
(00002029 22		ret)
;;;def di-fmt-dialog 8234
(0000202A 20 7 4 4 1)
(0000202F 100 5		UNVar5)
(00002031 100 6		UNVar6)
(00002033 1		nil)
(00002034 1		nil)
(00002035 42		cons)
(00002036 8 6		UnVar6)
(00002038 5 3		UnVar3)
(0000203A 50 0		0)
(0000203C 5 6		UnVar6)
(0000203E 95 3 158 32 0 0		di-fmt-pos-alist)
(00002044 8 5		UnVar5)
(00002046 5 1		UnVar1)
(00002048 13 42 0		nil->JMP 00002075)
(0000204B 5 1		UnVar1)
(0000204D 81 1 58 1 1 0		ipoint-h)
(00002053 5 6		UnVar6)
(00002055 40		car)
(00002056 81 2 222 0 1 0		MAX)
(0000205C 5 1		UnVar1)
(0000205E 81 1 57 1 1 0		ipoint-v)
(00002064 5 6		UnVar6)
(00002066 41		cdr)
(00002067 81 2 222 0 1 0		MAX)
(0000206D 81 2 54 1 1 0		make-ipoint)
(00002073 8 1		UnVar1)
(00002075 9 250 1		'(3549 dialog))
(00002078 5 0		UnVar0)
(0000207A 5 1		UnVar1)
(0000207C 14 12 0		T->JMP 0000208B)
(0000207F 5 6		UnVar6)
(00002081 40		car)
(00002082 5 6		UnVar6)
(00002084 41		cdr)
(00002085 81 2 54 1 1 0		make-ipoint)
(0000208B 5 2		UnVar2)
(0000208D 5 5		UnVar5)
(0000208F 81 1 196 1 1 0		nreverse)
(00002095 5 4		UnVar4)
(00002097 81 5 203 1 1 0		list*)
(0000209D 84		apply+ret)
;;;def di-fmt-pos-alist 8350
(0000209E 20 5 1 3 0)
(000020A3 100 3		UNVar3)
(000020A5 5 1		UnVar1)
(000020A7 60 4 0		T->JMP 000020AE)
(000020AA 50 0		0)
(000020AC 8 1		UnVar1)
(000020AE 5 0		UnVar0)
(000020B0 40		car)
(000020B1 8 3		UnVar3)
(000020B3 5 3		UnVar3)
(000020B5 8 4		UnVar4)
(000020B7 5 4		UnVar4)
(000020B9 9 221 0		'(:V :VL))
(000020BC 81 2 120 1 1 0		memq)
(000020C2 13 14 0		nil->JMP 000020D3)
(000020C5 5 0		UnVar0)
(000020C7 41		cdr)
(000020C8 1		nil)
(000020C9 5 1		UnVar1)
(000020CB 5 2		UnVar2)
(000020CD 96 4 134 33 0 0		func 00002186)
(000020D3 5 4		UnVar4)
(000020D5 9 220 0		':VC)
(000020D8 38		=)
(000020D9 13 16 0		nil->JMP 000020EC)
(000020DC 5 0		UnVar0)
(000020DE 41		cdr)
(000020DF 9 219 0		':CENTER)
(000020E2 5 1		UnVar1)
(000020E4 5 2		UnVar2)
(000020E6 96 4 134 33 0 0		func 00002186)
(000020EC 5 4		UnVar4)
(000020EE 9 218 0		':VR)
(000020F1 38		=)
(000020F2 13 16 0		nil->JMP 00002105)
(000020F5 5 0		UnVar0)
(000020F7 41		cdr)
(000020F8 9 217 0		':RIGHT)
(000020FB 5 1		UnVar1)
(000020FD 5 2		UnVar2)
(000020FF 96 4 134 33 0 0		func 00002186)
(00002105 5 4		UnVar4)
(00002107 9 216 0		'(:H :HU))
(0000210A 81 2 120 1 1 0		memq)
(00002110 13 14 0		nil->JMP 00002121)
(00002113 5 0		UnVar0)
(00002115 41		cdr)
(00002116 1		nil)
(00002117 5 1		UnVar1)
(00002119 5 2		UnVar2)
(0000211B 96 4 238 34 0 0		func 000022EE)
(00002121 5 4		UnVar4)
(00002123 9 215 0		':HC)
(00002126 38		=)
(00002127 13 16 0		nil->JMP 0000213A)
(0000212A 5 0		UnVar0)
(0000212C 41		cdr)
(0000212D 9 219 0		':CENTER)
(00002130 5 1		UnVar1)
(00002132 5 2		UnVar2)
(00002134 96 4 238 34 0 0		func 000022EE)
(0000213A 5 4		UnVar4)
(0000213C 9 214 0		':HD)
(0000213F 38		=)
(00002140 13 16 0		nil->JMP 00002153)
(00002143 5 0		UnVar0)
(00002145 41		cdr)
(00002146 9 213 0		':DOWN)
(00002149 5 1		UnVar1)
(0000214B 5 2		UnVar2)
(0000214D 96 4 238 34 0 0		func 000022EE)
(00002153 5 4		UnVar4)
(00002155 9 212 0		':GROUP)
(00002158 38		=)
(00002159 13 19 0		nil->JMP 0000216F)
(0000215C 5 0		UnVar0)
(0000215E 41		cdr)
(0000215F 40		car)
(00002160 5 0		UnVar0)
(00002162 41		cdr)
(00002163 41		cdr)
(00002164 40		car)
(00002165 5 1		UnVar1)
(00002167 5 2		UnVar2)
(00002169 96 4 124 37 0 0		func 0000257C)
(0000216F 9 194 1		"VLMSG.DLL")
(00002172 51 226 94 0 0		24290)
(00002177 81 2 193 1 1 0		string-resource)
(0000217D 5 3		UnVar3)
(0000217F 81 2 110 1 1 0		_msg-err)
(00002185 22		ret)
;;;def nil 8582
(00002186 20 15 4 4 0)
(0000218B 100 4		UNVar4)
(0000218D 100 5		UNVar5)
(0000218F 100 6		UNVar6)
(00002191 100 7		UNVar7)
(00002193 100 8		UNVar8)
(00002195 100 9		UNVar9)
(00002197 100 10		UNVar10)
(00002199 100 11		UNVar11)
(0000219B 100 12		UNVar12)
(0000219D 5 2		UnVar2)
(0000219F 81 1 58 1 1 0		ipoint-h)
(000021A5 8 12		UnVar12)
(000021A7 5 2		UnVar2)
(000021A9 81 1 57 1 1 0		ipoint-v)
(000021AF 8 11		UnVar11)
(000021B1 5 12		UnVar12)
(000021B3 8 10		UnVar10)
(000021B5 5 11		UnVar11)
(000021B7 8 9		UnVar9)
(000021B9 5 0		UnVar0)
(000021BB 8 13		UnVar13)
(000021BD 100 14		UNVar14)
(000021BF 15 243 0		JMP 000022B5)
(000021C2 5 13		UnVar13)
(000021C4 40		car)
(000021C5 8 14		UnVar14)
(000021C7 5 13		UnVar13)
(000021C9 41		cdr)
(000021CA 8 13		UnVar13)
(000021CC 5 14		UnVar14)
(000021CE 81 1 125 1 1 0		fixnump)
(000021D4 13 10 0		nil->JMP 000021E1)
(000021D7 5 11		UnVar11)
(000021D9 5 14		UnVar14)
(000021DB 70		+)
(000021DC 8 11		UnVar11)
(000021DE 15 200 0		JMP 000022A9)
(000021E1 5 14		UnVar14)
(000021E3 37 2		consp)
(000021E5 13 94 0		nil->JMP 00002246)
(000021E8 5 7		UnVar7)
(000021EA 60 5 0		T->JMP 000021F2)
(000021ED 1		nil)
(000021EE 1		nil)
(000021EF 42		cons)
(000021F0 8 7		UnVar7)
(000021F2 5 14		UnVar14)
(000021F4 5 12		UnVar12)
(000021F6 5 11		UnVar11)
(000021F8 81 2 54 1 1 0		make-ipoint)
(000021FE 5 7		UnVar7)
(00002200 95 3 158 32 0 0		di-fmt-pos-alist)
(00002206 8 4		UnVar4)
(00002208 5 7		UnVar7)
(0000220A 40		car)
(0000220B 8 6		UnVar6)
(0000220D 5 7		UnVar7)
(0000220F 41		cdr)
(00002210 8 5		UnVar5)
(00002212 5 1		UnVar1)
(00002214 61 8 0		nil->JMP 0000221F)
(00002217 5 6		UnVar6)
(00002219 5 12		UnVar12)
(0000221B 71		-)
(0000221C 57 1 0		list)
(0000221F 5 4		UnVar4)
(00002221 5 8		UnVar8)
(00002223 81 3 195 1 1 0		nconc)
(00002229 8 8		UnVar8)
(0000222B 5 5		UnVar5)
(0000222D 5 11		UnVar11)
(0000222F 75		>)
(00002230 13 4 0		nil->JMP 00002237)
(00002233 5 5		UnVar5)
(00002235 8 11		UnVar11)
(00002237 5 6		UnVar6)
(00002239 5 10		UnVar10)
(0000223B 75		>)
(0000223C 13 4 0		nil->JMP 00002243)
(0000223F 5 6		UnVar6)
(00002241 8 10		UnVar10)
(00002243 15 99 0		JMP 000022A9)
(00002246 5 14		UnVar14)
(00002248 5 12		UnVar12)
(0000224A 5 11		UnVar11)
(0000224C 81 2 54 1 1 0		make-ipoint)
(00002252 42		cons)
(00002253 8 4		UnVar4)
(00002255 5 14		UnVar14)
(00002257 9 61 1		'size)
(0000225A 81 2 60 1 1 0		slot-value)
(00002260 8 2		UnVar2)
(00002262 5 2		UnVar2)
(00002264 81 1 58 1 1 0		ipoint-h)
(0000226A 8 6		UnVar6)
(0000226C 5 2		UnVar2)
(0000226E 81 1 57 1 1 0		ipoint-v)
(00002274 8 5		UnVar5)
(00002276 5 1		UnVar1)
(00002278 61 5 0		nil->JMP 00002280)
(0000227B 5 6		UnVar6)
(0000227D 57 1 0		list)
(00002280 5 4		UnVar4)
(00002282 57 1 0		list)
(00002285 5 8		UnVar8)
(00002287 81 3 195 1 1 0		nconc)
(0000228D 8 8		UnVar8)
(0000228F 5 11		UnVar11)
(00002291 5 5		UnVar5)
(00002293 70		+)
(00002294 8 11		UnVar11)
(00002296 5 12		UnVar12)
(00002298 5 6		UnVar6)
(0000229A 70		+)
(0000229B 8 6		UnVar6)
(0000229D 5 6		UnVar6)
(0000229F 5 10		UnVar10)
(000022A1 75		>)
(000022A2 13 4 0		nil->JMP 000022A9)
(000022A5 5 6		UnVar6)
(000022A7 8 10		UnVar10)
(000022A9 5 11		UnVar11)
(000022AB 5 9		UnVar9)
(000022AD 75		>)
(000022AE 13 4 0		nil->JMP 000022B5)
(000022B1 5 11		UnVar11)
(000022B3 8 9		UnVar9)
(000022B5 5 13		UnVar13)
(000022B7 60 8 255		T->JMP 000021C2)
(000022BA 5 3		UnVar3)
(000022BC 37 2		consp)
(000022BE 13 22 0		nil->JMP 000022D7)
(000022C1 5 3		UnVar3)
(000022C3 5 10		UnVar10)
(000022C5 81 2 127 1 1 0		setcar)
(000022CB 10)
(000022CC 5 3		UnVar3)
(000022CE 5 9		UnVar9)
(000022D0 81 2 211 0 1 0		setcdr)
(000022D6 10)
(000022D7 5 1		UnVar1)
(000022D9 13 15 0		nil->JMP 000022EB)
(000022DC 5 8		UnVar8)
(000022DE 5 1		UnVar1)
(000022E0 5 10		UnVar10)
(000022E2 5 12		UnVar12)
(000022E4 71		-)
(000022E5 96 3 86 36 0 0		func 00002456)
(000022EB 5 8		UnVar8)
(000022ED 22		ret)
;;;def nil 8942
(000022EE 20 15 4 4 0)
(000022F3 100 4		UNVar4)
(000022F5 100 5		UNVar5)
(000022F7 100 6		UNVar6)
(000022F9 100 7		UNVar7)
(000022FB 100 8		UNVar8)
(000022FD 100 9		UNVar9)
(000022FF 100 10		UNVar10)
(00002301 100 11		UNVar11)
(00002303 100 12		UNVar12)
(00002305 5 2		UnVar2)
(00002307 81 1 58 1 1 0		ipoint-h)
(0000230D 8 12		UnVar12)
(0000230F 5 2		UnVar2)
(00002311 81 1 57 1 1 0		ipoint-v)
(00002317 8 11		UnVar11)
(00002319 5 12		UnVar12)
(0000231B 8 10		UnVar10)
(0000231D 5 11		UnVar11)
(0000231F 8 9		UnVar9)
(00002321 5 0		UnVar0)
(00002323 8 13		UnVar13)
(00002325 100 14		UNVar14)
(00002327 15 243 0		JMP 0000241D)
(0000232A 5 13		UnVar13)
(0000232C 40		car)
(0000232D 8 14		UnVar14)
(0000232F 5 13		UnVar13)
(00002331 41		cdr)
(00002332 8 13		UnVar13)
(00002334 5 14		UnVar14)
(00002336 81 1 125 1 1 0		fixnump)
(0000233C 13 10 0		nil->JMP 00002349)
(0000233F 5 12		UnVar12)
(00002341 5 14		UnVar14)
(00002343 70		+)
(00002344 8 12		UnVar12)
(00002346 15 200 0		JMP 00002411)
(00002349 5 14		UnVar14)
(0000234B 37 2		consp)
(0000234D 13 94 0		nil->JMP 000023AE)
(00002350 5 7		UnVar7)
(00002352 60 5 0		T->JMP 0000235A)
(00002355 1		nil)
(00002356 1		nil)
(00002357 42		cons)
(00002358 8 7		UnVar7)
(0000235A 5 14		UnVar14)
(0000235C 5 12		UnVar12)
(0000235E 5 11		UnVar11)
(00002360 81 2 54 1 1 0		make-ipoint)
(00002366 5 7		UnVar7)
(00002368 95 3 158 32 0 0		di-fmt-pos-alist)
(0000236E 8 4		UnVar4)
(00002370 5 7		UnVar7)
(00002372 40		car)
(00002373 8 6		UnVar6)
(00002375 5 7		UnVar7)
(00002377 41		cdr)
(00002378 8 5		UnVar5)
(0000237A 5 1		UnVar1)
(0000237C 61 8 0		nil->JMP 00002387)
(0000237F 5 5		UnVar5)
(00002381 5 11		UnVar11)
(00002383 71		-)
(00002384 57 1 0		list)
(00002387 5 4		UnVar4)
(00002389 5 8		UnVar8)
(0000238B 81 3 195 1 1 0		nconc)
(00002391 8 8		UnVar8)
(00002393 5 6		UnVar6)
(00002395 5 12		UnVar12)
(00002397 75		>)
(00002398 13 4 0		nil->JMP 0000239F)
(0000239B 5 6		UnVar6)
(0000239D 8 12		UnVar12)
(0000239F 5 5		UnVar5)
(000023A1 5 9		UnVar9)
(000023A3 75		>)
(000023A4 13 4 0		nil->JMP 000023AB)
(000023A7 5 5		UnVar5)
(000023A9 8 9		UnVar9)
(000023AB 15 99 0		JMP 00002411)
(000023AE 5 14		UnVar14)
(000023B0 5 12		UnVar12)
(000023B2 5 11		UnVar11)
(000023B4 81 2 54 1 1 0		make-ipoint)
(000023BA 42		cons)
(000023BB 8 4		UnVar4)
(000023BD 5 14		UnVar14)
(000023BF 9 61 1		'size)
(000023C2 81 2 60 1 1 0		slot-value)
(000023C8 8 2		UnVar2)
(000023CA 5 2		UnVar2)
(000023CC 81 1 58 1 1 0		ipoint-h)
(000023D2 8 6		UnVar6)
(000023D4 5 2		UnVar2)
(000023D6 81 1 57 1 1 0		ipoint-v)
(000023DC 8 5		UnVar5)
(000023DE 5 1		UnVar1)
(000023E0 61 5 0		nil->JMP 000023E8)
(000023E3 5 5		UnVar5)
(000023E5 57 1 0		list)
(000023E8 5 4		UnVar4)
(000023EA 57 1 0		list)
(000023ED 5 8		UnVar8)
(000023EF 81 3 195 1 1 0		nconc)
(000023F5 8 8		UnVar8)
(000023F7 5 12		UnVar12)
(000023F9 5 6		UnVar6)
(000023FB 70		+)
(000023FC 8 12		UnVar12)
(000023FE 5 11		UnVar11)
(00002400 5 5		UnVar5)
(00002402 70		+)
(00002403 8 5		UnVar5)
(00002405 5 5		UnVar5)
(00002407 5 9		UnVar9)
(00002409 75		>)
(0000240A 13 4 0		nil->JMP 00002411)
(0000240D 5 5		UnVar5)
(0000240F 8 9		UnVar9)
(00002411 5 12		UnVar12)
(00002413 5 10		UnVar10)
(00002415 75		>)
(00002416 13 4 0		nil->JMP 0000241D)
(00002419 5 12		UnVar12)
(0000241B 8 10		UnVar10)
(0000241D 5 13		UnVar13)
(0000241F 60 8 255		T->JMP 0000232A)
(00002422 5 3		UnVar3)
(00002424 37 2		consp)
(00002426 13 22 0		nil->JMP 0000243F)
(00002429 5 3		UnVar3)
(0000242B 5 10		UnVar10)
(0000242D 81 2 127 1 1 0		setcar)
(00002433 10)
(00002434 5 3		UnVar3)
(00002436 5 9		UnVar9)
(00002438 81 2 211 0 1 0		setcdr)
(0000243E 10)
(0000243F 5 1		UnVar1)
(00002441 13 15 0		nil->JMP 00002453)
(00002444 5 8		UnVar8)
(00002446 5 1		UnVar1)
(00002448 5 9		UnVar9)
(0000244A 5 11		UnVar11)
(0000244C 71		-)
(0000244D 96 3 233 36 0 0		func 000024E9)
(00002453 5 8		UnVar8)
(00002455 22		ret)
;;;def nil 9302
(00002456 20 7 3 5 0)
(0000245B 100 5		UNVar5)
(0000245D 100 6		UNVar6)
(0000245F 5 0		UnVar0)
(00002461 13 124 0		nil->JMP 000024E0)
(00002464 5 0		UnVar0)
(00002466 40		car)
(00002467 11)
(00002468 8 6		UnVar6)
(0000246A 81 1 125 1 1 0		fixnump)
(00002470 13 53 0		nil->JMP 000024A8)
(00002473 5 2		UnVar2)
(00002475 5 6		UnVar6)
(00002477 71		-)
(00002478 8 5		UnVar5)
(0000247A 5 1		UnVar1)
(0000247C 9 217 0		':RIGHT)
(0000247F 38		=)
(00002480 13 5 0		nil->JMP 00002488)
(00002483 5 5		UnVar5)
(00002485 15 5 0		JMP 0000248D)
(00002488 5 5		UnVar5)
(0000248A 50 2		2)
(0000248C 73		/)
(0000248D 50 0		0)
(0000248F 81 2 54 1 1 0		make-ipoint)
(00002495 8 3		UnVar3)
(00002497 5 0		UnVar0)
(00002499 41		cdr)
(0000249A 5 1		UnVar1)
(0000249C 5 2		UnVar2)
(0000249E 5 3		UnVar3)
(000024A0 5 4		UnVar4)
(000024A2 97 5 91 36 0 0		offset 0000245B)
(000024A8 5 6		UnVar6)
(000024AA 5 3		UnVar3)
(000024AC 5 6		UnVar6)
(000024AE 41		cdr)
(000024AF 81 2 59 1 1 0		add-ipoints)
(000024B5 81 2 211 0 1 0		setcdr)
(000024BB 10)
(000024BC 5 0		UnVar0)
(000024BE 8 6		UnVar6)
(000024C0 5 0		UnVar0)
(000024C2 41		cdr)
(000024C3 8 0		UnVar0)
(000024C5 5 6		UnVar6)
(000024C7 5 4		UnVar4)
(000024C9 81 2 211 0 1 0		setcdr)
(000024CF 10)
(000024D0 5 0		UnVar0)
(000024D2 5 1		UnVar1)
(000024D4 5 2		UnVar2)
(000024D6 5 3		UnVar3)
(000024D8 5 6		UnVar6)
(000024DA 97 5 91 36 0 0		offset 0000245B)
(000024E0 5 4		UnVar4)
(000024E2 81 1 196 1 1 0		nreverse)
(000024E8 22		ret)
;;;def nil 9449
(000024E9 20 7 3 5 0)
(000024EE 100 5		UNVar5)
(000024F0 100 6		UNVar6)
(000024F2 5 0		UnVar0)
(000024F4 13 124 0		nil->JMP 00002573)
(000024F7 5 0		UnVar0)
(000024F9 40		car)
(000024FA 11)
(000024FB 8 6		UnVar6)
(000024FD 81 1 125 1 1 0		fixnump)
(00002503 13 53 0		nil->JMP 0000253B)
(00002506 5 2		UnVar2)
(00002508 5 6		UnVar6)
(0000250A 71		-)
(0000250B 8 5		UnVar5)
(0000250D 50 0		0)
(0000250F 5 1		UnVar1)
(00002511 9 213 0		':DOWN)
(00002514 38		=)
(00002515 13 5 0		nil->JMP 0000251D)
(00002518 5 5		UnVar5)
(0000251A 15 5 0		JMP 00002522)
(0000251D 5 5		UnVar5)
(0000251F 50 2		2)
(00002521 73		/)
(00002522 81 2 54 1 1 0		make-ipoint)
(00002528 8 3		UnVar3)
(0000252A 5 0		UnVar0)
(0000252C 41		cdr)
(0000252D 5 1		UnVar1)
(0000252F 5 2		UnVar2)
(00002531 5 3		UnVar3)
(00002533 5 4		UnVar4)
(00002535 97 5 238 36 0 0		offset 000024EE)
(0000253B 5 6		UnVar6)
(0000253D 5 3		UnVar3)
(0000253F 5 6		UnVar6)
(00002541 41		cdr)
(00002542 81 2 59 1 1 0		add-ipoints)
(00002548 81 2 211 0 1 0		setcdr)
(0000254E 10)
(0000254F 5 0		UnVar0)
(00002551 8 6		UnVar6)
(00002553 5 0		UnVar0)
(00002555 41		cdr)
(00002556 8 0		UnVar0)
(00002558 5 6		UnVar6)
(0000255A 5 4		UnVar4)
(0000255C 81 2 211 0 1 0		setcdr)
(00002562 10)
(00002563 5 0		UnVar0)
(00002565 5 1		UnVar1)
(00002567 5 2		UnVar2)
(00002569 5 3		UnVar3)
(0000256B 5 6		UnVar6)
(0000256D 97 5 238 36 0 0		offset 000024EE)
(00002573 5 4		UnVar4)
(00002575 81 1 196 1 1 0		nreverse)
(0000257B 22		ret)
;;;def nil 9596
(0000257C 20 12 4 4 0)
(00002581 5 2		UnVar2)
(00002583 81 1 58 1 1 0		ipoint-h)
(00002589 50 1		1)
(0000258B 70		+)
(0000258C 5 2		UnVar2)
(0000258E 81 1 57 1 1 0		ipoint-v)
(00002594 5 0		UnVar0)
(00002596 13 5 0		nil->JMP 0000259E)
(00002599 50 12		12)
(0000259B 15 2 0		JMP 000025A0)
(0000259E 50 1		1)
(000025A0 70		+)
(000025A1 81 2 54 1 1 0		make-ipoint)
(000025A7 8 4		UnVar4)
(000025A9 1		nil)
(000025AA 1		nil)
(000025AB 42		cons)
(000025AC 8 5		UnVar5)
(000025AE 100 6		UNVar6)
(000025B0 100 7		UNVar7)
(000025B2 100 8		UNVar8)
(000025B4 100 9		UNVar9)
(000025B6 100 10		UNVar10)
(000025B8 100 11		UNVar11)
(000025BA 5 1		UnVar1)
(000025BC 5 4		UnVar4)
(000025BE 5 5		UnVar5)
(000025C0 95 3 158 32 0 0		di-fmt-pos-alist)
(000025C6 8 6		UnVar6)
(000025C8 5 5		UnVar5)
(000025CA 40		car)
(000025CB 8 7		UnVar7)
(000025CD 5 5		UnVar5)
(000025CF 41		cdr)
(000025D0 8 8		UnVar8)
(000025D2 5 7		UnVar7)
(000025D4 5 2		UnVar2)
(000025D6 81 1 58 1 1 0		ipoint-h)
(000025DC 71		-)
(000025DD 50 2		2)
(000025DF 70		+)
(000025E0 8 9		UnVar9)
(000025E2 5 8		UnVar8)
(000025E4 5 2		UnVar2)
(000025E6 81 1 57 1 1 0		ipoint-v)
(000025EC 71		-)
(000025ED 50 2		2)
(000025EF 70		+)
(000025F0 8 10		UnVar10)
(000025F2 5 9		UnVar9)
(000025F4 5 10		UnVar10)
(000025F6 81 2 54 1 1 0		make-ipoint)
(000025FC 5 0		UnVar0)
(000025FE 95 2 206 18 0 0		group-box)
(00002604 8 11		UnVar11)
(00002606 5 3		UnVar3)
(00002608 37 2		consp)
(0000260A 13 28 0		nil->JMP 00002629)
(0000260D 5 3		UnVar3)
(0000260F 50 1		1)
(00002611 5 7		UnVar7)
(00002613 70		+)
(00002614 81 2 127 1 1 0		setcar)
(0000261A 10)
(0000261B 5 3		UnVar3)
(0000261D 50 1		1)
(0000261F 5 8		UnVar8)
(00002621 70		+)
(00002622 81 2 211 0 1 0		setcdr)
(00002628 10)
(00002629 5 11		UnVar11)
(0000262B 5 2		UnVar2)
(0000262D 42		cons)
(0000262E 5 6		UnVar6)
(00002630 42		cons)
(00002631 22		ret)
;;;def center-dialog 9778
(00002632 20 8 2 2 0)
(00002637 5 0		UnVar0)
(00002639 81 1 251 0 1 0		dialog._apex-and-size)
(0000263F 8 2		UnVar2)
(00002641 5 1		UnVar1)
(00002643 81 1 210 0 1 0		mdiwindow._apex-and-size)
(00002649 8 3		UnVar3)
(0000264B 100 4		UNVar4)
(0000264D 100 5		UNVar5)
(0000264F 100 6		UNVar6)
(00002651 100 7		UNVar7)
(00002653 5 1		UnVar1)
(00002655 9 209 0		'state)
(00002658 81 2 60 1 1 0		slot-value)
(0000265E 9 208 0		':NORMAL)
(00002661 38		=)
(00002662 13 19 0		nil->JMP 00002678)
(00002665 5 3		UnVar3)
(00002667 40		car)
(00002668 81 1 207 0 1 0		_mdiclient->screen)
(0000266E 8 4		UnVar4)
(00002670 5 3		UnVar3)
(00002672 41		cdr)
(00002673 8 5		UnVar5)
(00002675 15 12 0		JMP 00002684)
(00002678 50 0		0)
(0000267A 8 4		UnVar4)
(0000267C 81 0 255 0 1 0		_screen-size)
(00002682 8 5		UnVar5)
(00002684 5 4		UnVar4)
(00002686 81 1 58 1 1 0		ipoint-h)
(0000268C 5 5		UnVar5)
(0000268E 81 1 58 1 1 0		ipoint-h)
(00002694 5 2		UnVar2)
(00002696 41		cdr)
(00002697 81 1 58 1 1 0		ipoint-h)
(0000269D 71		-)
(0000269E 50 2		2)
(000026A0 73		/)
(000026A1 70		+)
(000026A2 8 6		UnVar6)
(000026A4 5 4		UnVar4)
(000026A6 81 1 57 1 1 0		ipoint-v)
(000026AC 5 5		UnVar5)
(000026AE 81 1 57 1 1 0		ipoint-v)
(000026B4 5 2		UnVar2)
(000026B6 41		cdr)
(000026B7 81 1 57 1 1 0		ipoint-v)
(000026BD 71		-)
(000026BE 50 2		2)
(000026C0 73		/)
(000026C1 70		+)
(000026C2 8 7		UnVar7)
(000026C4 5 6		UnVar6)
(000026C6 50 0		0)
(000026C8 76		<)
(000026C9 13 4 0		nil->JMP 000026D0)
(000026CC 50 17		17)
(000026CE 8 6		UnVar6)
(000026D0 5 7		UnVar7)
(000026D2 50 0		0)
(000026D4 76		<)
(000026D5 13 4 0		nil->JMP 000026DC)
(000026D8 50 17		17)
(000026DA 8 7		UnVar7)
(000026DC 5 6		UnVar6)
(000026DE 81 0 255 0 1 0		_screen-size)
(000026E4 81 1 58 1 1 0		ipoint-h)
(000026EA 5 2		UnVar2)
(000026EC 41		cdr)
(000026ED 81 1 58 1 1 0		ipoint-h)
(000026F3 71		-)
(000026F4 75		>)
(000026F5 13 31 0		nil->JMP 00002717)
(000026F8 81 0 255 0 1 0		_screen-size)
(000026FE 81 1 58 1 1 0		ipoint-h)
(00002704 5 2		UnVar2)
(00002706 41		cdr)
(00002707 81 1 58 1 1 0		ipoint-h)
(0000270D 71		-)
(0000270E 8 6		UnVar6)
(00002710 5 6		UnVar6)
(00002712 50 17		17)
(00002714 71		-)
(00002715 8 6		UnVar6)
(00002717 5 7		UnVar7)
(00002719 81 0 255 0 1 0		_screen-size)
(0000271F 81 1 57 1 1 0		ipoint-v)
(00002725 5 2		UnVar2)
(00002727 41		cdr)
(00002728 81 1 57 1 1 0		ipoint-v)
(0000272E 71		-)
(0000272F 75		>)
(00002730 13 31 0		nil->JMP 00002752)
(00002733 81 0 255 0 1 0		_screen-size)
(00002739 81 1 57 1 1 0		ipoint-v)
(0000273F 5 2		UnVar2)
(00002741 41		cdr)
(00002742 81 1 57 1 1 0		ipoint-v)
(00002748 71		-)
(00002749 8 7		UnVar7)
(0000274B 5 6		UnVar6)
(0000274D 50 17		17)
(0000274F 71		-)
(00002750 8 6		UnVar6)
(00002752 5 0		UnVar0)
(00002754 5 6		UnVar6)
(00002756 5 7		UnVar7)
(00002758 81 2 54 1 1 0		make-ipoint)
(0000275E 9 241 0		'apex)
(00002761 81 3 239 0 1 0		slot-value<-)
(00002767 22		ret)
;;;def _dialog-x2d 10088
(00002768 20 6 3 3 0)
(0000276D 5 0		UnVar0)
(0000276F 5 1		UnVar1)
(00002771 51 232 3 232 3		65537000)
(00002776 81 3 206 0 1 0		_dialog-pixsize)
(0000277C 8 3		UnVar3)
(0000277E 100 4		UNVar4)
(00002780 100 5		UNVar5)
(00002782 5 3		UnVar3)
(00002784 81 1 58 1 1 0		ipoint-h)
(0000278A 8 4		UnVar4)
(0000278C 5 3		UnVar3)
(0000278E 81 1 57 1 1 0		ipoint-v)
(00002794 8 5		UnVar5)
(00002796 51 232 3 0 0		1000)
(0000279B 5 2		UnVar2)
(0000279D 81 1 58 1 1 0		ipoint-h)
(000027A3 72		*)
(000027A4 5 4		UnVar4)
(000027A6 80		1-)
(000027A7 70		+)
(000027A8 5 4		UnVar4)
(000027AA 73		/)
(000027AB 51 232 3 0 0		1000)
(000027B0 5 2		UnVar2)
(000027B2 81 1 57 1 1 0		ipoint-v)
(000027B8 72		*)
(000027B9 5 4		UnVar4)
(000027BB 80		1-)
(000027BC 70		+)
(000027BD 5 5		UnVar5)
(000027BF 73		/)
(000027C0 81 2 54 1 1 0		make-ipoint)
(000027C6 22		ret)
;;;def alert-info.new-instance 10183
(000027C7 20 5 4 4 0)
(000027CC 5 0		UnVar0)
(000027CE 8 4		UnVar4)
(000027D0 5 1		UnVar1)
(000027D2 5 4		UnVar4)
(000027D4 45 0		IDFun0)
(000027D6 10)
(000027D7 5 2		UnVar2)
(000027D9 5 4		UnVar4)
(000027DB 45 1		IDFun1)
(000027DD 10)
(000027DE 5 3		UnVar3)
(000027E0 5 4		UnVar4)
(000027E2 45 2		IDFun2)
(000027E4 10)
(000027E5 5 0		UnVar0)
(000027E7 22		ret)
;;;def alert-info 10216
(000027E8 20 3 3 3 0)
(000027ED 9 205 0		'alert-info)
(000027F0 53 1 52 1 1 32		allocate-instance)
(000027F6 5 0		UnVar0)
(000027F8 5 1		UnVar1)
(000027FA 5 2		UnVar2)
(000027FC 96 4 199 39 0 0		alert-info.new-instance)
;;;def alert 10242
(00002802 20 4 1 1 1)
(00002807 5 0		UnVar0)
(00002809 8 2		UnVar2)
(0000280B 100 3		UNVar3)
(0000280D 9 204 0		'alert)
(00002810 5 2		UnVar2)
(00002812 81 2 204 1 1 0		compute-applicable-methods)
(00002818 8 3		UnVar3)
(0000281A 5 3		UnVar3)
(0000281C 37 2		consp)
(0000281E 13 17 0		nil->JMP 00002832)
(00002821 5 3		UnVar3)
(00002823 40		car)
(00002824 5 3		UnVar3)
(00002826 41		cdr)
(00002827 5 2		UnVar2)
(00002829 5 1		UnVar1)
(0000282B 81 3 203 1 1 0		list*)
(00002831 84		apply+ret)
(00002832 9 202 1		'no-applicable-method)
(00002835 9 204 0		'alert)
(00002838 5 2		UnVar2)
(0000283A 5 1		UnVar1)
(0000283C 81 3 203 1 1 0		list*)
(00002842 84		apply+ret)
;;;def alert-info.alert 10307
(00002843 20 5 3 3 1)
(00002848 5 1		UnVar1)
(0000284A 8 4		UnVar4)
(0000284C 5 2		UnVar2)
(0000284E 37 4		stringp)
(00002850 60 12 0		T->JMP 0000285F)
(00002853 9 203 0		"stringp")
(00002856 5 2		UnVar2)
(00002858 81 2 123 1 1 0		_bat-err)
(0000285E 10)
(0000285F 81 0 202 0 1 0		make-string-output-stream)
(00002865 8 1		UnVar1)
(00002867 9 140 1		'prinf)
(0000286A 5 1		UnVar1)
(0000286C 5 2		UnVar2)
(0000286E 5 3		UnVar3)
(00002870 81 3 203 1 1 0		list*)
(00002876 83		apply)
(00002877 10)
(00002878 5 1		UnVar1)
(0000287A 81 1 201 0 1 0		_ostream-position)
(00002880 51 250 0 0 0		250)
(00002885 75		>)
(00002886 13 29 0		nil->JMP 000028A6)
(00002889 5 1		UnVar1)
(0000288B 51 250 0 0 0		250)
(00002890 50 4		4)
(00002892 71		-)
(00002893 81 2 200 0 1 0		_ostream-position<-)
(00002899 10)
(0000289A 9 199 0		" ...")
(0000289D 5 1		UnVar1)
(0000289F 81 2 198 0 1 0		princ)
(000028A5 10)
(000028A6 5 4		UnVar4)
(000028A8 44 2		IDFun2)
(000028AA 13 11 0		nil->JMP 000028B8)
(000028AD 5 4		UnVar4)
(000028AF 44 2		IDFun2)
(000028B1 81 1 197 0 1 0		message-beep)
(000028B7 10)
(000028B8 9 196 0		'(nil :OK :CANCEL :ABORT :RETRY :IGNORE :YES :NO))
(000028BB 9 195 0		"\r")
(000028BE 9 194 0		" ")
(000028C1 5 1		UnVar1)
(000028C3 81 1 193 0 1 0		get-output-stream-string)
(000028C9 81 3 192 0 1 0		nstring-translate)
(000028CF 5 4		UnVar4)
(000028D1 44 0		IDFun0)
(000028D3 5 4		UnVar4)
(000028D5 44 1		IDFun1)
(000028D7 81 3 191 0 1 0		_message-box)
(000028DD 81 2 190 0 1 0		vector-elt)
(000028E3 22		ret)
;;;def yes-or-no-p 10468
(000028E4 20 2 1 1 1)
(000028E9 9 189 0		':YES)
(000028EC 9 249 1		'(10242 alert))
(000028EF 3 188 0		*question-alert*)
(000028F2 5 0		UnVar0)
(000028F4 5 1		UnVar1)
(000028F6 81 3 203 1 1 0		list*)
(000028FC 83		apply)
(000028FD 38		=)
(000028FE 22		ret)
;;;def alert-dialog.new-instance 10495
(000028FF 20 7 4 4 1)
(00002904 100 5		UNVar5)
(00002906 5 0		UnVar0)
(00002908 8 6		UnVar6)
(0000290A 9 194 1		"VLMSG.DLL")
(0000290D 51 155 0 0 0		155)
(00002912 81 2 193 1 1 0		string-resource)
(00002918 95 1 45 7 0 0		font-pitch-str->list)
(0000291E 8 5		UnVar5)
(00002920 5 0		UnVar0)
(00002922 51 100 0 100 0		6553700)
(00002927 51 44 0 44 0		2883628)
(0000292C 5 1		UnVar1)
(0000292E 1		nil)
(0000292F 9 75 1		':FONT)
(00002932 5 5		UnVar5)
(00002934 40		car)
(00002935 9 73 1		':PITCH)
(00002938 5 5		UnVar5)
(0000293A 41		cdr)
(0000293B 40		car)
(0000293C 9 71 1		':DEFAULT-PUSH-BUTTON)
(0000293F 5 4		UnVar4)
(00002941 40		car)
(00002942 95 11 158 11 0 0		dialog.new-instance)
(00002948 10)
(00002949 5 2		UnVar2)
(0000294B 5 6		UnVar6)
(0000294D 45 11		IDFun11)
(0000294F 10)
(00002950 5 3		UnVar3)
(00002952 5 6		UnVar6)
(00002954 45 14		IDFun14)
(00002956 10)
(00002957 5 4		UnVar4)
(00002959 5 6		UnVar6)
(0000295B 45 12		IDFun12)
(0000295D 10)
(0000295E 51 4 0 4 0		262148)
(00002963 9 187 0		"Quux")
(00002966 9 186 0		':LEFT)
(00002969 95 3 249 15 0 0		static-text)
(0000296F 5 6		UnVar6)
(00002971 45 13		IDFun13)
(00002973 10)
(00002974 5 0		UnVar0)
(00002976 22		ret)
;;;def alert-dialog 10615
(00002977 20 1 0 0 1)
(0000297C 9 248 1		'(10495 alert-dialog.new-instance))
(0000297F 9 185 0		'alert-dialog)
(00002982 53 1 52 1 1 32		allocate-instance)
(00002988 5 0		UnVar0)
(0000298A 42		cons)
(0000298B 84		apply+ret)
;;;def alert-dialog.adjust-alert 10636
(0000298C 20 13 2 2 0)
(00002991 100 2		UNVar2)
(00002993 100 3		UNVar3)
(00002995 100 4		UNVar4)
(00002997 100 5		UNVar5)
(00002999 100 6		UNVar6)
(0000299B 100 7		UNVar7)
(0000299D 100 8		UNVar8)
(0000299F 5 0		UnVar0)
(000029A1 8 9		UnVar9)
(000029A3 50 10		10)
(000029A5 8 2		UnVar2)
(000029A7 51 140 0 0 0		140)
(000029AC 8 3		UnVar3)
(000029AE 50 32		32)
(000029B0 8 8		UnVar8)
(000029B2 5 2		UnVar2)
(000029B4 8 4		UnVar4)
(000029B6 50 0		0)
(000029B8 8 5		UnVar5)
(000029BA 5 9		UnVar9)
(000029BC 44 12		IDFun12)
(000029BE 8 10		UnVar10)
(000029C0 100 11		UNVar11)
(000029C2 15 63 0		JMP 00002A04)
(000029C5 5 10		UnVar10)
(000029C7 40		car)
(000029C8 8 11		UnVar11)
(000029CA 5 10		UnVar10)
(000029CC 41		cdr)
(000029CD 8 10		UnVar10)
(000029CF 5 11		UnVar11)
(000029D1 9 61 1		'size)
(000029D4 81 2 60 1 1 0		slot-value)
(000029DA 8 12		UnVar12)
(000029DC 5 4		UnVar4)
(000029DE 5 12		UnVar12)
(000029E0 81 1 58 1 1 0		ipoint-h)
(000029E6 70		+)
(000029E7 5 2		UnVar2)
(000029E9 70		+)
(000029EA 8 4		UnVar4)
(000029EC 5 12		UnVar12)
(000029EE 81 1 57 1 1 0		ipoint-v)
(000029F4 5 5		UnVar5)
(000029F6 75		>)
(000029F7 13 10 0		nil->JMP 00002A04)
(000029FA 5 12		UnVar12)
(000029FC 81 1 57 1 1 0		ipoint-v)
(00002A02 8 5		UnVar5)
(00002A04 5 10		UnVar10)
(00002A06 60 188 255		T->JMP 000029C5)
(00002A09 5 4		UnVar4)
(00002A0B 5 3		UnVar3)
(00002A0D 75		>)
(00002A0E 13 4 0		nil->JMP 00002A15)
(00002A11 5 4		UnVar4)
(00002A13 8 3		UnVar3)
(00002A15 50 4		4)
(00002A17 5 1		UnVar1)
(00002A19 81 1 184 0 1 0		string-length)
(00002A1F 72		*)
(00002A20 8 6		UnVar6)
(00002A22 50 8		8)
(00002A24 5 6		UnVar6)
(00002A26 5 3		UnVar3)
(00002A28 5 8		UnVar8)
(00002A2A 50 2		2)
(00002A2C 81 3 183 0 1 0		-&)
(00002A32 73		/)
(00002A33 79		1+)
(00002A34 72		*)
(00002A35 8 7		UnVar7)
(00002A37 5 7		UnVar7)
(00002A39 50 25		25)
(00002A3B 76		<)
(00002A3C 13 4 0		nil->JMP 00002A43)
(00002A3F 50 25		25)
(00002A41 8 7		UnVar7)
(00002A43 5 3		UnVar3)
(00002A45 5 8		UnVar8)
(00002A47 50 2		2)
(00002A49 81 3 183 0 1 0		-&)
(00002A4F 8 6		UnVar6)
(00002A51 5 2		UnVar2)
(00002A53 5 3		UnVar3)
(00002A55 5 2		UnVar2)
(00002A57 81 3 154 1 1 0		+)
(00002A5D 5 2		UnVar2)
(00002A5F 5 7		UnVar7)
(00002A61 5 2		UnVar2)
(00002A63 5 5		UnVar5)
(00002A65 5 2		UnVar2)
(00002A67 81 5 154 1 1 0		+)
(00002A6D 81 2 54 1 1 0		make-ipoint)
(00002A73 5 9		UnVar9)
(00002A75 45 2		IDFun2)
(00002A77 10)
(00002A78 5 9		UnVar9)
(00002A7A 44 13		IDFun13)
(00002A7C 8 10		UnVar10)
(00002A7E 5 10		UnVar10)
(00002A80 5 1		UnVar1)
(00002A82 9 182 0		'text)
(00002A85 81 3 239 0 1 0		slot-value<-)
(00002A8B 10)
(00002A8C 5 10		UnVar10)
(00002A8E 5 6		UnVar6)
(00002A90 5 7		UnVar7)
(00002A92 81 2 54 1 1 0		make-ipoint)
(00002A98 9 61 1		'size)
(00002A9B 81 3 239 0 1 0		slot-value<-)
(00002AA1 10)
(00002AA2 1		nil)
(00002AA3 5 9		UnVar9)
(00002AA5 45 5		IDFun5)
(00002AA7 10)
(00002AA8 5 9		UnVar9)
(00002AAA 44 11		IDFun11)
(00002AAC 5 2		UnVar2)
(00002AAE 5 2		UnVar2)
(00002AB0 50 2		2)
(00002AB2 70		+)
(00002AB3 81 2 54 1 1 0		make-ipoint)
(00002AB9 42		cons)
(00002ABA 5 9		UnVar9)
(00002ABC 44 5		IDFun5)
(00002ABE 42		cons)
(00002ABF 5 9		UnVar9)
(00002AC1 45 5		IDFun5)
(00002AC3 10)
(00002AC4 5 2		UnVar2)
(00002AC6 5 2		UnVar2)
(00002AC8 70		+)
(00002AC9 5 3		UnVar3)
(00002ACB 5 4		UnVar4)
(00002ACD 71		-)
(00002ACE 50 2		2)
(00002AD0 73		/)
(00002AD1 70		+)
(00002AD2 8 4		UnVar4)
(00002AD4 5 9		UnVar9)
(00002AD6 44 12		IDFun12)
(00002AD8 8 10		UnVar10)
(00002ADA 100 11		UNVar11)
(00002ADC 15 72 0		JMP 00002B27)
(00002ADF 5 10		UnVar10)
(00002AE1 40		car)
(00002AE2 8 11		UnVar11)
(00002AE4 5 10		UnVar10)
(00002AE6 41		cdr)
(00002AE7 8 10		UnVar10)
(00002AE9 5 11		UnVar11)
(00002AEB 5 4		UnVar4)
(00002AED 5 2		UnVar2)
(00002AEF 5 7		UnVar7)
(00002AF1 5 2		UnVar2)
(00002AF3 81 3 181 0 1 0		+&)
(00002AF9 81 2 54 1 1 0		make-ipoint)
(00002AFF 42		cons)
(00002B00 5 9		UnVar9)
(00002B02 44 5		IDFun5)
(00002B04 42		cons)
(00002B05 5 9		UnVar9)
(00002B07 45 5		IDFun5)
(00002B09 10)
(00002B0A 5 4		UnVar4)
(00002B0C 5 11		UnVar11)
(00002B0E 9 61 1		'size)
(00002B11 81 2 60 1 1 0		slot-value)
(00002B17 81 1 58 1 1 0		ipoint-h)
(00002B1D 5 2		UnVar2)
(00002B1F 81 3 181 0 1 0		+&)
(00002B25 8 4		UnVar4)
(00002B27 5 10		UnVar10)
(00002B29 60 179 255		T->JMP 00002ADF)
(00002B2C 5 9		UnVar9)
(00002B2E 44 13		IDFun13)
(00002B30 5 2		UnVar2)
(00002B32 5 8		UnVar8)
(00002B34 50 2		2)
(00002B36 81 3 181 0 1 0		+&)
(00002B3C 5 2		UnVar2)
(00002B3E 81 2 54 1 1 0		make-ipoint)
(00002B44 42		cons)
(00002B45 5 9		UnVar9)
(00002B47 44 5		IDFun5)
(00002B49 42		cons)
(00002B4A 5 9		UnVar9)
(00002B4C 45 5		IDFun5)
(00002B4E 22		ret)
;;;def alert-dialog.alert 11087
(00002B4F 20 5 3 3 1)
(00002B54 5 1		UnVar1)
(00002B56 8 4		UnVar4)
(00002B58 5 2		UnVar2)
(00002B5A 37 4		stringp)
(00002B5C 60 12 0		T->JMP 00002B6B)
(00002B5F 9 203 0		"stringp")
(00002B62 5 2		UnVar2)
(00002B64 81 2 123 1 1 0		_bat-err)
(00002B6A 10)
(00002B6B 9 180 0		'*print-length*)
(00002B6E 50 3		3)
(00002B70 9 179 0		'*print-level*)
(00002B73 50 2		2)
(00002B75 24 4 0)
(00002B78 9 178 0		'format)
(00002B7B 1		nil)
(00002B7C 5 2		UnVar2)
(00002B7E 5 3		UnVar3)
(00002B80 81 3 203 1 1 0		list*)
(00002B86 83		apply)
(00002B87 8 2		UnVar2)
(00002B89 25 2 0)
(00002B8C 5 1		UnVar1)
(00002B8E 5 2		UnVar2)
(00002B90 95 2 140 41 0 0		alert-dialog.adjust-alert)
(00002B96 10)
(00002B97 5 4		UnVar4)
(00002B99 44 14		IDFun14)
(00002B9B 13 11 0		nil->JMP 00002BA9)
(00002B9E 5 4		UnVar4)
(00002BA0 44 14		IDFun14)
(00002BA2 81 1 197 0 1 0		message-beep)
(00002BA8 10)
(00002BA9 5 1		UnVar1)
(00002BAB 47 1 177 0 32 32		modal-dialog!!)
;;;def nil 11185
(00002BB1 20 1 1 1 0)
(00002BB6 5 0		UnVar0)
(00002BB8 95 1 197 0 0 0		destroy-host-spouse)
(00002BBE 10)
(00002BBF 9 232 0		':OK)
(00002BC2 22		ret)
;;;def nil 11203
(00002BC3 20 1 1 1 0)
(00002BC8 5 0		UnVar0)
(00002BCA 95 1 197 0 0 0		destroy-host-spouse)
(00002BD0 10)
(00002BD1 9 227 0		':CANCEL)
(00002BD4 22		ret)
;;;def nil 11221
(00002BD5 20 1 1 1 0)
(00002BDA 5 0		UnVar0)
(00002BDC 95 1 197 0 0 0		destroy-host-spouse)
(00002BE2 10)
(00002BE3 9 189 0		':YES)
(00002BE6 22		ret)
;;;def nil 11239
(00002BE7 20 1 1 1 0)
(00002BEC 5 0		UnVar0)
(00002BEE 95 1 197 0 0 0		destroy-host-spouse)
(00002BF4 10)
(00002BF5 9 176 0		':NO)
(00002BF8 22		ret)
;;;def nil 11257
(00002BF9 20 1 1 1 0)
(00002BFE 5 0		UnVar0)
(00002C00 95 1 197 0 0 0		destroy-host-spouse)
(00002C06 10)
(00002C07 9 175 0		':RETRY)
(00002C0A 22		ret)
;;;def nil 11275
(00002C0B 20 1 1 1 0)
(00002C10 5 0		UnVar0)
(00002C12 95 1 197 0 0 0		destroy-host-spouse)
(00002C18 10)
(00002C19 9 174 0		':SAVE)
(00002C1C 22		ret)
;;;def nil 11293
(00002C1D 20 1 1 1 0)
(00002C22 5 0		UnVar0)
(00002C24 95 1 197 0 0 0		destroy-host-spouse)
(00002C2A 10)
(00002C2B 9 189 0		':YES)
(00002C2E 22		ret)
;;;def nil 11311
(00002C2F 20 1 1 1 0)
(00002C34 5 0		UnVar0)
(00002C36 95 1 197 0 0 0		destroy-host-spouse)
(00002C3C 10)
(00002C3D 9 176 0		':NO)
(00002C40 22		ret)
;;;def dialog-with-labels-p 11329
(00002C41 20 1 1 1 0)
(00002C46 5 0		UnVar0)
(00002C48 9 173 0		'dialog-with-labels)
(00002C4B 47 2 82 1 32 32		typep)
;;;def dialog-labels 11345
(00002C51 20 3 1 1 0)
(00002C56 5 0		UnVar0)
(00002C58 8 1		UnVar1)
(00002C5A 100 2		UNVar2)
(00002C5C 9 172 0		'dialog-labels)
(00002C5F 5 1		UnVar1)
(00002C61 81 2 204 1 1 0		compute-applicable-methods)
(00002C67 8 2		UnVar2)
(00002C69 5 2		UnVar2)
(00002C6B 37 2		consp)
(00002C6D 13 10 0		nil->JMP 00002C7A)
(00002C70 5 2		UnVar2)
(00002C72 41		cdr)
(00002C73 5 1		UnVar1)
(00002C75 5 2		UnVar2)
(00002C77 40		car)
(00002C78 46 2		invoke+ret)
(00002C7A 9 172 0		'dialog-labels)
(00002C7D 5 1		UnVar1)
(00002C7F 81 2 202 1 1 0		no-applicable-method)
(00002C85 22		ret)
;;;def dialog-with-labels.dialog-labels 11398
(00002C86 20 3 2 2 0)
(00002C8B 5 1		UnVar1)
(00002C8D 8 2		UnVar2)
(00002C8F 5 2		UnVar2)
(00002C91 44 11		IDFun11)
(00002C93 22		ret)
;;;def dialog-labels<- 11412
(00002C94 20 4 2 2 0)
(00002C99 5 0		UnVar0)
(00002C9B 8 2		UnVar2)
(00002C9D 100 3		UNVar3)
(00002C9F 9 171 0		'dialog-labels<-)
(00002CA2 5 2		UnVar2)
(00002CA4 81 2 204 1 1 0		compute-applicable-methods)
(00002CAA 8 3		UnVar3)
(00002CAC 5 3		UnVar3)
(00002CAE 37 2		consp)
(00002CB0 13 12 0		nil->JMP 00002CBF)
(00002CB3 5 3		UnVar3)
(00002CB5 41		cdr)
(00002CB6 5 2		UnVar2)
(00002CB8 5 1		UnVar1)
(00002CBA 5 3		UnVar3)
(00002CBC 40		car)
(00002CBD 46 3		invoke+ret)
(00002CBF 9 171 0		'dialog-labels<-)
(00002CC2 5 2		UnVar2)
(00002CC4 81 2 202 1 1 0		no-applicable-method)
(00002CCA 22		ret)
;;;def dialog-with-labels.dialog-labels<- 11467
(00002CCB 20 4 3 3 0)
(00002CD0 5 1		UnVar1)
(00002CD2 8 3		UnVar3)
(00002CD4 5 2		UnVar2)
(00002CD6 5 3		UnVar3)
(00002CD8 45 11		IDFun11)
(00002CDA 22		ret)
;;;def dialog-status 11483
(00002CDB 20 1 1 1 0)
(00002CE0 5 0		UnVar0)
(00002CE2 44 11		IDFun11)
(00002CE4 9 170 0		':STATUS)
(00002CE7 81 2 74 1 1 0		getf)
(00002CED 22		ret)
;;;def label-getf 11502
(00002CEE 20 2 2 2 0)
(00002CF3 5 0		UnVar0)
(00002CF5 44 11		IDFun11)
(00002CF7 5 1		UnVar1)
(00002CF9 81 2 74 1 1 0		getf)
(00002CFF 22		ret)
;;;def set-dialog-status 11520
(00002D00 20 3 1 2 0)
(00002D05 100 2		UNVar2)
(00002D07 5 0		UnVar0)
(00002D09 95 1 65 44 0 0		dialog-with-labels-p)
(00002D0F 61 16 0		nil->JMP 00002D22)
(00002D12 5 0		UnVar0)
(00002D14 44 11		IDFun11)
(00002D16 9 170 0		':STATUS)
(00002D19 81 2 74 1 1 0		getf)
(00002D1F 11)
(00002D20 8 2		UnVar2)
(00002D22 63		nil->ret)
(00002D23 5 2		UnVar2)
(00002D25 5 1		UnVar1)
(00002D27 14 3 0		T->JMP 00002D2D)
(00002D2A 9 150 1		"")
(00002D2D 95 2 185 54 0 0		static-text.text<-)
(00002D33 10)
(00002D34 5 2		UnVar2)
(00002D36 95 1 250 0 0 0		host-spouse-exists-p)
(00002D3C 63		nil->ret)
(00002D3D 5 2		UnVar2)
(00002D3F 96 1 67 0 0 0		update-host-spouse)
;;;def _label-getf 11589
(00002D45 20 4 3 3 0)
(00002D4A 100 3		UNVar3)
(00002D4C 5 2		UnVar2)
(00002D4E 37 3		symbolp)
(00002D50 9 169 0		"Bad label")
(00002D53 5 2		UnVar2)
(00002D55 53 3 66 1 1 32		assert)
(00002D5B 10)
(00002D5C 5 1		UnVar1)
(00002D5E 5 2		UnVar2)
(00002D60 4 1 0		UpVar1-0)
(00002D63 81 3 74 1 1 0		getf)
(00002D69 8 3		UnVar3)
(00002D6B 5 3		UnVar3)
(00002D6D 4 1 0		UpVar1-0)
(00002D70 38		=)
(00002D71 13 24 0		nil->JMP 00002D8C)
(00002D74 9 194 1		"VLMSG.DLL")
(00002D77 51 134 96 0 0		24710)
(00002D7C 81 2 193 1 1 0		string-resource)
(00002D82 5 2		UnVar2)
(00002D84 5 0		UnVar0)
(00002D86 47 3 168 0 32 32		error-fmt)
(00002D8C 5 3		UnVar3)
(00002D8E 22		ret)
;;;def nil 11663
(00002D8F 20 7 3 3 1)
(00002D94 100 4		UNVar4)
(00002D96 100 5		UNVar5)
(00002D98 100 6		UNVar6)
(00002D9A 5 1		UnVar1)
(00002D9C 37 3		symbolp)
(00002D9E 13 19 0		nil->JMP 00002DB4)
(00002DA1 5 1		UnVar1)
(00002DA3 8 6		UnVar6)
(00002DA5 5 6		UnVar6)
(00002DA7 53 1 167 0 1 32		intern-keyword)
(00002DAD 8 5		UnVar5)
(00002DAF 100 4		UNVar4)
(00002DB1 15 163 0		JMP 00002E57)
(00002DB4 5 1		UnVar1)
(00002DB6 36		atom)
(00002DB7 13 26 0		nil->JMP 00002DD4)
(00002DBA 9 194 1		"VLMSG.DLL")
(00002DBD 51 144 96 0 0		24720)
(00002DC2 81 2 193 1 1 0		string-resource)
(00002DC8 5 1		UnVar1)
(00002DCA 53 2 166 0 1 32		error)
(00002DD0 10)
(00002DD1 15 131 0		JMP 00002E57)
(00002DD4 5 1		UnVar1)
(00002DD6 40		car)
(00002DD7 37 3		symbolp)
(00002DD9 13 30 0		nil->JMP 00002DFA)
(00002DDC 5 1		UnVar1)
(00002DDE 40		car)
(00002DDF 8 6		UnVar6)
(00002DE1 5 6		UnVar6)
(00002DE3 53 1 167 0 1 32		intern-keyword)
(00002DE9 8 5		UnVar5)
(00002DEB 5 1		UnVar1)
(00002DED 41		cdr)
(00002DEE 61 4 0		nil->JMP 00002DF5)
(00002DF1 5 1		UnVar1)
(00002DF3 41		cdr)
(00002DF4 40		car)
(00002DF5 8 4		UnVar4)
(00002DF7 15 93 0		JMP 00002E57)
(00002DFA 5 1		UnVar1)
(00002DFC 40		car)
(00002DFD 36		atom)
(00002DFE 13 26 0		nil->JMP 00002E1B)
(00002E01 9 194 1		"VLMSG.DLL")
(00002E04 51 144 96 0 0		24720)
(00002E09 81 2 193 1 1 0		string-resource)
(00002E0F 5 1		UnVar1)
(00002E11 53 2 166 0 1 32		error)
(00002E17 10)
(00002E18 15 60 0		JMP 00002E57)
(00002E1B 5 1		UnVar1)
(00002E1D 40		car)
(00002E1E 40		car)
(00002E1F 37 3		symbolp)
(00002E21 13 28 0		nil->JMP 00002E40)
(00002E24 5 1		UnVar1)
(00002E26 40		car)
(00002E27 41		cdr)
(00002E28 40		car)
(00002E29 8 6		UnVar6)
(00002E2B 5 1		UnVar1)
(00002E2D 40		car)
(00002E2E 40		car)
(00002E2F 8 5		UnVar5)
(00002E31 5 1		UnVar1)
(00002E33 41		cdr)
(00002E34 61 4 0		nil->JMP 00002E3B)
(00002E37 5 1		UnVar1)
(00002E39 41		cdr)
(00002E3A 40		car)
(00002E3B 8 4		UnVar4)
(00002E3D 15 23 0		JMP 00002E57)
(00002E40 9 194 1		"VLMSG.DLL")
(00002E43 51 144 96 0 0		24720)
(00002E48 81 2 193 1 1 0		string-resource)
(00002E4E 5 1		UnVar1)
(00002E50 53 2 166 0 1 32		error)
(00002E56 10)
(00002E57 5 4		UnVar4)
(00002E59 13 23 0		nil->JMP 00002E73)
(00002E5C 9 194 1		"VLMSG.DLL")
(00002E5F 51 154 96 0 0		24730)
(00002E64 81 2 193 1 1 0		string-resource)
(00002E6A 5 1		UnVar1)
(00002E6C 53 2 166 0 1 32		error)
(00002E72 10)
(00002E73 9 165 0		'let)
(00002E76 5 6		UnVar6)
(00002E78 9 164 0		'_label-getf)
(00002E7B 5 0		UnVar0)
(00002E7D 5 2		UnVar2)
(00002E7F 9 163 0		'quote)
(00002E82 5 5		UnVar5)
(00002E84 57 2 0		list)
(00002E87 57 4 0		list)
(00002E8A 57 2 0		list)
(00002E8D 57 1 0		list)
(00002E90 5 3		UnVar3)
(00002E92 81 3 203 1 1 0		list*)
(00002E98 22		ret)
;;;def with-labels-aux 11929
(00002E99 20 4 4 4 0)
(00002E9E 5 1		UnVar1)
(00002EA0 13 35 0		nil->JMP 00002EC6)
(00002EA3 9 162 0		'with-label)
(00002EA6 5 0		UnVar0)
(00002EA8 5 1		UnVar1)
(00002EAA 40		car)
(00002EAB 5 2		UnVar2)
(00002EAD 5 0		UnVar0)
(00002EAF 5 1		UnVar1)
(00002EB1 41		cdr)
(00002EB2 5 2		UnVar2)
(00002EB4 5 3		UnVar3)
(00002EB6 95 4 153 46 0 0		with-labels-aux)
(00002EBC 81 5 203 1 1 0		list*)
(00002EC2 57 1 0		list)
(00002EC5 22		ret)
(00002EC6 5 3		UnVar3)
(00002EC8 22		ret)
;;;def nil 11977
(00002EC9 20 5 2 2 1)
(00002ECE 100 3		UNVar3)
(00002ED0 100 4		UNVar4)
(00002ED2 81 0 161 0 1 0		gensym)
(00002ED8 8 4		UnVar4)
(00002EDA 81 0 161 0 1 0		gensym)
(00002EE0 8 3		UnVar3)
(00002EE2 9 160 0		'let*)
(00002EE5 5 4		UnVar4)
(00002EE7 5 1		UnVar1)
(00002EE9 57 2 0		list)
(00002EEC 5 3		UnVar3)
(00002EEE 9 60 1		'slot-value)
(00002EF1 9 159 0		'the)
(00002EF4 9 173 0		'dialog-with-labels)
(00002EF7 57 1 0		list)
(00002EFA 5 4		UnVar4)
(00002EFC 57 3 0		list)
(00002EFF 9 163 0		'quote)
(00002F02 9 158 0		'labels)
(00002F05 57 2 0		list)
(00002F08 57 3 0		list)
(00002F0B 57 2 0		list)
(00002F0E 57 2 0		list)
(00002F11 5 4		UnVar4)
(00002F13 5 0		UnVar0)
(00002F15 5 3		UnVar3)
(00002F17 5 2		UnVar2)
(00002F19 95 4 153 46 0 0		with-labels-aux)
(00002F1F 81 3 203 1 1 0		list*)
(00002F25 22		ret)
;;;def dialog-with-labels.di-fmt 12070
(00002F26 20 13 4 4 1)
(00002F2B 5 4		UnVar4)
(00002F2D 8 5		UnVar5)
(00002F2F 5 5		UnVar5)
(00002F31 9 157 0		':LABELS)
(00002F34 9 156 0		':LOST-LABEL)
(00002F37 81 3 74 1 1 0		getf)
(00002F3D 8 6		UnVar6)
(00002F3F 5 5		UnVar5)
(00002F41 9 170 0		':STATUS)
(00002F44 1		nil)
(00002F45 81 3 74 1 1 0		getf)
(00002F4B 8 7		UnVar7)
(00002F4D 100 8		UNVar8)
(00002F4F 100 9		UNVar9)
(00002F51 100 10		UNVar10)
(00002F53 100 11		UNVar11)
(00002F55 5 0		UnVar0)
(00002F57 8 12		UnVar12)
(00002F59 5 3		UnVar3)
(00002F5B 13 77 0		nil->JMP 00002FAB)
(00002F5E 50 0		0)
(00002F60 50 0		0)
(00002F62 42		cons)
(00002F63 8 8		UnVar8)
(00002F65 5 3		UnVar3)
(00002F67 50 0		0)
(00002F69 5 8		UnVar8)
(00002F6B 95 3 158 32 0 0		di-fmt-pos-alist)
(00002F71 81 1 196 1 1 0		nreverse)
(00002F77 5 12		UnVar12)
(00002F79 45 5		IDFun5)
(00002F7B 10)
(00002F7C 5 2		UnVar2)
(00002F7E 13 42 0		nil->JMP 00002FAB)
(00002F81 5 2		UnVar2)
(00002F83 81 1 58 1 1 0		ipoint-h)
(00002F89 5 8		UnVar8)
(00002F8B 40		car)
(00002F8C 81 2 222 0 1 0		MAX)
(00002F92 5 2		UnVar2)
(00002F94 81 1 57 1 1 0		ipoint-v)
(00002F9A 5 8		UnVar8)
(00002F9C 41		cdr)
(00002F9D 81 2 222 0 1 0		MAX)
(00002FA3 81 2 54 1 1 0		make-ipoint)
(00002FA9 8 2		UnVar2)
(00002FAB 5 2		UnVar2)
(00002FAD 14 24 0		T->JMP 00002FC8)
(00002FB0 5 8		UnVar8)
(00002FB2 61 12 0		nil->JMP 00002FC1)
(00002FB5 5 8		UnVar8)
(00002FB7 40		car)
(00002FB8 5 8		UnVar8)
(00002FBA 41		cdr)
(00002FBB 81 2 54 1 1 0		make-ipoint)
(00002FC1 14 4 0		T->JMP 00002FC8)
(00002FC4 5 12		UnVar12)
(00002FC6 44 2		IDFun2)
(00002FC8 5 12		UnVar12)
(00002FCA 45 2		IDFun2)
(00002FCC 10)
(00002FCD 5 6		UnVar6)
(00002FCF 9 156 0		':LOST-LABEL)
(00002FD2 38		=)
(00002FD3 13 3 0		nil->JMP 00002FD9)
(00002FD6 15 7 0		JMP 00002FE0)
(00002FD9 5 6		UnVar6)
(00002FDB 5 12		UnVar12)
(00002FDD 45 11		IDFun11)
(00002FDF 10)
(00002FE0 5 7		UnVar7)
(00002FE2 13 249 0		nil->JMP 000030DE)
(00002FE5 5 7		UnVar7)
(00002FE7 81 1 125 1 1 0		fixnump)
(00002FED 13 15 0		nil->JMP 00002FFF)
(00002FF0 5 7		UnVar7)
(00002FF2 50 8		8)
(00002FF4 72		*)
(00002FF5 8 9		UnVar9)
(00002FF7 9 150 1		"")
(00002FFA 8 10		UnVar10)
(00002FFC 15 70 0		JMP 00003045)
(00002FFF 5 7		UnVar7)
(00003001 37 4		stringp)
(00003003 13 11 0		nil->JMP 00003011)
(00003006 50 8		8)
(00003008 8 9		UnVar9)
(0000300A 5 7		UnVar7)
(0000300C 8 10		UnVar10)
(0000300E 15 52 0		JMP 00003045)
(00003011 5 7		UnVar7)
(00003013 37 2		consp)
(00003015 61 17 0		nil->JMP 00003029)
(00003018 5 7		UnVar7)
(0000301A 40		car)
(0000301B 81 1 125 1 1 0		fixnump)
(00003021 61 5 0		nil->JMP 00003029)
(00003024 5 7		UnVar7)
(00003026 41		cdr)
(00003027 37 4		stringp)
(00003029 9 155 0		"Bad status line!")
(0000302C 53 2 66 1 1 32		assert)
(00003032 10)
(00003033 5 7		UnVar7)
(00003035 40		car)
(00003036 50 8		8)
(00003038 81 2 152 1 1 0		*)
(0000303E 8 9		UnVar9)
(00003040 5 7		UnVar7)
(00003042 41		cdr)
(00003043 8 10		UnVar10)
(00003045 5 12		UnVar12)
(00003047 44 2		IDFun2)
(00003049 81 1 58 1 1 0		ipoint-h)
(0000304F 5 9		UnVar9)
(00003051 81 2 54 1 1 0		make-ipoint)
(00003057 5 10		UnVar10)
(00003059 95 2 249 15 0 0		static-text)
(0000305F 8 11		UnVar11)
(00003061 5 11		UnVar11)
(00003063 9 154 0		'(128 128 128))
(00003066 81 2 91 1 1 0		dialog-item.bcolor<-)
(0000306C 10)
(0000306D 5 11		UnVar11)
(0000306F 2		T)
(00003070 81 2 45 1 1 0		dialog-item.color-enabled<-)
(00003076 10)
(00003077 5 12		UnVar12)
(00003079 44 5		IDFun5)
(0000307B 5 11		UnVar11)
(0000307D 50 0		0)
(0000307F 5 12		UnVar12)
(00003081 44 2		IDFun2)
(00003083 81 1 57 1 1 0		ipoint-v)
(00003089 50 2		2)
(0000308B 70		+)
(0000308C 81 2 54 1 1 0		make-ipoint)
(00003092 42		cons)
(00003093 57 1 0		list)
(00003096 81 2 195 1 1 0		nconc)
(0000309C 5 12		UnVar12)
(0000309E 45 5		IDFun5)
(000030A0 10)
(000030A1 5 12		UnVar12)
(000030A3 44 2		IDFun2)
(000030A5 81 1 58 1 1 0		ipoint-h)
(000030AB 5 12		UnVar12)
(000030AD 44 2		IDFun2)
(000030AF 81 1 57 1 1 0		ipoint-v)
(000030B5 50 2		2)
(000030B7 5 9		UnVar9)
(000030B9 81 3 154 1 1 0		+)
(000030BF 81 2 54 1 1 0		make-ipoint)
(000030C5 5 12		UnVar12)
(000030C7 45 2		IDFun2)
(000030C9 10)
(000030CA 9 170 0		':STATUS)
(000030CD 5 11		UnVar11)
(000030CF 5 12		UnVar12)
(000030D1 44 11		IDFun11)
(000030D3 81 3 203 1 1 0		list*)
(000030D9 5 12		UnVar12)
(000030DB 45 11		IDFun11)
(000030DD 10)
(000030DE 5 0		UnVar0)
(000030E0 22		ret)
;;;def dialog-with-labels.new-instance 12513
(000030E1 20 9 5 5 1)
(000030E6 5 5		UnVar5)
(000030E8 8 6		UnVar6)
(000030EA 5 6		UnVar6)
(000030EC 9 157 0		':LABELS)
(000030EF 1		nil)
(000030F0 81 3 74 1 1 0		getf)
(000030F6 8 7		UnVar7)
(000030F8 5 0		UnVar0)
(000030FA 8 8		UnVar8)
(000030FC 9 18 2		'(2974 dialog.new-instance))
(000030FF 5 0		UnVar0)
(00003101 5 1		UnVar1)
(00003103 5 2		UnVar2)
(00003105 5 3		UnVar3)
(00003107 5 4		UnVar4)
(00003109 5 5		UnVar5)
(0000310B 81 6 203 1 1 0		list*)
(00003111 83		apply)
(00003112 10)
(00003113 5 7		UnVar7)
(00003115 5 8		UnVar8)
(00003117 45 11		IDFun11)
(00003119 10)
(0000311A 5 0		UnVar0)
(0000311C 22		ret)
;;;def dialog-with-labels 12573
(0000311D 20 1 0 0 1)
(00003122 9 247 1		'(12513 dialog-with-labels.new-instance))
(00003125 9 173 0		'dialog-with-labels)
(00003128 53 1 52 1 1 32		allocate-instance)
(0000312E 5 0		UnVar0)
(00003130 42		cons)
(00003131 84		apply+ret)
;;;def dialog-fmt 12594
(00003132 20 5 4 4 1)
(00003137 9 246 1		'(12573 dialog-with-labels))
(0000313A 5 0		UnVar0)
(0000313C 5 1		UnVar1)
(0000313E 5 2		UnVar2)
(00003140 1		nil)
(00003141 5 4		UnVar4)
(00003143 81 5 203 1 1 0		list*)
(00003149 83		apply)
(0000314A 1		nil)
(0000314B 1		nil)
(0000314C 5 3		UnVar3)
(0000314E 9 170 0		':STATUS)
(00003151 5 4		UnVar4)
(00003153 9 170 0		':STATUS)
(00003156 81 2 74 1 1 0		getf)
(0000315C 9 157 0		':LABELS)
(0000315F 9 156 0		':LOST-LABEL)
(00003162 96 8 38 47 0 0		dialog-with-labels.di-fmt)
;;;def push-protected-ok 12648
(00003168 20 1 1 1 0)
(0000316D 5 0		UnVar0)
(0000316F 95 1 131 49 0 0		verified-sync-down)
(00003175 62		T->ret)
(00003176 5 0		UnVar0)
(00003178 95 1 197 0 0 0		destroy-host-spouse)
(0000317E 10)
(0000317F 9 232 0		':OK)
(00003182 22		ret)
;;;def verified-sync-down 12675
(00003183 20 2 1 2 0)
(00003188 5 1		UnVar1)
(0000318A 13 7 0		nil->JMP 00003194)
(0000318D 5 1		UnVar1)
(0000318F 37 12		boxp)
(00003191 15 1 0		JMP 00003195)
(00003194 2		T)
(00003195 9 153 0		"WINDLG internal: _err is not box!")
(00003198 53 2 66 1 1 32		assert)
(0000319E 10)
(0000319F 9 15 1		'_%reinput%)
(000031A2 1		nil)
(000031A3 9 152 0		'_%err%)
(000031A6 5 1		UnVar1)
(000031A8 14 7 0		T->JMP 000031B2)
(000031AB 1		nil)
(000031AC 81 1 145 1 1 0		box)
(000031B2 9 238 0		'_%curr-rep-cntx%)
(000031B5 5 0		UnVar0)
(000031B7 9 53 1		'l-context)
(000031BA 81 2 60 1 1 0		slot-value)
(000031C0 14 3 0		T->JMP 000031C6)
(000031C3 3 238 0		_%curr-rep-cntx%)
(000031C6 24 6 0)
(000031C9 5 0		UnVar0)
(000031CB 95 1 32 20 0 0		accessed-verify)
(000031D1 13 11 0		nil->JMP 000031DF)
(000031D4 5 0		UnVar0)
(000031D6 95 1 116 14 0 0		sync-down)
(000031DC 15 34 0		JMP 00003201)
(000031DF 3 15 1		_%reinput%)
(000031E2 13 27 0		nil->JMP 00003200)
(000031E5 5 0		UnVar0)
(000031E7 3 15 1		_%reinput%)
(000031EA 3 152 0		_%err%)
(000031ED 81 1 151 0 1 0		unbox)
(000031F3 95 3 191 50 0 0		dialog.reinput)
(000031F9 10)
(000031FA 3 152 0		_%err%)
(000031FD 15 1 0		JMP 00003201)
(00003200 1		nil)
(00003201 25 3 0)
(00003204 22		ret)
;;;def verify-dialog 12805
(00003205 20 6 1 3 0)
(0000320A 5 2		UnVar2)
(0000320C 13 7 0		nil->JMP 00003216)
(0000320F 5 2		UnVar2)
(00003211 37 12		boxp)
(00003213 15 1 0		JMP 00003217)
(00003216 2		T)
(00003217 9 153 0		"WINDLG internal: _err is not box!")
(0000321A 53 2 66 1 1 32		assert)
(00003220 10)
(00003221 9 15 1		'_%reinput%)
(00003224 1		nil)
(00003225 9 152 0		'_%err%)
(00003228 5 2		UnVar2)
(0000322A 14 7 0		T->JMP 00003234)
(0000322D 1		nil)
(0000322E 81 1 145 1 1 0		box)
(00003234 9 238 0		'_%curr-rep-cntx%)
(00003237 5 0		UnVar0)
(00003239 9 53 1		'l-context)
(0000323C 81 2 60 1 1 0		slot-value)
(00003242 14 3 0		T->JMP 00003248)
(00003245 3 238 0		_%curr-rep-cntx%)
(00003248 24 6 0)
(0000324B 5 1		UnVar1)
(0000324D 13 56 0		nil->JMP 00003288)
(00003250 5 1		UnVar1)
(00003252 8 3		UnVar3)
(00003254 100 4		UNVar4)
(00003256 15 5 0		JMP 0000325E)
(00003259 5 3		UnVar3)
(0000325B 41		cdr)
(0000325C 8 3		UnVar3)
(0000325E 5 3		UnVar3)
(00003260 61 26 0		nil->JMP 0000327D)
(00003263 5 3		UnVar3)
(00003265 40		car)
(00003266 8 5		UnVar5)
(00003268 5 5		UnVar5)
(0000326A 95 1 32 20 0 0		accessed-verify)
(00003270 13 4 0		nil->JMP 00003277)
(00003273 1		nil)
(00003274 15 2 0		JMP 00003279)
(00003277 5 5		UnVar5)
(00003279 11)
(0000327A 8 4		UnVar4)
(0000327C 35		not)
(0000327D 60 217 255		T->JMP 00003259)
(00003280 5 4		UnVar4)
(00003282 6 15 1		_%reinput%)
(00003285 15 9 0		JMP 00003291)
(00003288 5 0		UnVar0)
(0000328A 95 1 32 20 0 0		accessed-verify)
(00003290 10)
(00003291 3 15 1		_%reinput%)
(00003294 13 35 0		nil->JMP 000032BA)
(00003297 3 15 1		_%reinput%)
(0000329A 13 25 0		nil->JMP 000032B6)
(0000329D 5 0		UnVar0)
(0000329F 3 15 1		_%reinput%)
(000032A2 3 152 0		_%err%)
(000032A5 81 1 151 0 1 0		unbox)
(000032AB 95 3 191 50 0 0		dialog.reinput)
(000032B1 10)
(000032B2 1		nil)
(000032B3 15 1 0		JMP 000032B7)
(000032B6 1		nil)
(000032B7 15 1 0		JMP 000032BB)
(000032BA 2		T)
(000032BB 25 3 0)
(000032BE 22		ret)
;;;def dialog.reinput 12991
(000032BF 20 4 2 3 0)
(000032C4 100 3		UNVar3)
(000032C6 50 16		16)
(000032C8 81 1 197 0 1 0		message-beep)
(000032CE 10)
(000032CF 5 1		UnVar1)
(000032D1 95 1 67 0 0 0		update-host-spouse)
(000032D7 10)
(000032D8 5 0		UnVar0)
(000032DA 95 1 65 44 0 0		dialog-with-labels-p)
(000032E0 61 11 0		nil->JMP 000032EE)
(000032E3 5 0		UnVar0)
(000032E5 95 1 219 44 0 0		dialog-status)
(000032EB 11)
(000032EC 8 3		UnVar3)
(000032EE 13 27 0		nil->JMP 0000330C)
(000032F1 5 2		UnVar2)
(000032F3 13 22 0		nil->JMP 0000330C)
(000032F6 5 2		UnVar2)
(000032F8 5 3		UnVar3)
(000032FA 45 0		IDFun0)
(000032FC 10)
(000032FD 5 0		UnVar0)
(000032FF 95 1 219 44 0 0		dialog-status)
(00003305 95 1 67 0 0 0		update-host-spouse)
(0000330B 10)
(0000330C 5 0		UnVar0)
(0000330E 5 1		UnVar1)
(00003310 81 2 150 0 1 0		dialog-item-activate)
(00003316 22		ret)
;;;def _protected-tabbed-ok 13079
(00003317 20 2 1 2 0)
(0000331C 5 1		UnVar1)
(0000331E 13 7 0		nil->JMP 00003328)
(00003321 5 1		UnVar1)
(00003323 37 12		boxp)
(00003325 15 1 0		JMP 00003329)
(00003328 2		T)
(00003329 9 153 0		"WINDLG internal: _err is not box!")
(0000332C 53 2 66 1 1 32		assert)
(00003332 10)
(00003333 9 15 1		'_%reinput%)
(00003336 1		nil)
(00003337 9 152 0		'_%err%)
(0000333A 5 1		UnVar1)
(0000333C 14 7 0		T->JMP 00003346)
(0000333F 1		nil)
(00003340 81 1 145 1 1 0		box)
(00003346 9 238 0		'_%curr-rep-cntx%)
(00003349 5 0		UnVar0)
(0000334B 9 53 1		'l-context)
(0000334E 81 2 60 1 1 0		slot-value)
(00003354 14 3 0		T->JMP 0000335A)
(00003357 3 238 0		_%curr-rep-cntx%)
(0000335A 24 6 0)
(0000335D 5 0		UnVar0)
(0000335F 95 1 32 20 0 0		accessed-verify)
(00003365 10)
(00003366 3 15 1		_%reinput%)
(00003369 13 34 0		nil->JMP 0000338E)
(0000336C 5 0		UnVar0)
(0000336E 95 1 0 45 0 0		set-dialog-status)
(00003374 10)
(00003375 5 0		UnVar0)
(00003377 3 15 1		_%reinput%)
(0000337A 3 152 0		_%err%)
(0000337D 81 1 151 0 1 0		unbox)
(00003383 95 3 191 50 0 0		dialog.reinput)
(00003389 10)
(0000338A 1		nil)
(0000338B 15 12 0		JMP 0000339A)
(0000338E 5 0		UnVar0)
(00003390 95 1 116 14 0 0		sync-down)
(00003396 10)
(00003397 9 232 0		':OK)
(0000339A 25 3 0)
(0000339D 22		ret)
;;;def snap-to-string 13214
(0000339E 20 3 1 3 0)
(000033A3 5 2		UnVar2)
(000033A5 13 3 0		nil->JMP 000033AB)
(000033A8 15 7 0		JMP 000033B2)
(000033AB 51 255 0 0 0		255)
(000033B0 8 2		UnVar2)
(000033B2 9 180 0		'*print-length*)
(000033B5 50 12		12)
(000033B7 9 179 0		'*print-level*)
(000033BA 50 3		3)
(000033BC 24 4 0)
(000033BF 5 0		UnVar0)
(000033C1 81 1 149 0 1 0		prin1-to-string)
(000033C7 8 0		UnVar0)
(000033C9 5 0		UnVar0)
(000033CB 81 1 177 1 1 0		strlen)
(000033D1 5 2		UnVar2)
(000033D3 75		>)
(000033D4 13 26 0		nil->JMP 000033F1)
(000033D7 5 0		UnVar0)
(000033D9 50 0		0)
(000033DB 5 2		UnVar2)
(000033DD 50 3		3)
(000033DF 71		-)
(000033E0 81 3 161 1 1 0		substr)
(000033E6 9 148 0		"...")
(000033E9 81 2 187 1 1 0		concat)
(000033EF 8 0		UnVar0)
(000033F1 25 2 0)
(000033F4 5 1		UnVar1)
(000033F6 13 11 0		nil->JMP 00003404)
(000033F9 5 1		UnVar1)
(000033FB 5 0		UnVar0)
(000033FD 81 2 187 1 1 0		concat)
(00003403 22		ret)
(00003404 5 0		UnVar0)
(00003406 22		ret)
;;;def _protected-read-string 13319
(00003407 21 6 3 3 0)
(0000340C 100 3		UNVar3)
(0000340E 100 4		UNVar4)
(00003410 100 5		UNVar5)
(00003412 5 1		UnVar1)
(00003414 13 23 0		nil->JMP 0000342E)
(00003417 9 150 1		"")
(0000341A 9 147 0		" \t\n\r")
(0000341D 5 1		UnVar1)
(0000341F 81 2 146 0 1 0		string-trim)
(00003425 81 2 145 0 1 0		string=)
(0000342B 15 1 0		JMP 0000342F)
(0000342E 2		T)
(0000342F 13 23 0		nil->JMP 00003449)
(00003432 5 2		UnVar2)
(00003434 8 4		UnVar4)
(00003436 9 194 1		"VLMSG.DLL")
(00003439 51 220 95 0 0		24540)
(0000343E 81 2 193 1 1 0		string-resource)
(00003444 8 3		UnVar3)
(00003446 15 130 0		JMP 000034CB)
(00003449 9 144 1		'_%sys-error-hook%)
(0000344C 15 12 0		JMP 0000345B)
(0000344F 20 1 1 1 0)
(00003454 5 0		UnVar0)
(00003456 11)
(00003457 7 1 3		UpVar1-3)
(0000345A 22		ret)
(0000345B 12 245 1		'(13391 nil))
(0000345E 9 137 1		'*xsubr-trace-hook*)
(00003461 1		nil)
(00003462 9 144 0		'*check-question*)
(00003465 1		nil)
(00003466 9 136 1		'_%kbd-break-hook%)
(00003469 15 26 0		JMP 00003486)
(0000346C 20 0 0 0 0)
(00003471 9 194 1		"VLMSG.DLL")
(00003474 51 190 95 0 0		24510)
(00003479 81 2 193 1 1 0		string-resource)
(0000347F 81 1 110 1 1 0		_msg-err)
(00003485 22		ret)
(00003486 9 244 1		'(13420 nil))
(00003489 24 8 0)
(0000348C 5 1		UnVar1)
(0000348E 81 1 143 0 1 0		make-string-input-stream)
(00003494 8 5		UnVar5)
(00003496 5 0		UnVar0)
(00003498 5 5		UnVar5)
(0000349A 5 2		UnVar2)
(0000349C 53 3 142 0 1 32		rep-cntx.p-read)
(000034A2 8 4		UnVar4)
(000034A4 5 3		UnVar3)
(000034A6 13 4 0		nil->JMP 000034AD)
(000034A9 1		nil)
(000034AA 15 8 0		JMP 000034B5)
(000034AD 5 5		UnVar5)
(000034AF 81 1 141 0 1 0		eof-streamp)
(000034B5 13 16 0		nil->JMP 000034C8)
(000034B8 9 194 1		"VLMSG.DLL")
(000034BB 51 164 96 0 0		24740)
(000034C0 81 2 193 1 1 0		string-resource)
(000034C6 8 3		UnVar3)
(000034C8 25 4 0)
(000034CB 5 4		UnVar4)
(000034CD 5 2		UnVar2)
(000034CF 38		=)
(000034D0 13 14 0		nil->JMP 000034E1)
(000034D3 5 2		UnVar2)
(000034D5 5 3		UnVar3)
(000034D7 81 2 140 0 1 0		unbox<-)
(000034DD 10)
(000034DE 5 2		UnVar2)
(000034E0 22		ret)
(000034E1 5 4		UnVar4)
(000034E3 22		ret)
;;;def _protected-read 13540
(000034E4 20 5 4 4 0)
(000034E9 100 4		UNVar4)
(000034EB 5 3		UnVar3)
(000034ED 37 12		boxp)
(000034EF 9 139 0		"Bad _err handler value!")
(000034F2 53 2 66 1 1 32		assert)
(000034F8 10)
(000034F9 5 1		UnVar1)
(000034FB 5 2		UnVar2)
(000034FD 5 3		UnVar3)
(000034FF 53 3 138 0 1 32		_protected-read-string)
(00003505 8 4		UnVar4)
(00003507 5 4		UnVar4)
(00003509 22		ret)
;;;def _protected-read-eval 13578
(0000350A 21 6 4 4 0)
(0000350F 100 4		UNVar4)
(00003511 100 5		UNVar5)
(00003513 5 1		UnVar1)
(00003515 5 2		UnVar2)
(00003517 5 3		UnVar3)
(00003519 53 3 138 0 1 32		_protected-read-string)
(0000351F 8 5		UnVar5)
(00003521 5 3		UnVar3)
(00003523 8 4		UnVar4)
(00003525 9 238 0		'_%curr-rep-cntx%)
(00003528 5 1		UnVar1)
(0000352A 14 3 0		T->JMP 00003530)
(0000352D 3 238 0		_%curr-rep-cntx%)
(00003530 9 144 1		'_%sys-error-hook%)
(00003533 15 17 0		JMP 00003547)
(00003536 20 1 1 1 0)
(0000353B 4 1 3		UpVar1-3)
(0000353E 5 0		UnVar0)
(00003540 81 2 140 0 1 0		unbox<-)
(00003546 22		ret)
(00003547 12 243 1		'(13622 nil))
(0000354A 9 137 1		'*xsubr-trace-hook*)
(0000354D 1		nil)
(0000354E 9 144 0		'*check-question*)
(00003551 1		nil)
(00003552 9 136 1		'_%kbd-break-hook%)
(00003555 15 26 0		JMP 00003572)
(00003558 20 0 0 0 0)
(0000355D 9 194 1		"VLMSG.DLL")
(00003560 51 190 95 0 0		24510)
(00003565 81 2 193 1 1 0		string-resource)
(0000356B 81 1 110 1 1 0		_msg-err)
(00003571 22		ret)
(00003572 9 242 1		'(13656 nil))
(00003575 24 10 0)
(00003578 5 5		UnVar5)
(0000357A 5 3		UnVar3)
(0000357C 38		=)
(0000357D 13 3 0		nil->JMP 00003583)
(00003580 15 24 0		JMP 0000359B)
(00003583 9 137 0		':INSPECT-EVAL)
(00003586 9 136 0		'rep-cntx.p-eval)
(00003589 3 238 0		_%curr-rep-cntx%)
(0000358C 5 3		UnVar3)
(0000358E 5 5		UnVar5)
(00003590 57 3 0		list)
(00003593 95 3 0 80 0 0		_traced-service-eval-call)
(00003599 8 4		UnVar4)
(0000359B 5 4		UnVar4)
(0000359D 25 5 0)
(000035A0 22		ret)
;;;def accessed-value 13729
(000035A1 20 1 1 1 0)
(000035A6 5 0		UnVar0)
(000035A8 37 2		consp)
(000035AA 13 27 0		nil->JMP 000035C8)
(000035AD 5 0		UnVar0)
(000035AF 9 135 0		'deep-value)
(000035B2 81 2 134 0 1 0		eqcar)
(000035B8 13 8 0		nil->JMP 000035C3)
(000035BB 5 0		UnVar0)
(000035BD 41		cdr)
(000035BE 40		car)
(000035BF 41		cdr)
(000035C0 40		car)
(000035C1 46 0		invoke+ret)
(000035C3 5 0		UnVar0)
(000035C5 40		car)
(000035C6 46 0		invoke+ret)
(000035C8 5 0		UnVar0)
(000035CA 81 1 133 0 1 0		symbol-value)
(000035D0 22		ret)
;;;def accessed-value<- 13777
(000035D1 20 2 2 2 0)
(000035D6 5 0		UnVar0)
(000035D8 36		atom)
(000035D9 13 11 0		nil->JMP 000035E7)
(000035DC 5 0		UnVar0)
(000035DE 5 1		UnVar1)
(000035E0 81 2 132 0 1 0		set)
(000035E6 22		ret)
(000035E7 5 0		UnVar0)
(000035E9 9 135 0		'deep-value)
(000035EC 81 2 134 0 1 0		eqcar)
(000035F2 13 10 0		nil->JMP 000035FF)
(000035F5 5 1		UnVar1)
(000035F7 5 0		UnVar0)
(000035F9 41		cdr)
(000035FA 40		car)
(000035FB 41		cdr)
(000035FC 40		car)
(000035FD 46 1		invoke+ret)
(000035FF 5 0		UnVar0)
(00003601 41		cdr)
(00003602 13 8 0		nil->JMP 0000360D)
(00003605 5 1		UnVar1)
(00003607 5 0		UnVar0)
(00003609 41		cdr)
(0000360A 40		car)
(0000360B 46 1		invoke+ret)
(0000360D 5 1		UnVar1)
(0000360F 5 0		UnVar0)
(00003611 40		car)
(00003612 46 1		invoke+ret)
;;;def _item-p 13844
(00003614 20 1 1 1 0)
(00003619 5 0		UnVar0)
(0000361B 37 2		consp)
(0000361D 63		nil->ret)
(0000361E 5 0		UnVar0)
(00003620 40		car)
(00003621 37 4		stringp)
(00003623 22		ret)
;;;def _item-list-p 13860
(00003624 20 3 1 1 0)
(00003629 5 0		UnVar0)
(0000362B 81 1 19 1 1 0		list-length)
(00003631 63		nil->ret)
(00003632 5 0		UnVar0)
(00003634 8 1		UnVar1)
(00003636 100 2		UNVar2)
(00003638 2		T)
(00003639 8 2		UnVar2)
(0000363B 15 5 0		JMP 00003643)
(0000363E 5 1		UnVar1)
(00003640 41		cdr)
(00003641 8 1		UnVar1)
(00003643 5 1		UnVar1)
(00003645 61 12 0		nil->JMP 00003654)
(00003648 5 1		UnVar1)
(0000364A 40		car)
(0000364B 95 1 20 54 0 0		_item-p)
(00003651 11)
(00003652 8 2		UnVar2)
(00003654 60 231 255		T->JMP 0000363E)
(00003657 5 2		UnVar2)
(00003659 22		ret)
;;;def check-box.checked 13914
(0000365A 20 1 1 1 0)
(0000365F 5 0		UnVar0)
(00003661 44 4		IDFun4)
(00003663 22		ret)
;;;def check-box.checked<- 13924
(00003664 20 2 2 2 0)
(00003669 5 1		UnVar1)
(0000366B 5 0		UnVar0)
(0000366D 45 4		IDFun4)
(0000366F 22		ret)
;;;def radio-button.selected 13936
(00003670 20 1 1 1 0)
(00003675 5 0		UnVar0)
(00003677 44 4		IDFun4)
(00003679 22		ret)
;;;def radio-button.selected<- 13946
(0000367A 20 2 2 2 0)
(0000367F 5 1		UnVar1)
(00003681 5 0		UnVar0)
(00003683 45 4		IDFun4)
(00003685 22		ret)
;;;def editable-text.text 13958
(00003686 20 1 1 1 0)
(0000368B 5 0		UnVar0)
(0000368D 44 0		IDFun0)
(0000368F 22		ret)
;;;def editable-text.text<- 13968
(00003690 20 2 2 2 0)
(00003695 5 1		UnVar1)
(00003697 37 4		stringp)
(00003699 60 12 0		T->JMP 000036A8)
(0000369C 9 131 0		"bad value for slot editable-text.text:")
(0000369F 5 1		UnVar1)
(000036A1 81 2 110 1 1 0		_msg-err)
(000036A7 10)
(000036A8 5 1		UnVar1)
(000036AA 5 0		UnVar0)
(000036AC 45 0		IDFun0)
(000036AE 22		ret)
;;;def static-text.text 13999
(000036AF 20 1 1 1 0)
(000036B4 5 0		UnVar0)
(000036B6 44 0		IDFun0)
(000036B8 22		ret)
;;;def static-text.text<- 14009
(000036B9 20 2 2 2 0)
(000036BE 5 1		UnVar1)
(000036C0 37 4		stringp)
(000036C2 60 12 0		T->JMP 000036D1)
(000036C5 9 130 0		"bad value for slot static-text.text:")
(000036C8 5 1		UnVar1)
(000036CA 81 2 110 1 1 0		_msg-err)
(000036D0 10)
(000036D1 5 1		UnVar1)
(000036D3 5 0		UnVar0)
(000036D5 45 0		IDFun0)
(000036D7 22		ret)
;;;def list-box.items 14040
(000036D8 20 1 1 1 0)
(000036DD 5 0		UnVar0)
(000036DF 44 4		IDFun4)
(000036E1 22		ret)
;;;def list-box.items<- 14050
(000036E2 20 2 2 2 0)
(000036E7 5 1		UnVar1)
(000036E9 95 1 36 54 0 0		_item-list-p)
(000036EF 60 12 0		T->JMP 000036FE)
(000036F2 9 129 0		"bad value for slot list-box.items:")
(000036F5 5 1		UnVar1)
(000036F7 81 2 110 1 1 0		_msg-err)
(000036FD 10)
(000036FE 5 1		UnVar1)
(00003700 5 0		UnVar0)
(00003702 45 4		IDFun4)
(00003704 22		ret)
;;;def drop-down-list-box.items 14085
(00003705 20 1 1 1 0)
(0000370A 5 0		UnVar0)
(0000370C 44 4		IDFun4)
(0000370E 22		ret)
;;;def drop-down-list-box.items<- 14095
(0000370F 20 2 2 2 0)
(00003714 5 1		UnVar1)
(00003716 95 1 36 54 0 0		_item-list-p)
(0000371C 60 12 0		T->JMP 0000372B)
(0000371F 9 128 0		"bad value for slot drop-down-list-box.items:")
(00003722 5 1		UnVar1)
(00003724 81 2 110 1 1 0		_msg-err)
(0000372A 10)
(0000372B 5 1		UnVar1)
(0000372D 5 0		UnVar0)
(0000372F 45 4		IDFun4)
(00003731 22		ret)
;;;def drop-down-list-box.text 14130
(00003732 20 1 1 1 0)
(00003737 5 0		UnVar0)
(00003739 44 0		IDFun0)
(0000373B 22		ret)
;;;def drop-down-list-box.text<- 14140
(0000373C 20 2 2 2 0)
(00003741 5 1		UnVar1)
(00003743 37 4		stringp)
(00003745 60 12 0		T->JMP 00003754)
(00003748 9 127 0		"bad value for slot drop-down-list-box.text:")
(0000374B 5 1		UnVar1)
(0000374D 81 2 110 1 1 0		_msg-err)
(00003753 10)
(00003754 5 1		UnVar1)
(00003756 5 0		UnVar0)
(00003758 45 0		IDFun0)
(0000375A 22		ret)
;;;def lazy-disable 14171
(0000375B 20 2 2 2 0)
(00003760 5 1		UnVar1)
(00003762 61 9 0		nil->JMP 0000376E)
(00003765 5 0		UnVar0)
(00003767 95 1 250 10 0 0		dialog-item.disable)
(0000376D 35		not)
(0000376E 14 17 0		T->JMP 00003782)
(00003771 5 1		UnVar1)
(00003773 13 4 0		nil->JMP 0000377A)
(00003776 1		nil)
(00003777 15 8 0		JMP 00003782)
(0000377A 5 0		UnVar0)
(0000377C 95 1 250 10 0 0		dialog-item.disable)
(00003782 63		nil->ret)
(00003783 5 0		UnVar0)
(00003785 5 1		UnVar1)
(00003787 95 2 27 11 0 0		dialog-item.disable<-)
(0000378D 10)
(0000378E 5 0		UnVar0)
(00003790 96 1 67 0 0 0		update-host-spouse)
;;;def accessed-dialog-item-p 14230
(00003796 20 1 1 1 0)
(0000379B 5 0		UnVar0)
(0000379D 9 126 0		'accessed-dialog-item)
(000037A0 47 2 82 1 32 32		typep)
;;;def accessed-dialog-item.update-host-spouse 14246
(000037A6 20 3 2 3 0)
(000037AB 5 1		UnVar1)
(000037AD 5 2		UnVar2)
(000037AF 81 2 125 0 1 0		dialog-item.update-host-spouse)
(000037B5 22		ret)
;;;def accessed-dialog-item.new-instance 14262
(000037B6 20 5 3 4 0)
(000037BB 5 0		UnVar0)
(000037BD 8 4		UnVar4)
(000037BF 5 1		UnVar1)
(000037C1 5 4		UnVar4)
(000037C3 45 1		IDFun1)
(000037C5 10)
(000037C6 5 2		UnVar2)
(000037C8 5 4		UnVar4)
(000037CA 45 0		IDFun0)
(000037CC 10)
(000037CD 5 3		UnVar3)
(000037CF 5 4		UnVar4)
(000037D1 45 2		IDFun2)
(000037D3 10)
(000037D4 5 0		UnVar0)
(000037D6 22		ret)
;;;def accessed-dialog-item.host-spouse-exists-p 14295
(000037D7 20 2 2 2 0)
(000037DC 5 1		UnVar1)
(000037DE 96 1 67 0 0 0		update-host-spouse)
;;;def accessed-dialog-item.sync-up 14308
(000037E4 20 2 2 2 0)
(000037E9 1		nil)
(000037EA 22		ret)
;;;def accessed-dialog-item.sync-down 14315
(000037EB 20 2 2 2 0)
(000037F0 1		nil)
(000037F1 22		ret)
;;;def accessed-dialog-item._untabstop 14322
(000037F2 20 2 1 1 0)
(000037F7 100 1		UNVar1)
(000037F9 5 0		UnVar0)
(000037FB 81 1 86 1 1 0		dialog-item._msw-style)
(00003801 8 1		UnVar1)
(00003803 5 0		UnVar0)
(00003805 5 1		UnVar1)
(00003807 51 0 0 1 0		65536)
(0000380C 81 1 87 1 1 0		lognot)
(00003812 81 2 167 1 1 0		logand)
(00003818 81 2 84 1 1 0		dialog-item._msw-style<-)
(0000381E 10)
(0000381F 5 0		UnVar0)
(00003821 22		ret)
;;;def accessed-dialog-item.accessed-verify 14370
(00003822 20 1 1 1 0)
(00003827 2		T)
(00003828 22		ret)
;;;def accessed-editable-string.new-instance 14377
(00003829 20 7 3 6 0)
(0000382E 5 0		UnVar0)
(00003830 8 6		UnVar6)
(00003832 5 0		UnVar0)
(00003834 5 1		UnVar1)
(00003836 9 150 1		"")
(00003839 5 4		UnVar4)
(0000383B 95 4 182 55 0 0		accessed-dialog-item.new-instance)
(00003841 10)
(00003842 5 3		UnVar3)
(00003844 5 6		UnVar6)
(00003846 45 3		IDFun3)
(00003848 10)
(00003849 5 2		UnVar2)
(0000384B 5 6		UnVar6)
(0000384D 45 4		IDFun4)
(0000384F 10)
(00003850 5 5		UnVar5)
(00003852 5 6		UnVar6)
(00003854 45 5		IDFun5)
(00003856 10)
(00003857 5 0		UnVar0)
(00003859 22		ret)
;;;def accessed-editable-string 14426
(0000385A 20 1 0 0 1)
(0000385F 9 241 1		'(14377 accessed-editable-string.new-instance))
(00003862 9 124 0		'accessed-editable-string)
(00003865 53 1 52 1 1 32		allocate-instance)
(0000386B 5 0		UnVar0)
(0000386D 42		cons)
(0000386E 84		apply+ret)
;;;def accessed-editable-string.sync-up 14447
(0000386F 20 3 2 2 0)
(00003874 5 1		UnVar1)
(00003876 8 2		UnVar2)
(00003878 5 2		UnVar2)
(0000387A 44 4		IDFun4)
(0000387C 95 1 161 53 0 0		accessed-value)
(00003882 14 3 0		T->JMP 00003888)
(00003885 9 150 1		"")
(00003888 5 2		UnVar2)
(0000388A 45 0		IDFun0)
(0000388C 10)
(0000388D 1		nil)
(0000388E 5 2		UnVar2)
(00003890 45 6		IDFun6)
(00003892 22		ret)
;;;def accessed-editable-string.accessed-verify 14483
(00003893 20 2 1 1 0)
(00003898 5 0		UnVar0)
(0000389A 8 1		UnVar1)
(0000389C 5 1		UnVar1)
(0000389E 44 5		IDFun5)
(000038A0 13 22 0		nil->JMP 000038B9)
(000038A3 5 0		UnVar0)
(000038A5 3 238 0		_%curr-rep-cntx%)
(000038A8 5 1		UnVar1)
(000038AA 44 0		IDFun0)
(000038AC 3 152 0		_%err%)
(000038AF 5 1		UnVar1)
(000038B1 44 5		IDFun5)
(000038B3 52 4 1		)
(000038B6 15 4 0		JMP 000038BD)
(000038B9 5 1		UnVar1)
(000038BB 44 0		IDFun0)
(000038BD 5 1		UnVar1)
(000038BF 45 6		IDFun6)
(000038C1 10)
(000038C2 5 1		UnVar1)
(000038C4 44 6		IDFun6)
(000038C6 3 152 0		_%err%)
(000038C9 38		=)
(000038CA 35		not)
(000038CB 22		ret)
;;;def accessed-editable-string.sync-down 14540
(000038CC 20 3 2 2 0)
(000038D1 5 1		UnVar1)
(000038D3 8 2		UnVar2)
(000038D5 5 2		UnVar2)
(000038D7 44 4		IDFun4)
(000038D9 5 2		UnVar2)
(000038DB 44 6		IDFun6)
(000038DD 97 2 214 53 0 0		offset 000035D6)
;;;def accessed-editable-text.new-instance 14563
(000038E3 20 7 3 6 0)
(000038E8 5 0		UnVar0)
(000038EA 8 6		UnVar6)
(000038EC 5 0		UnVar0)
(000038EE 5 1		UnVar1)
(000038F0 9 150 1		"")
(000038F3 5 4		UnVar4)
(000038F5 95 4 182 55 0 0		accessed-dialog-item.new-instance)
(000038FB 10)
(000038FC 5 3		UnVar3)
(000038FE 5 6		UnVar6)
(00003900 45 3		IDFun3)
(00003902 10)
(00003903 5 2		UnVar2)
(00003905 5 6		UnVar6)
(00003907 45 4		IDFun4)
(00003909 10)
(0000390A 5 5		UnVar5)
(0000390C 5 6		UnVar6)
(0000390E 45 5		IDFun5)
(00003910 10)
(00003911 5 0		UnVar0)
(00003913 22		ret)
;;;def accessed-editable-text 14612
(00003914 20 1 0 0 1)
(00003919 9 240 1		'(14563 accessed-editable-text.new-instance))
(0000391C 9 123 0		'accessed-editable-text)
(0000391F 53 1 52 1 1 32		allocate-instance)
(00003925 5 0		UnVar0)
(00003927 42		cons)
(00003928 84		apply+ret)
;;;def accessed-editable-text.sync-up 14633
(00003929 20 4 2 2 0)
(0000392E 100 2		UNVar2)
(00003930 5 1		UnVar1)
(00003932 8 3		UnVar3)
(00003934 5 3		UnVar3)
(00003936 44 4		IDFun4)
(00003938 95 1 161 53 0 0		accessed-value)
(0000393E 8 2		UnVar2)
(00003940 1		nil)
(00003941 5 3		UnVar3)
(00003943 45 6		IDFun6)
(00003945 10)
(00003946 3 152 0		_%err%)
(00003949 5 2		UnVar2)
(0000394B 38		=)
(0000394C 62		T->ret)
(0000394D 5 3		UnVar3)
(0000394F 44 5		IDFun5)
(00003951 13 43 0		nil->JMP 0000397F)
(00003954 5 2		UnVar2)
(00003956 37 3		symbolp)
(00003958 14 4 0		T->JMP 0000395F)
(0000395B 5 2		UnVar2)
(0000395D 37 2		consp)
(0000395F 13 16 0		nil->JMP 00003972)
(00003962 5 2		UnVar2)
(00003964 9 122 0		"'")
(00003967 95 2 158 51 0 0		snap-to-string)
(0000396D 5 3		UnVar3)
(0000396F 45 0		IDFun0)
(00003971 22		ret)
(00003972 5 2		UnVar2)
(00003974 95 1 158 51 0 0		snap-to-string)
(0000397A 5 3		UnVar3)
(0000397C 45 0		IDFun0)
(0000397E 22		ret)
(0000397F 5 2		UnVar2)
(00003981 95 1 158 51 0 0		snap-to-string)
(00003987 5 3		UnVar3)
(00003989 45 0		IDFun0)
(0000398B 22		ret)
;;;def accessed-editable-text.accessed-verify 14732
(0000398C 20 2 1 1 0)
(00003991 5 0		UnVar0)
(00003993 8 1		UnVar1)
(00003995 5 1		UnVar1)
(00003997 44 5		IDFun5)
(00003999 13 22 0		nil->JMP 000039B2)
(0000399C 5 0		UnVar0)
(0000399E 3 238 0		_%curr-rep-cntx%)
(000039A1 5 1		UnVar1)
(000039A3 44 0		IDFun0)
(000039A5 3 152 0		_%err%)
(000039A8 5 1		UnVar1)
(000039AA 44 5		IDFun5)
(000039AC 52 4 1		)
(000039AF 15 18 0		JMP 000039C4)
(000039B2 5 0		UnVar0)
(000039B4 3 238 0		_%curr-rep-cntx%)
(000039B7 5 1		UnVar1)
(000039B9 44 0		IDFun0)
(000039BB 3 152 0		_%err%)
(000039BE 95 4 228 52 0 0		_protected-read)
(000039C4 5 1		UnVar1)
(000039C6 45 6		IDFun6)
(000039C8 10)
(000039C9 5 1		UnVar1)
(000039CB 44 6		IDFun6)
(000039CD 3 152 0		_%err%)
(000039D0 38		=)
(000039D1 35		not)
(000039D2 22		ret)
;;;def accessed-editable-text.sync-down 14803
(000039D3 20 3 2 2 0)
(000039D8 5 1		UnVar1)
(000039DA 8 2		UnVar2)
(000039DC 5 2		UnVar2)
(000039DE 44 4		IDFun4)
(000039E0 5 2		UnVar2)
(000039E2 44 6		IDFun6)
(000039E4 97 2 214 53 0 0		offset 000035D6)
;;;def accessed-radio-button.new-instance 14826
(000039EA 20 10 5 9 0)
(000039EF 5 0		UnVar0)
(000039F1 8 9		UnVar9)
(000039F3 5 5		UnVar5)
(000039F5 13 3 0		nil->JMP 000039FB)
(000039F8 15 10 0		JMP 00003A05)
(000039FB 5 3		UnVar3)
(000039FD 81 1 149 0 1 0		prin1-to-string)
(00003A03 8 5		UnVar5)
(00003A05 5 0		UnVar0)
(00003A07 5 1		UnVar1)
(00003A09 5 5		UnVar5)
(00003A0B 5 4		UnVar4)
(00003A0D 95 4 182 55 0 0		accessed-dialog-item.new-instance)
(00003A13 10)
(00003A14 5 7		UnVar7)
(00003A16 5 9		UnVar9)
(00003A18 45 3		IDFun3)
(00003A1A 10)
(00003A1B 5 6		UnVar6)
(00003A1D 5 9		UnVar9)
(00003A1F 45 5		IDFun5)
(00003A21 10)
(00003A22 5 2		UnVar2)
(00003A24 5 9		UnVar9)
(00003A26 45 6		IDFun6)
(00003A28 10)
(00003A29 5 3		UnVar3)
(00003A2B 5 9		UnVar9)
(00003A2D 45 7		IDFun7)
(00003A2F 10)
(00003A30 5 8		UnVar8)
(00003A32 5 9		UnVar9)
(00003A34 45 8		IDFun8)
(00003A36 10)
(00003A37 5 0		UnVar0)
(00003A39 22		ret)
;;;def accessed-radio-button 14906
(00003A3A 20 1 0 0 1)
(00003A3F 9 239 1		'(14826 accessed-radio-button.new-instance))
(00003A42 9 121 0		'accessed-radio-button)
(00003A45 53 1 52 1 1 32		allocate-instance)
(00003A4B 5 0		UnVar0)
(00003A4D 42		cons)
(00003A4E 84		apply+ret)
;;;def accessed-radio-button.sync-up 14927
(00003A4F 20 3 2 2 0)
(00003A54 5 1		UnVar1)
(00003A56 8 2		UnVar2)
(00003A58 5 2		UnVar2)
(00003A5A 44 6		IDFun6)
(00003A5C 95 1 161 53 0 0		accessed-value)
(00003A62 5 2		UnVar2)
(00003A64 44 7		IDFun7)
(00003A66 38		=)
(00003A67 5 2		UnVar2)
(00003A69 45 4		IDFun4)
(00003A6B 22		ret)
;;;def accessed-radio-button.accessed-verify 14956
(00003A6C 20 2 1 1 0)
(00003A71 5 0		UnVar0)
(00003A73 8 1		UnVar1)
(00003A75 5 1		UnVar1)
(00003A77 44 4		IDFun4)
(00003A79 61 4 0		nil->JMP 00003A80)
(00003A7C 5 1		UnVar1)
(00003A7E 44 8		IDFun8)
(00003A80 13 25 0		nil->JMP 00003A9C)
(00003A83 5 0		UnVar0)
(00003A85 3 238 0		_%curr-rep-cntx%)
(00003A88 5 1		UnVar1)
(00003A8A 44 7		IDFun7)
(00003A8C 3 152 0		_%err%)
(00003A8F 5 1		UnVar1)
(00003A91 44 8		IDFun8)
(00003A93 52 4 1		)
(00003A96 3 152 0		_%err%)
(00003A99 38		=)
(00003A9A 35		not)
(00003A9B 22		ret)
(00003A9C 2		T)
(00003A9D 22		ret)
;;;def accessed-radio-button.sync-down 15006
(00003A9E 20 3 2 2 0)
(00003AA3 5 1		UnVar1)
(00003AA5 8 2		UnVar2)
(00003AA7 5 2		UnVar2)
(00003AA9 44 4		IDFun4)
(00003AAB 63		nil->ret)
(00003AAC 5 2		UnVar2)
(00003AAE 44 6		IDFun6)
(00003AB0 5 2		UnVar2)
(00003AB2 44 7		IDFun7)
(00003AB4 97 2 214 53 0 0		offset 000035D6)
;;;def accessed-check-box.new-instance 15034
(00003ABA 20 9 3 8 0)
(00003ABF 5 0		UnVar0)
(00003AC1 8 8		UnVar8)
(00003AC3 5 3		UnVar3)
(00003AC5 5 8		UnVar8)
(00003AC7 45 5		IDFun5)
(00003AC9 10)
(00003ACA 5 5		UnVar5)
(00003ACC 5 8		UnVar8)
(00003ACE 45 3		IDFun3)
(00003AD0 10)
(00003AD1 5 2		UnVar2)
(00003AD3 5 8		UnVar8)
(00003AD5 45 6		IDFun6)
(00003AD7 10)
(00003AD8 5 6		UnVar6)
(00003ADA 5 8		UnVar8)
(00003ADC 45 7		IDFun7)
(00003ADE 10)
(00003ADF 5 0		UnVar0)
(00003AE1 5 1		UnVar1)
(00003AE3 5 4		UnVar4)
(00003AE5 14 8 0		T->JMP 00003AF0)
(00003AE8 5 2		UnVar2)
(00003AEA 81 1 149 0 1 0		prin1-to-string)
(00003AF0 5 7		UnVar7)
(00003AF2 97 4 187 55 0 0		offset 000037BB)
;;;def accessed-check-box 15096
(00003AF8 20 1 0 0 1)
(00003AFD 9 238 1		'(15034 accessed-check-box.new-instance))
(00003B00 9 120 0		'accessed-check-box)
(00003B03 53 1 52 1 1 32		allocate-instance)
(00003B09 5 0		UnVar0)
(00003B0B 42		cons)
(00003B0C 84		apply+ret)
;;;def accessed-check-box.sync-up 15117
(00003B0D 20 3 2 2 0)
(00003B12 5 1		UnVar1)
(00003B14 8 2		UnVar2)
(00003B16 5 2		UnVar2)
(00003B18 44 6		IDFun6)
(00003B1A 95 1 161 53 0 0		accessed-value)
(00003B20 5 2		UnVar2)
(00003B22 45 4		IDFun4)
(00003B24 22		ret)
;;;def accessed-check-box.accessed-verify 15141
(00003B25 20 3 1 1 0)
(00003B2A 100 1		UNVar1)
(00003B2C 5 0		UnVar0)
(00003B2E 8 2		UnVar2)
(00003B30 5 2		UnVar2)
(00003B32 44 7		IDFun7)
(00003B34 13 25 0		nil->JMP 00003B50)
(00003B37 5 0		UnVar0)
(00003B39 3 238 0		_%curr-rep-cntx%)
(00003B3C 5 2		UnVar2)
(00003B3E 44 4		IDFun4)
(00003B40 3 152 0		_%err%)
(00003B43 5 2		UnVar2)
(00003B45 44 7		IDFun7)
(00003B47 52 4 1		)
(00003B4A 3 152 0		_%err%)
(00003B4D 38		=)
(00003B4E 35		not)
(00003B4F 22		ret)
(00003B50 2		T)
(00003B51 22		ret)
;;;def accessed-check-box.sync-down 15186
(00003B52 20 3 2 2 0)
(00003B57 5 1		UnVar1)
(00003B59 8 2		UnVar2)
(00003B5B 5 2		UnVar2)
(00003B5D 44 6		IDFun6)
(00003B5F 5 2		UnVar2)
(00003B61 44 4		IDFun4)
(00003B63 97 2 214 53 0 0		offset 000035D6)
;;;def accessed-drop-down-list-box.new-instance 15209
(00003B69 20 10 3 9 0)
(00003B6E 5 0		UnVar0)
(00003B70 8 9		UnVar9)
(00003B72 5 0		UnVar0)
(00003B74 5 1		UnVar1)
(00003B76 1		nil)
(00003B77 5 4		UnVar4)
(00003B79 95 4 182 55 0 0		accessed-dialog-item.new-instance)
(00003B7F 10)
(00003B80 5 3		UnVar3)
(00003B82 5 9		UnVar9)
(00003B84 45 3		IDFun3)
(00003B86 10)
(00003B87 5 0		UnVar0)
(00003B89 3 119 0		*LBS_WITH-STRING*)
(00003B8C 81 2 84 1 1 0		dialog-item._msw-style<-)
(00003B92 10)
(00003B93 5 2		UnVar2)
(00003B95 5 9		UnVar9)
(00003B97 45 6		IDFun6)
(00003B99 10)
(00003B9A 5 5		UnVar5)
(00003B9C 14 2 0		T->JMP 00003BA1)
(00003B9F 50 32		32)
(00003BA1 5 9		UnVar9)
(00003BA3 45 7		IDFun7)
(00003BA5 10)
(00003BA6 5 7		UnVar7)
(00003BA8 5 9		UnVar9)
(00003BAA 45 8		IDFun8)
(00003BAC 10)
(00003BAD 5 8		UnVar8)
(00003BAF 5 9		UnVar9)
(00003BB1 45 9		IDFun9)
(00003BB3 10)
(00003BB4 5 6		UnVar6)
(00003BB6 5 9		UnVar9)
(00003BB8 45 11		IDFun11)
(00003BBA 10)
(00003BBB 5 0		UnVar0)
(00003BBD 22		ret)
;;;def accessed-drop-down-list-box 15294
(00003BBE 20 1 0 0 1)
(00003BC3 9 237 1		'(15209 accessed-drop-down-list-box.new-instance))
(00003BC6 9 118 0		'accessed-drop-down-list-box)
(00003BC9 53 1 52 1 1 32		allocate-instance)
(00003BCF 5 0		UnVar0)
(00003BD1 42		cons)
(00003BD2 84		apply+ret)
;;;def accessed-drop-down-list-box.sync-up 15315
(00003BD3 20 4 2 2 0)
(00003BD8 100 2		UNVar2)
(00003BDA 5 1		UnVar1)
(00003BDC 8 3		UnVar3)
(00003BDE 5 3		UnVar3)
(00003BE0 44 6		IDFun6)
(00003BE2 95 1 161 53 0 0		accessed-value)
(00003BE8 8 2		UnVar2)
(00003BEA 1		nil)
(00003BEB 5 3		UnVar3)
(00003BED 45 10		IDFun10)
(00003BEF 10)
(00003BF0 5 2		UnVar2)
(00003BF2 3 152 0		_%err%)
(00003BF5 38		=)
(00003BF6 60 87 0		T->JMP 00003C50)
(00003BF9 5 3		UnVar3)
(00003BFB 44 8		IDFun8)
(00003BFD 13 23 0		nil->JMP 00003C17)
(00003C00 5 2		UnVar2)
(00003C02 37 4		stringp)
(00003C04 13 5 0		nil->JMP 00003C0C)
(00003C07 5 2		UnVar2)
(00003C09 15 3 0		JMP 00003C0F)
(00003C0C 9 150 1		"")
(00003C0F 5 3		UnVar3)
(00003C11 45 0		IDFun0)
(00003C13 10)
(00003C14 15 57 0		JMP 00003C50)
(00003C17 5 3		UnVar3)
(00003C19 44 9		IDFun9)
(00003C1B 13 14 0		nil->JMP 00003C2C)
(00003C1E 5 2		UnVar2)
(00003C20 36		atom)
(00003C21 61 5 0		nil->JMP 00003C29)
(00003C24 5 2		UnVar2)
(00003C26 37 3		symbolp)
(00003C28 35		not)
(00003C29 15 1 0		JMP 00003C2D)
(00003C2C 2		T)
(00003C2D 13 16 0		nil->JMP 00003C40)
(00003C30 5 2		UnVar2)
(00003C32 95 1 158 51 0 0		snap-to-string)
(00003C38 5 3		UnVar3)
(00003C3A 45 0		IDFun0)
(00003C3C 10)
(00003C3D 15 16 0		JMP 00003C50)
(00003C40 5 2		UnVar2)
(00003C42 9 122 0		"'")
(00003C45 95 2 158 51 0 0		snap-to-string)
(00003C4B 5 3		UnVar3)
(00003C4D 45 0		IDFun0)
(00003C4F 10)
(00003C50 5 3		UnVar3)
(00003C52 44 11		IDFun11)
(00003C54 63		nil->ret)
(00003C55 5 1		UnVar1)
(00003C57 5 3		UnVar3)
(00003C59 44 11		IDFun11)
(00003C5B 95 1 161 53 0 0		accessed-value)
(00003C61 96 2 39 61 0 0		accessed-drop-down-list-box.set-history)
;;;def accessed-drop-down-list-box.accessed-verify 15463
(00003C67 20 2 1 1 0)
(00003C6C 5 0		UnVar0)
(00003C6E 8 1		UnVar1)
(00003C70 5 1		UnVar1)
(00003C72 44 9		IDFun9)
(00003C74 13 22 0		nil->JMP 00003C8D)
(00003C77 5 0		UnVar0)
(00003C79 3 238 0		_%curr-rep-cntx%)
(00003C7C 5 1		UnVar1)
(00003C7E 44 0		IDFun0)
(00003C80 3 152 0		_%err%)
(00003C83 5 1		UnVar1)
(00003C85 44 9		IDFun9)
(00003C87 52 4 1		)
(00003C8A 15 32 0		JMP 00003CAD)
(00003C8D 5 1		UnVar1)
(00003C8F 44 8		IDFun8)
(00003C91 13 7 0		nil->JMP 00003C9B)
(00003C94 5 1		UnVar1)
(00003C96 44 0		IDFun0)
(00003C98 15 18 0		JMP 00003CAD)
(00003C9B 5 0		UnVar0)
(00003C9D 3 238 0		_%curr-rep-cntx%)
(00003CA0 5 1		UnVar1)
(00003CA2 44 0		IDFun0)
(00003CA4 3 152 0		_%err%)
(00003CA7 95 4 228 52 0 0		_protected-read)
(00003CAD 5 1		UnVar1)
(00003CAF 45 10		IDFun10)
(00003CB1 10)
(00003CB2 5 1		UnVar1)
(00003CB4 44 10		IDFun10)
(00003CB6 3 152 0		_%err%)
(00003CB9 38		=)
(00003CBA 35		not)
(00003CBB 22		ret)
;;;def _add-item 15548
(00003CBC 20 3 2 3 0)
(00003CC1 5 0		UnVar0)
(00003CC3 13 3 0		nil->JMP 00003CC9)
(00003CC6 15 5 0		JMP 00003CCE)
(00003CC9 9 150 1		"")
(00003CCC 8 0		UnVar0)
(00003CCE 5 0		UnVar0)
(00003CD0 5 0		UnVar0)
(00003CD2 5 1		UnVar1)
(00003CD4 81 2 117 0 1 0		delete)
(00003CDA 42		cons)
(00003CDB 5 2		UnVar2)
(00003CDD 14 2 0		T->JMP 00003CE2)
(00003CE0 50 15		15)
(00003CE2 47 2 178 1 32 32		ncut)
;;;def accessed-drop-down-list-box.sync-down 15592
(00003CE8 20 3 2 2 0)
(00003CED 5 1		UnVar1)
(00003CEF 8 2		UnVar2)
(00003CF1 5 2		UnVar2)
(00003CF3 44 6		IDFun6)
(00003CF5 5 2		UnVar2)
(00003CF7 44 10		IDFun10)
(00003CF9 95 2 209 53 0 0		accessed-value<-)
(00003CFF 10)
(00003D00 5 2		UnVar2)
(00003D02 44 11		IDFun11)
(00003D04 63		nil->ret)
(00003D05 5 2		UnVar2)
(00003D07 44 11		IDFun11)
(00003D09 5 2		UnVar2)
(00003D0B 44 0		IDFun0)
(00003D0D 5 2		UnVar2)
(00003D0F 44 11		IDFun11)
(00003D11 95 1 161 53 0 0		accessed-value)
(00003D17 5 2		UnVar2)
(00003D19 44 7		IDFun7)
(00003D1B 95 3 188 60 0 0		_add-item)
(00003D21 97 2 214 53 0 0		offset 000035D6)
;;;def accessed-drop-down-list-box.set-history 15655
(00003D27 20 9 2 4 0)
(00003D2C 100 4		UNVar4)
(00003D2E 100 5		UNVar5)
(00003D30 5 0		UnVar0)
(00003D32 8 6		UnVar6)
(00003D34 5 2		UnVar2)
(00003D36 13 32 0		nil->JMP 00003D59)
(00003D39 5 1		UnVar1)
(00003D3B 81 1 116 0 1 0		length)
(00003D41 5 2		UnVar2)
(00003D43 75		>)
(00003D44 13 18 0		nil->JMP 00003D59)
(00003D47 5 1		UnVar1)
(00003D49 50 2		2)
(00003D4B 81 2 115 0 1 0		last)
(00003D51 1		nil)
(00003D52 81 2 211 0 1 0		setcdr)
(00003D58 10)
(00003D59 9 114 0		'stringp)
(00003D5C 5 1		UnVar1)
(00003D5E 81 2 113 0 1 0		delete-if-not)
(00003D64 8 1		UnVar1)
(00003D66 9 150 1		"")
(00003D69 5 1		UnVar1)
(00003D6B 81 2 117 0 1 0		delete)
(00003D71 8 7		UnVar7)
(00003D73 100 8		UNVar8)
(00003D75 15 16 0		JMP 00003D88)
(00003D78 5 7		UnVar7)
(00003D7A 40		car)
(00003D7B 57 1 0		list)
(00003D7E 5 8		UnVar8)
(00003D80 42		cons)
(00003D81 8 8		UnVar8)
(00003D83 5 7		UnVar7)
(00003D85 41		cdr)
(00003D86 8 7		UnVar7)
(00003D88 5 7		UnVar7)
(00003D8A 60 235 255		T->JMP 00003D78)
(00003D8D 5 8		UnVar8)
(00003D8F 81 1 196 1 1 0		nreverse)
(00003D95 5 6		UnVar6)
(00003D97 45 4		IDFun4)
(00003D99 10)
(00003D9A 5 6		UnVar6)
(00003D9C 44 1		IDFun1)
(00003D9E 81 1 58 1 1 0		ipoint-h)
(00003DA4 8 4		UnVar4)
(00003DA6 50 84		84)
(00003DA8 50 19		19)
(00003DAA 50 8		8)
(00003DAC 5 6		UnVar6)
(00003DAE 44 4		IDFun4)
(00003DB0 81 1 116 0 1 0		length)
(00003DB6 72		*)
(00003DB7 70		+)
(00003DB8 81 2 112 0 1 0		MIN)
(00003DBE 8 5		UnVar5)
(00003DC0 5 4		UnVar4)
(00003DC2 5 5		UnVar5)
(00003DC4 81 2 54 1 1 0		make-ipoint)
(00003DCA 5 6		UnVar6)
(00003DCC 45 1		IDFun1)
(00003DCE 22		ret)
;;;def self-defined-static-text 15823
(00003DCF 20 1 1 1 0)
(00003DD4 50 2		2)
(00003DD6 50 4		4)
(00003DD8 5 0		UnVar0)
(00003DDA 81 1 184 0 1 0		string-length)
(00003DE0 72		*)
(00003DE1 70		+)
(00003DE2 50 12		12)
(00003DE4 81 2 54 1 1 0		make-ipoint)
(00003DEA 5 0		UnVar0)
(00003DEC 96 2 249 15 0 0		static-text)
;;;def nil 15858
(00003DF2 20 1 1 1 0)
(00003DF7 5 0		UnVar0)
(00003DF9 95 1 197 0 0 0		destroy-host-spouse)
(00003DFF 10)
(00003E00 9 227 0		':CANCEL)
(00003E03 22		ret)
;;;def nil 15876
(00003E04 20 3 3 3 0)
(00003E09 9 111 0		':H)
(00003E0C 50 2		2)
(00003E0E 5 2		UnVar2)
(00003E10 95 1 207 61 0 0		self-defined-static-text)
(00003E16 50 2		2)
(00003E18 51 80 0 12 0		786512)
(00003E1D 5 1		UnVar1)
(00003E1F 9 194 1		"VLMSG.DLL")
(00003E22 51 200 95 0 0		24520)
(00003E27 81 2 193 1 1 0		string-resource)
(00003E2D 95 3 20 57 0 0		accessed-editable-text)
(00003E33 57 5 0		list)
(00003E36 22		ret)
;;;def accessed-string-item 15927
(00003E37 20 3 1 3 0)
(00003E3C 5 1		UnVar1)
(00003E3E 14 5 0		T->JMP 00003E46)
(00003E41 51 80 0 12 0		786512)
(00003E46 5 0		UnVar0)
(00003E48 53 1 110 0 1 32		option-reader-instantiate)
(00003E4E 5 0		UnVar0)
(00003E50 53 1 109 0 1 32		option-string-instantiate)
(00003E56 57 2 0		list)
(00003E59 5 2		UnVar2)
(00003E5B 14 14 0		T->JMP 00003E6C)
(00003E5E 9 194 1		"VLMSG.DLL")
(00003E61 51 200 95 0 0		24520)
(00003E66 81 2 193 1 1 0		string-resource)
(00003E6C 96 3 90 56 0 0		accessed-editable-string)
;;;def nil 15986
(00003E72 20 3 3 3 0)
(00003E77 9 111 0		':H)
(00003E7A 50 2		2)
(00003E7C 5 2		UnVar2)
(00003E7E 95 1 207 61 0 0		self-defined-static-text)
(00003E84 50 2		2)
(00003E86 5 1		UnVar1)
(00003E88 95 1 55 62 0 0		accessed-string-item)
(00003E8E 57 5 0		list)
(00003E91 22		ret)
;;;def option-string-instantiate 16018
(00003E92 21 1 1 1 0)
(00003E97 15 16 0		JMP 00003EAA)
(00003E9A 20 1 1 1 0)
(00003E9F 4 1 0		UpVar1-0)
(00003EA2 5 0		UnVar0)
(00003EA4 96 2 209 53 0 0		accessed-value<-)
(00003EAA 12 236 1		'(16026 nil))
(00003EAD 22		ret)
;;;def accessed-checked-editable-text.new-instance 16046
(00003EAE 20 8 7 7 0)
(00003EB3 5 0		UnVar0)
(00003EB5 8 7		UnVar7)
(00003EB7 5 1		UnVar1)
(00003EB9 5 7		UnVar7)
(00003EBB 45 1		IDFun1)
(00003EBD 10)
(00003EBE 5 2		UnVar2)
(00003EC0 5 7		UnVar7)
(00003EC2 45 4		IDFun4)
(00003EC4 10)
(00003EC5 5 3		UnVar3)
(00003EC7 5 7		UnVar7)
(00003EC9 45 8		IDFun8)
(00003ECB 10)
(00003ECC 5 5		UnVar5)
(00003ECE 5 7		UnVar7)
(00003ED0 45 7		IDFun7)
(00003ED2 10)
(00003ED3 5 4		UnVar4)
(00003ED5 5 7		UnVar7)
(00003ED7 45 9		IDFun9)
(00003ED9 10)
(00003EDA 5 6		UnVar6)
(00003EDC 5 7		UnVar7)
(00003EDE 45 3		IDFun3)
(00003EE0 10)
(00003EE1 5 0		UnVar0)
(00003EE3 22		ret)
;;;def accessed-checked-editable-text 16100
(00003EE4 20 6 6 6 0)
(00003EE9 9 108 0		'accessed-checked-editable-text)
(00003EEC 53 1 52 1 1 32		allocate-instance)
(00003EF2 5 0		UnVar0)
(00003EF4 5 1		UnVar1)
(00003EF6 5 2		UnVar2)
(00003EF8 5 3		UnVar3)
(00003EFA 5 4		UnVar4)
(00003EFC 5 5		UnVar5)
(00003EFE 96 7 174 62 0 0		accessed-checked-editable-text.new-instance)
;;;def accessed-checked-value-item 16132
(00003F04 20 6 2 6 0)
(00003F09 5 2		UnVar2)
(00003F0B 13 3 0		nil->JMP 00003F11)
(00003F0E 15 10 0		JMP 00003F1B)
(00003F11 5 1		UnVar1)
(00003F13 81 1 107 0 1 0		symbol-name)
(00003F19 8 2		UnVar2)
(00003F1B 5 4		UnVar4)
(00003F1D 14 5 0		T->JMP 00003F25)
(00003F20 51 80 0 12 0		786512)
(00003F25 5 0		UnVar0)
(00003F27 5 1		UnVar1)
(00003F29 5 2		UnVar2)
(00003F2B 5 3		UnVar3)
(00003F2D 5 5		UnVar5)
(00003F2F 14 14 0		T->JMP 00003F40)
(00003F32 9 194 1		"VLMSG.DLL")
(00003F35 51 200 95 0 0		24520)
(00003F3A 81 2 193 1 1 0		string-resource)
(00003F40 97 6 233 62 0 0		offset 00003EE9)
;;;def nil 16198
(00003F46 20 5 5 5 0)
(00003F4B 9 111 0		':H)
(00003F4E 50 2		2)
(00003F50 5 2		UnVar2)
(00003F52 95 1 207 61 0 0		self-defined-static-text)
(00003F58 50 2		2)
(00003F5A 5 1		UnVar1)
(00003F5C 5 3		UnVar3)
(00003F5E 5 4		UnVar4)
(00003F60 5 2		UnVar2)
(00003F62 95 4 4 63 0 0		accessed-checked-value-item)
(00003F68 57 5 0		list)
(00003F6B 22		ret)
;;;def accessed-checked-editable-text.accessed-verify 16236
(00003F6C 20 3 1 1 0)
(00003F71 5 0		UnVar0)
(00003F73 8 1		UnVar1)
(00003F75 5 0		UnVar0)
(00003F77 3 238 0		_%curr-rep-cntx%)
(00003F7A 5 1		UnVar1)
(00003F7C 44 0		IDFun0)
(00003F7E 3 152 0		_%err%)
(00003F81 95 4 228 52 0 0		_protected-read)
(00003F87 8 2		UnVar2)
(00003F89 5 2		UnVar2)
(00003F8B 3 152 0		_%err%)
(00003F8E 38		=)
(00003F8F 13 2 0		nil->JMP 00003F94)
(00003F92 1		nil)
(00003F93 22		ret)
(00003F94 5 2		UnVar2)
(00003F96 5 1		UnVar1)
(00003F98 44 8		IDFun8)
(00003F9A 52 1 1		)
(00003F9D 13 9 0		nil->JMP 00003FA9)
(00003FA0 5 2		UnVar2)
(00003FA2 5 1		UnVar1)
(00003FA4 45 6		IDFun6)
(00003FA6 10)
(00003FA7 2		T)
(00003FA8 22		ret)
(00003FA9 3 152 0		_%err%)
(00003FAC 37 12		boxp)
(00003FAE 13 50 0		nil->JMP 00003FE3)
(00003FB1 3 152 0		_%err%)
(00003FB4 9 194 1		"VLMSG.DLL")
(00003FB7 51 176 119 0 0		30640)
(00003FBC 81 2 193 1 1 0		string-resource)
(00003FC2 5 1		UnVar1)
(00003FC4 44 7		IDFun7)
(00003FC6 81 1 106 0 1 0		princ-to-string)
(00003FCC 5 1		UnVar1)
(00003FCE 44 9		IDFun9)
(00003FD0 81 1 106 0 1 0		princ-to-string)
(00003FD6 81 3 191 1 1 0		_win-format-message)
(00003FDC 81 2 140 0 1 0		unbox<-)
(00003FE2 10)
(00003FE3 1		nil)
(00003FE4 22		ret)
;;;def option-checked-instantiate 16357
(00003FE5 21 4 4 4 0)
(00003FEA 15 25 0		JMP 00004006)
(00003FED 20 1 1 1 0)
(00003FF2 4 1 0		UpVar1-0)
(00003FF5 4 1 1		UpVar1-1)
(00003FF8 5 0		UnVar0)
(00003FFA 4 1 2		UpVar1-2)
(00003FFD 4 1 3		UpVar1-3)
(00004000 47 5 105 0 32 32		check-alert)
(00004006 12 235 1		'(16365 nil))
(00004009 22		ret)
;;;def option-reader-instantiate 16394
(0000400A 21 1 1 1 0)
(0000400F 5 0		UnVar0)
(00004011 37 3		symbolp)
(00004013 13 22 0		nil->JMP 0000402C)
(00004016 15 15 0		JMP 00004028)
(00004019 20 0 0 0 0)
(0000401E 4 1 0		UpVar1-0)
(00004021 81 1 133 0 1 0		symbol-value)
(00004027 22		ret)
(00004028 12 234 1		'(16409 nil))
(0000402B 22		ret)
(0000402C 5 0		UnVar0)
(0000402E 40		car)
(0000402F 22		ret)
;;;def option-some-of-accessor 16432
(00004030 20 4 2 2 1)
(00004035 100 3		UNVar3)
(00004037 5 0		UnVar0)
(00004039 95 1 161 53 0 0		accessed-value)
(0000403F 8 3		UnVar3)
(00004041 5 2		UnVar2)
(00004043 13 61 0		nil->JMP 00004083)
(00004046 5 2		UnVar2)
(00004048 40		car)
(00004049 13 33 0		nil->JMP 0000406D)
(0000404C 5 1		UnVar1)
(0000404E 5 3		UnVar3)
(00004050 81 2 184 1 1 0		member)
(00004056 13 3 0		nil->JMP 0000405C)
(00004059 15 14 0		JMP 0000406A)
(0000405C 5 0		UnVar0)
(0000405E 5 1		UnVar1)
(00004060 5 3		UnVar3)
(00004062 42		cons)
(00004063 95 2 209 53 0 0		accessed-value<-)
(00004069 10)
(0000406A 15 19 0		JMP 00004080)
(0000406D 5 0		UnVar0)
(0000406F 5 1		UnVar1)
(00004071 5 3		UnVar3)
(00004073 81 2 117 0 1 0		delete)
(00004079 95 2 209 53 0 0		accessed-value<-)
(0000407F 10)
(00004080 15 0 0		JMP 00004083)
(00004083 5 1		UnVar1)
(00004085 5 3		UnVar3)
(00004087 81 2 184 1 1 0		member)
(0000408D 22		ret)
;;;def option-some-of-intantiate 16526
(0000408E 21 2 2 2 0)
(00004093 15 23 0		JMP 000040AD)
(00004096 20 1 0 0 1)
(0000409B 9 233 1		'(16432 option-some-of-accessor))
(0000409E 4 1 0		UpVar1-0)
(000040A1 4 1 1		UpVar1-1)
(000040A4 5 0		UnVar0)
(000040A6 81 3 203 1 1 0		list*)
(000040AC 84		apply+ret)
(000040AD 12 232 1		'(16534 nil))
(000040B0 22		ret)
;;;def option-init-item-some-of 16561
(000040B1 20 14 3 7 0)
(000040B6 100 7		UNVar7)
(000040B8 5 3		UnVar3)
(000040BA 81 1 116 0 1 0		length)
(000040C0 5 2		UnVar2)
(000040C2 81 1 116 0 1 0		length)
(000040C8 81 2 175 1 1 0		=&)
(000040CE 13 3 0		nil->JMP 000040D4)
(000040D1 15 43 0		JMP 000040FF)
(000040D4 5 2		UnVar2)
(000040D6 8 8		UnVar8)
(000040D8 100 9		UNVar9)
(000040DA 15 19 0		JMP 000040F0)
(000040DD 5 8		UnVar8)
(000040DF 40		car)
(000040E0 81 1 106 0 1 0		princ-to-string)
(000040E6 5 9		UnVar9)
(000040E8 42		cons)
(000040E9 8 9		UnVar9)
(000040EB 5 8		UnVar8)
(000040ED 41		cdr)
(000040EE 8 8		UnVar8)
(000040F0 5 8		UnVar8)
(000040F2 60 232 255		T->JMP 000040DD)
(000040F5 5 9		UnVar9)
(000040F7 81 1 196 1 1 0		nreverse)
(000040FD 8 3		UnVar3)
(000040FF 5 5		UnVar5)
(00004101 81 1 116 0 1 0		length)
(00004107 5 2		UnVar2)
(00004109 81 1 116 0 1 0		length)
(0000410F 81 2 175 1 1 0		=&)
(00004115 13 3 0		nil->JMP 0000411B)
(00004118 15 4 0		JMP 0000411F)
(0000411B 5 3		UnVar3)
(0000411D 8 5		UnVar5)
(0000411F 5 3		UnVar3)
(00004121 8 8		UnVar8)
(00004123 5 2		UnVar2)
(00004125 8 9		UnVar9)
(00004127 5 5		UnVar5)
(00004129 8 10		UnVar10)
(0000412B 15 97 0		JMP 0000418F)
(0000412E 50 1		1)
(00004130 5 4		UnVar4)
(00004132 14 23 0		T->JMP 0000414C)
(00004135 50 12		12)
(00004137 50 4		4)
(00004139 5 8		UnVar8)
(0000413B 40		car)
(0000413C 81 1 184 0 1 0		string-length)
(00004142 72		*)
(00004143 70		+)
(00004144 50 12		12)
(00004146 81 2 54 1 1 0		make-ipoint)
(0000414C 5 1		UnVar1)
(0000414E 5 9		UnVar9)
(00004150 40		car)
(00004151 53 2 104 0 1 32		option-some-of-intantiate)
(00004157 57 1 0		list)
(0000415A 1		nil)
(0000415B 5 8		UnVar8)
(0000415D 40		car)
(0000415E 5 10		UnVar10)
(00004160 40		car)
(00004161 1		nil)
(00004162 5 6		UnVar6)
(00004164 95 7 248 58 0 0		accessed-check-box)
(0000416A 5 7		UnVar7)
(0000416C 81 3 203 1 1 0		list*)
(00004172 8 7		UnVar7)
(00004174 5 8		UnVar8)
(00004176 41		cdr)
(00004177 8 11		UnVar11)
(00004179 5 9		UnVar9)
(0000417B 41		cdr)
(0000417C 8 12		UnVar12)
(0000417E 5 10		UnVar10)
(00004180 41		cdr)
(00004181 8 13		UnVar13)
(00004183 5 11		UnVar11)
(00004185 8 8		UnVar8)
(00004187 5 12		UnVar12)
(00004189 8 9		UnVar9)
(0000418B 5 13		UnVar13)
(0000418D 8 10		UnVar10)
(0000418F 5 9		UnVar9)
(00004191 61 2 0		nil->JMP 00004196)
(00004194 5 8		UnVar8)
(00004196 60 149 255		T->JMP 0000412E)
(00004199 9 212 0		':GROUP)
(0000419C 5 0		UnVar0)
(0000419E 9 111 0		':H)
(000041A1 50 4		4)
(000041A3 9 103 0		':V)
(000041A6 50 1		1)
(000041A8 5 7		UnVar7)
(000041AA 81 1 196 1 1 0		nreverse)
(000041B0 81 3 203 1 1 0		list*)
(000041B6 57 3 0		list)
(000041B9 57 3 0		list)
(000041BC 22		ret)
;;;def copy-user-function 16829
(000041BD 20 1 1 1 0)
(000041C2 5 0		UnVar0)
(000041C4 37 10		xsubrp)
(000041C6 13 31 0		nil->JMP 000041E8)
(000041C9 5 0		UnVar0)
(000041CB 81 1 102 0 1 0		xsubr-module)
(000041D1 5 0		UnVar0)
(000041D3 81 1 101 0 1 0		xsubr-offs)
(000041D9 5 0		UnVar0)
(000041DB 81 1 100 0 1 0		_subr-name)
(000041E1 81 3 99 0 1 0		make-xsubr)
(000041E7 22		ret)
(000041E8 5 0		UnVar0)
(000041EA 37 11		closurep)
(000041EC 13 23 0		nil->JMP 00004206)
(000041EF 5 0		UnVar0)
(000041F1 81 1 98 0 1 0		closure-procedure)
(000041F7 5 0		UnVar0)
(000041F9 81 1 97 0 1 0		closure-environment)
(000041FF 81 2 96 0 1 0		make-closure)
(00004205 22		ret)
(00004206 5 0		UnVar0)
(00004208 37 2		consp)
(0000420A 61 7 0		nil->JMP 00004214)
(0000420D 9 95 0		'lambda)
(00004210 5 0		UnVar0)
(00004212 40		car)
(00004213 38		=)
(00004214 13 8 0		nil->JMP 0000421F)
(00004217 5 0		UnVar0)
(00004219 47 1 183 1 32 32		copy-list)
(0000421F 9 194 1		"VLMSG.DLL")
(00004222 51 210 95 0 0		24530)
(00004227 81 2 193 1 1 0		string-resource)
(0000422D 5 0		UnVar0)
(0000422F 81 2 123 1 1 0		_bat-err)
(00004235 22		ret)
;;;def option-init-item-one-of 16950
(00004236 20 14 3 7 0)
(0000423B 100 7		UNVar7)
(0000423D 5 3		UnVar3)
(0000423F 81 1 116 0 1 0		length)
(00004245 5 2		UnVar2)
(00004247 81 1 116 0 1 0		length)
(0000424D 81 2 175 1 1 0		=&)
(00004253 13 3 0		nil->JMP 00004259)
(00004256 15 43 0		JMP 00004284)
(00004259 5 2		UnVar2)
(0000425B 8 8		UnVar8)
(0000425D 100 9		UNVar9)
(0000425F 15 19 0		JMP 00004275)
(00004262 5 8		UnVar8)
(00004264 40		car)
(00004265 81 1 149 0 1 0		prin1-to-string)
(0000426B 5 9		UnVar9)
(0000426D 42		cons)
(0000426E 8 9		UnVar9)
(00004270 5 8		UnVar8)
(00004272 41		cdr)
(00004273 8 8		UnVar8)
(00004275 5 8		UnVar8)
(00004277 60 232 255		T->JMP 00004262)
(0000427A 5 9		UnVar9)
(0000427C 81 1 196 1 1 0		nreverse)
(00004282 8 3		UnVar3)
(00004284 5 3		UnVar3)
(00004286 81 1 116 0 1 0		length)
(0000428C 5 5		UnVar5)
(0000428E 81 1 116 0 1 0		length)
(00004294 81 2 175 1 1 0		=&)
(0000429A 13 3 0		nil->JMP 000042A0)
(0000429D 15 4 0		JMP 000042A4)
(000042A0 5 3		UnVar3)
(000042A2 8 5		UnVar5)
(000042A4 5 6		UnVar6)
(000042A6 13 3 0		nil->JMP 000042AC)
(000042A9 15 21 0		JMP 000042C1)
(000042AC 15 7 0		JMP 000042B6)
(000042AF 20 1 1 1 0)
(000042B4 1		nil)
(000042B5 22		ret)
(000042B6 9 231 1		'(17071 nil))
(000042B9 95 1 189 65 0 0		copy-user-function)
(000042BF 8 6		UnVar6)
(000042C1 5 3		UnVar3)
(000042C3 8 8		UnVar8)
(000042C5 5 2		UnVar2)
(000042C7 8 9		UnVar9)
(000042C9 5 5		UnVar5)
(000042CB 8 10		UnVar10)
(000042CD 15 87 0		JMP 00004327)
(000042D0 50 1		1)
(000042D2 5 4		UnVar4)
(000042D4 14 23 0		T->JMP 000042EE)
(000042D7 50 12		12)
(000042D9 50 4		4)
(000042DB 5 8		UnVar8)
(000042DD 40		car)
(000042DE 81 1 184 0 1 0		string-length)
(000042E4 72		*)
(000042E5 70		+)
(000042E6 50 12		12)
(000042E8 81 2 54 1 1 0		make-ipoint)
(000042EE 5 1		UnVar1)
(000042F0 5 9		UnVar9)
(000042F2 40		car)
(000042F3 5 6		UnVar6)
(000042F5 5 8		UnVar8)
(000042F7 40		car)
(000042F8 1		nil)
(000042F9 5 10		UnVar10)
(000042FB 40		car)
(000042FC 95 7 58 58 0 0		accessed-radio-button)
(00004302 5 7		UnVar7)
(00004304 81 3 203 1 1 0		list*)
(0000430A 8 7		UnVar7)
(0000430C 5 8		UnVar8)
(0000430E 41		cdr)
(0000430F 8 11		UnVar11)
(00004311 5 9		UnVar9)
(00004313 41		cdr)
(00004314 8 12		UnVar12)
(00004316 5 10		UnVar10)
(00004318 41		cdr)
(00004319 8 13		UnVar13)
(0000431B 5 11		UnVar11)
(0000431D 8 8		UnVar8)
(0000431F 5 12		UnVar12)
(00004321 8 9		UnVar9)
(00004323 5 13		UnVar13)
(00004325 8 10		UnVar10)
(00004327 5 9		UnVar9)
(00004329 61 2 0		nil->JMP 0000432E)
(0000432C 5 8		UnVar8)
(0000432E 60 159 255		T->JMP 000042D0)
(00004331 9 212 0		':GROUP)
(00004334 5 0		UnVar0)
(00004336 9 111 0		':H)
(00004339 50 2		2)
(0000433B 9 103 0		':V)
(0000433E 50 1		1)
(00004340 5 7		UnVar7)
(00004342 81 1 196 1 1 0		nreverse)
(00004348 81 3 203 1 1 0		list*)
(0000434E 57 3 0		list)
(00004351 57 3 0		list)
(00004354 22		ret)
;;;def option-init-item-flag 17237
(00004355 20 4 3 3 0)
(0000435A 100 3		UNVar3)
(0000435C 5 0		UnVar0)
(0000435E 14 2 0		T->JMP 00004363)
(00004361 5 2		UnVar2)
(00004363 8 3		UnVar3)
(00004365 50 12		12)
(00004367 50 4		4)
(00004369 5 3		UnVar3)
(0000436B 81 1 184 0 1 0		string-length)
(00004371 72		*)
(00004372 70		+)
(00004373 50 10		10)
(00004375 81 2 54 1 1 0		make-ipoint)
(0000437B 5 1		UnVar1)
(0000437D 1		nil)
(0000437E 5 3		UnVar3)
(00004380 5 0		UnVar0)
(00004382 61 2 0		nil->JMP 00004387)
(00004385 5 2		UnVar2)
(00004387 96 5 248 58 0 0		accessed-check-box)
;;;def option-init-an-item 17293
(0000438D 20 5 3 3 1)
(00004392 5 3		UnVar3)
(00004394 40		car)
(00004395 8 4		UnVar4)
(00004397 5 4		UnVar4)
(00004399 9 94 0		':CHECKED)
(0000439C 38		=)
(0000439D 13 21 0		nil->JMP 000043B5)
(000043A0 5 1		UnVar1)
(000043A2 5 0		UnVar0)
(000043A4 5 2		UnVar2)
(000043A6 5 3		UnVar3)
(000043A8 41		cdr)
(000043A9 40		car)
(000043AA 5 3		UnVar3)
(000043AC 41		cdr)
(000043AD 41		cdr)
(000043AE 40		car)
(000043AF 97 5 75 63 0 0		offset 00003F4B)
(000043B5 5 4		UnVar4)
(000043B7 9 93 0		':FLAG)
(000043BA 38		=)
(000043BB 13 12 0		nil->JMP 000043CA)
(000043BE 5 1		UnVar1)
(000043C0 5 0		UnVar0)
(000043C2 5 2		UnVar2)
(000043C4 97 3 90 67 0 0		offset 0000435A)
(000043CA 5 4		UnVar4)
(000043CC 9 92 0		':ONE-OF)
(000043CF 38		=)
(000043D0 13 17 0		nil->JMP 000043E4)
(000043D3 9 230 1		'(16950 option-init-item-one-of))
(000043D6 5 1		UnVar1)
(000043D8 5 0		UnVar0)
(000043DA 5 3		UnVar3)
(000043DC 41		cdr)
(000043DD 81 3 203 1 1 0		list*)
(000043E3 84		apply+ret)
(000043E4 5 4		UnVar4)
(000043E6 9 91 0		':SOME-OF)
(000043E9 38		=)
(000043EA 13 17 0		nil->JMP 000043FE)
(000043ED 9 229 1		'(16561 option-init-item-some-of))
(000043F0 5 1		UnVar1)
(000043F2 5 0		UnVar0)
(000043F4 5 3		UnVar3)
(000043F6 41		cdr)
(000043F7 81 3 203 1 1 0		list*)
(000043FD 84		apply+ret)
(000043FE 5 4		UnVar4)
(00004400 9 90 0		':STRING)
(00004403 38		=)
(00004404 13 12 0		nil->JMP 00004413)
(00004407 5 1		UnVar1)
(00004409 5 0		UnVar0)
(0000440B 5 2		UnVar2)
(0000440D 97 3 119 62 0 0		offset 00003E77)
(00004413 5 3		UnVar3)
(00004415 35		not)
(00004416 9 89 0		"Bad syntax of varslist-dialog!")
(00004419 5 0		UnVar0)
(0000441B 5 1		UnVar1)
(0000441D 9 148 0		"...")
(00004420 53 5 66 1 1 32		assert)
(00004426 10)
(00004427 5 1		UnVar1)
(00004429 5 0		UnVar0)
(0000442B 5 2		UnVar2)
(0000442D 97 3 9 62 0 0		offset 00003E09)
;;;def nil 17459
(00004433 20 2 0 0 0)
(00004438 100 0		UNVar0)
(0000443A 100 1		UNVar1)
(0000443C 95 0 232 4 0 0		_W-BORDER)
(00004442 8 1		UnVar1)
(00004444 81 0 255 0 1 0		_screen-size)
(0000444A 8 0		UnVar0)
(0000444C 5 1		UnVar1)
(0000444E 5 1		UnVar1)
(00004450 81 2 54 1 1 0		make-ipoint)
(00004456 5 0		UnVar0)
(00004458 81 1 58 1 1 0		ipoint-h)
(0000445E 50 2		2)
(00004460 72		*)
(00004461 50 3		3)
(00004463 73		/)
(00004464 5 0		UnVar0)
(00004466 81 1 57 1 1 0		ipoint-v)
(0000446C 50 2		2)
(0000446E 73		/)
(0000446F 81 2 54 1 1 0		make-ipoint)
(00004475 42		cons)
(00004476 22		ret)
;;;def varslist->dialog 17527
(00004477 20 14 2 5 0)
(0000447C 100 5		UNVar5)
(0000447E 100 6		UNVar6)
(00004480 5 1		UnVar1)
(00004482 8 7		UnVar7)
(00004484 100 8		UNVar8)
(00004486 15 182 0		JMP 0000453F)
(00004489 5 7		UnVar7)
(0000448B 40		car)
(0000448C 8 8		UnVar8)
(0000448E 5 7		UnVar7)
(00004490 41		cdr)
(00004491 8 7		UnVar7)
(00004493 100 6		UNVar6)
(00004495 5 8		UnVar8)
(00004497 37 2		consp)
(00004499 61 5 0		nil->JMP 000044A1)
(0000449C 5 8		UnVar8)
(0000449E 41		cdr)
(0000449F 37 2		consp)
(000044A1 13 121 0		nil->JMP 0000451D)
(000044A4 5 8		UnVar8)
(000044A6 40		car)
(000044A7 9 212 0		':GROUP)
(000044AA 38		=)
(000044AB 13 88 0		nil->JMP 00004506)
(000044AE 5 8		UnVar8)
(000044B0 41		cdr)
(000044B1 40		car)
(000044B2 8 9		UnVar9)
(000044B4 5 8		UnVar8)
(000044B6 41		cdr)
(000044B7 41		cdr)
(000044B8 8 10		UnVar10)
(000044BA 5 10		UnVar10)
(000044BC 8 11		UnVar11)
(000044BE 100 12		UNVar12)
(000044C0 15 31 0		JMP 000044E2)
(000044C3 5 12		UnVar12)
(000044C5 5 11		UnVar11)
(000044C7 40		car)
(000044C8 8 13		UnVar13)
(000044CA 50 1		1)
(000044CC 9 228 1		'(17293 option-init-an-item))
(000044CF 5 13		UnVar13)
(000044D1 83		apply)
(000044D2 57 2 0		list)
(000044D5 81 2 195 1 1 0		nconc)
(000044DB 8 12		UnVar12)
(000044DD 5 11		UnVar11)
(000044DF 41		cdr)
(000044E0 8 11		UnVar11)
(000044E2 5 11		UnVar11)
(000044E4 60 220 255		T->JMP 000044C3)
(000044E7 5 12		UnVar12)
(000044E9 8 6		UnVar6)
(000044EB 9 212 0		':GROUP)
(000044EE 5 9		UnVar9)
(000044F0 9 111 0		':H)
(000044F3 50 2		2)
(000044F5 9 103 0		':V)
(000044F8 5 6		UnVar6)
(000044FA 42		cons)
(000044FB 57 3 0		list)
(000044FE 57 3 0		list)
(00004501 8 6		UnVar6)
(00004503 15 20 0		JMP 0000451A)
(00004506 5 8		UnVar8)
(00004508 41		cdr)
(00004509 41		cdr)
(0000450A 37 2		consp)
(0000450C 13 11 0		nil->JMP 0000451A)
(0000450F 9 228 1		'(17293 option-init-an-item))
(00004512 5 8		UnVar8)
(00004514 83		apply)
(00004515 8 6		UnVar6)
(00004517 15 0 0		JMP 0000451A)
(0000451A 15 0 0		JMP 0000451D)
(0000451D 5 6		UnVar6)
(0000451F 13 17 0		nil->JMP 00004533)
(00004522 50 2		2)
(00004524 5 6		UnVar6)
(00004526 5 5		UnVar5)
(00004528 81 3 203 1 1 0		list*)
(0000452E 8 5		UnVar5)
(00004530 15 12 0		JMP 0000453F)
(00004533 9 89 0		"Bad syntax of varslist-dialog!")
(00004536 5 8		UnVar8)
(00004538 53 2 166 0 1 32		error)
(0000453E 10)
(0000453F 5 7		UnVar7)
(00004541 60 69 255		T->JMP 00004489)
(00004544 3 88 0		*options-cascade*)
(00004547 95 1 86 23 0 0		dcascade-apex)
(0000454D 5 2		UnVar2)
(0000454F 5 0		UnVar0)
(00004551 9 220 0		':VC)
(00004554 50 4		4)
(00004556 9 111 0		':H)
(00004559 50 4		4)
(0000455B 9 103 0		':V)
(0000455E 5 5		UnVar5)
(00004560 81 1 196 1 1 0		nreverse)
(00004566 42		cons)
(00004567 50 5		5)
(00004569 57 4 0		list)
(0000456C 50 4		4)
(0000456E 9 111 0		':H)
(00004571 3 87 0		*parms-dialog-ok-button*)
(00004574 50 10		10)
(00004576 3 86 0		*parms-dialog-cancel-button*)
(00004579 57 4 0		list)
(0000457C 50 4		4)
(0000457E 57 6 0		list)
(00004581 9 71 1		':DEFAULT-PUSH-BUTTON)
(00004584 3 87 0		*parms-dialog-ok-button*)
(00004587 9 72 1		':PARENT)
(0000458A 5 4		UnVar4)
(0000458C 9 75 1		':FONT)
(0000458F 3 85 0		*inspector-font*)
(00004592 9 73 1		':PITCH)
(00004595 3 84 0		*inspector-pitch*)
(00004598 9 170 0		':STATUS)
(0000459B 5 3		UnVar3)
(0000459D 96 14 50 49 0 0		dialog-fmt)
;;;def varslist->tabbed-dialog 17827
(000045A3 20 16 1 4 0)
(000045A8 100 4		UNVar4)
(000045AA 100 5		UNVar5)
(000045AC 5 0		UnVar0)
(000045AE 8 6		UnVar6)
(000045B0 100 7		UNVar7)
(000045B2 15 36 1		JMP 000046D9)
(000045B5 5 6		UnVar6)
(000045B7 40		car)
(000045B8 8 8		UnVar8)
(000045BA 5 8		UnVar8)
(000045BC 41		cdr)
(000045BD 8 9		UnVar9)
(000045BF 100 10		UNVar10)
(000045C1 15 182 0		JMP 0000467A)
(000045C4 5 9		UnVar9)
(000045C6 40		car)
(000045C7 8 10		UnVar10)
(000045C9 5 9		UnVar9)
(000045CB 41		cdr)
(000045CC 8 9		UnVar9)
(000045CE 100 5		UNVar5)
(000045D0 5 10		UnVar10)
(000045D2 37 2		consp)
(000045D4 61 5 0		nil->JMP 000045DC)
(000045D7 5 10		UnVar10)
(000045D9 41		cdr)
(000045DA 37 2		consp)
(000045DC 13 121 0		nil->JMP 00004658)
(000045DF 5 10		UnVar10)
(000045E1 40		car)
(000045E2 9 212 0		':GROUP)
(000045E5 38		=)
(000045E6 13 88 0		nil->JMP 00004641)
(000045E9 5 10		UnVar10)
(000045EB 41		cdr)
(000045EC 40		car)
(000045ED 8 11		UnVar11)
(000045EF 5 10		UnVar10)
(000045F1 41		cdr)
(000045F2 41		cdr)
(000045F3 8 12		UnVar12)
(000045F5 5 12		UnVar12)
(000045F7 8 13		UnVar13)
(000045F9 100 14		UNVar14)
(000045FB 15 31 0		JMP 0000461D)
(000045FE 5 14		UnVar14)
(00004600 5 13		UnVar13)
(00004602 40		car)
(00004603 8 15		UnVar15)
(00004605 50 1		1)
(00004607 9 228 1		'(17293 option-init-an-item))
(0000460A 5 15		UnVar15)
(0000460C 83		apply)
(0000460D 57 2 0		list)
(00004610 81 2 195 1 1 0		nconc)
(00004616 8 14		UnVar14)
(00004618 5 13		UnVar13)
(0000461A 41		cdr)
(0000461B 8 13		UnVar13)
(0000461D 5 13		UnVar13)
(0000461F 60 220 255		T->JMP 000045FE)
(00004622 5 14		UnVar14)
(00004624 8 5		UnVar5)
(00004626 9 212 0		':GROUP)
(00004629 5 11		UnVar11)
(0000462B 9 111 0		':H)
(0000462E 50 2		2)
(00004630 9 103 0		':V)
(00004633 5 5		UnVar5)
(00004635 42		cons)
(00004636 57 3 0		list)
(00004639 57 3 0		list)
(0000463C 8 5		UnVar5)
(0000463E 15 20 0		JMP 00004655)
(00004641 5 10		UnVar10)
(00004643 41		cdr)
(00004644 41		cdr)
(00004645 37 2		consp)
(00004647 13 11 0		nil->JMP 00004655)
(0000464A 9 228 1		'(17293 option-init-an-item))
(0000464D 5 10		UnVar10)
(0000464F 83		apply)
(00004650 8 5		UnVar5)
(00004652 15 0 0		JMP 00004655)
(00004655 15 0 0		JMP 00004658)
(00004658 5 5		UnVar5)
(0000465A 13 17 0		nil->JMP 0000466E)
(0000465D 50 2		2)
(0000465F 5 5		UnVar5)
(00004661 5 4		UnVar4)
(00004663 81 3 203 1 1 0		list*)
(00004669 8 4		UnVar4)
(0000466B 15 12 0		JMP 0000467A)
(0000466E 9 89 0		"Bad syntax of varslist-dialog!")
(00004671 5 10		UnVar10)
(00004673 53 2 166 0 1 32		error)
(00004679 10)
(0000467A 5 9		UnVar9)
(0000467C 60 69 255		T->JMP 000045C4)
(0000467F 3 88 0		*options-cascade*)
(00004682 95 1 86 23 0 0		dcascade-apex)
(00004688 5 1		UnVar1)
(0000468A 5 8		UnVar8)
(0000468C 40		car)
(0000468D 9 220 0		':VC)
(00004690 50 4		4)
(00004692 9 111 0		':H)
(00004695 50 4		4)
(00004697 9 103 0		':V)
(0000469A 5 4		UnVar4)
(0000469C 81 1 196 1 1 0		nreverse)
(000046A2 42		cons)
(000046A3 50 5		5)
(000046A5 57 4 0		list)
(000046A8 50 4		4)
(000046AA 57 4 0		list)
(000046AD 9 71 1		':DEFAULT-PUSH-BUTTON)
(000046B0 3 87 0		*parms-dialog-ok-button*)
(000046B3 9 72 1		':PARENT)
(000046B6 5 3		UnVar3)
(000046B8 9 75 1		':FONT)
(000046BB 3 85 0		*inspector-font*)
(000046BE 9 73 1		':PITCH)
(000046C1 3 84 0		*inspector-pitch*)
(000046C4 9 170 0		':STATUS)
(000046C7 5 2		UnVar2)
(000046C9 95 14 50 49 0 0		dialog-fmt)
(000046CF 5 7		UnVar7)
(000046D1 42		cons)
(000046D2 8 7		UnVar7)
(000046D4 5 6		UnVar6)
(000046D6 41		cdr)
(000046D7 8 6		UnVar6)
(000046D9 5 6		UnVar6)
(000046DB 60 215 254		T->JMP 000045B5)
(000046DE 5 7		UnVar7)
(000046E0 81 1 196 1 1 0		nreverse)
(000046E6 22		ret)
;;;def _eval-string-p 18151
(000046E7 20 5 4 4 0)
(000046EC 100 4		UNVar4)
(000046EE 5 3		UnVar3)
(000046F0 37 12		boxp)
(000046F2 9 139 0		"Bad _err handler value!")
(000046F5 53 2 66 1 1 32		assert)
(000046FB 10)
(000046FC 5 2		UnVar2)
(000046FE 53 1 83 0 1 32		_fine-stringp)
(00004704 13 3 0		nil->JMP 0000470A)
(00004707 5 2		UnVar2)
(00004709 22		ret)
(0000470A 5 3		UnVar3)
(0000470C 9 194 1		"VLMSG.DLL")
(0000470F 51 220 95 0 0		24540)
(00004714 81 2 193 1 1 0		string-resource)
(0000471A 81 2 140 0 1 0		unbox<-)
(00004720 10)
(00004721 5 0		UnVar0)
(00004723 6 15 1		_%reinput%)
(00004726 5 3		UnVar3)
(00004728 22		ret)
;;;def vars-dialog-list-dialog 18217
(00004729 21 19 3 3 1)
(0000472E 5 3		UnVar3)
(00004730 8 4		UnVar4)
(00004732 5 4		UnVar4)
(00004734 9 82 0		':STR)
(00004737 1		nil)
(00004738 81 3 74 1 1 0		getf)
(0000473E 8 5		UnVar5)
(00004740 5 4		UnVar4)
(00004742 9 81 0		':ORD)
(00004745 1		nil)
(00004746 81 3 74 1 1 0		getf)
(0000474C 8 6		UnVar6)
(0000474E 5 4		UnVar4)
(00004750 9 80 0		':SIZE)
(00004753 1		nil)
(00004754 81 3 74 1 1 0		getf)
(0000475A 8 7		UnVar7)
(0000475C 5 4		UnVar4)
(0000475E 9 79 0		':EVAL)
(00004761 1		nil)
(00004762 81 3 74 1 1 0		getf)
(00004768 8 8		UnVar8)
(0000476A 5 4		UnVar4)
(0000476C 9 170 0		':STATUS)
(0000476F 1		nil)
(00004770 81 3 74 1 1 0		getf)
(00004776 8 9		UnVar9)
(00004778 5 4		UnVar4)
(0000477A 9 72 1		':PARENT)
(0000477D 1		nil)
(0000477E 81 3 74 1 1 0		getf)
(00004784 8 10		UnVar10)
(00004786 100 11		UNVar11)
(00004788 100 12		UNVar12)
(0000478A 100 13		UNVar13)
(0000478C 100 14		UNVar14)
(0000478E 100 15		UNVar15)
(00004790 100 16		UNVar16)
(00004792 100 17		UNVar17)
(00004794 100 18		UNVar18)
(00004796 3 78 0		*vars-dialog-popup-menu*)
(00004799 13 3 0		nil->JMP 0000479F)
(0000479C 15 7 0		JMP 000047A6)
(0000479F 95 0 80 74 0 0		func 00004A50)
(000047A5 10)
(000047A6 5 7		UnVar7)
(000047A8 13 11 0		nil->JMP 000047B6)
(000047AB 5 7		UnVar7)
(000047AD 81 1 58 1 1 0		ipoint-h)
(000047B3 15 2 0		JMP 000047B8)
(000047B6 50 100		100)
(000047B8 8 14		UnVar14)
(000047BA 5 5		UnVar5)
(000047BC 13 59 0		nil->JMP 000047FA)
(000047BF 5 14		UnVar14)
(000047C1 50 12		12)
(000047C3 81 2 54 1 1 0		make-ipoint)
(000047C9 9 77 0		'*mds-expr*)
(000047CC 9 194 1		"VLMSG.DLL")
(000047CF 51 186 119 0 0		30650)
(000047D4 81 2 193 1 1 0		string-resource)
(000047DA 5 2		UnVar2)
(000047DC 81 1 192 1 1 0		string)
(000047E2 81 2 191 1 1 0		_win-format-message)
(000047E8 1		nil)
(000047E9 5 8		UnVar8)
(000047EB 14 3 0		T->JMP 000047F1)
(000047EE 9 227 1		'(18151 _eval-string-p))
(000047F1 95 5 90 56 0 0		accessed-editable-string)
(000047F7 15 50 0		JMP 0000482C)
(000047FA 5 14		UnVar14)
(000047FC 50 12		12)
(000047FE 81 2 54 1 1 0		make-ipoint)
(00004804 9 77 0		'*mds-expr*)
(00004807 9 194 1		"VLMSG.DLL")
(0000480A 51 186 119 0 0		30650)
(0000480F 81 2 193 1 1 0		string-resource)
(00004815 5 2		UnVar2)
(00004817 81 1 192 1 1 0		string)
(0000481D 81 2 191 1 1 0		_win-format-message)
(00004823 1		nil)
(00004824 5 8		UnVar8)
(00004826 95 5 20 57 0 0		accessed-editable-text)
(0000482C 8 12		UnVar12)
(0000482E 5 5		UnVar5)
(00004830 13 91 0		nil->JMP 0000488E)
(00004833 5 7		UnVar7)
(00004835 14 5 0		T->JMP 0000483D)
(00004838 51 100 0 120 0		7864420)
(0000483D 9 76 0		'(("Quux")))
(00004840 9 75 0		':MULTIPLE-SELECTION)
(00004843 2		T)
(00004844 9 112 1		':COMMAND)
(00004847 15 19 0		JMP 0000485D)
(0000484A 20 1 1 1 0)
(0000484F 5 0		UnVar0)
(00004851 4 1 5		UpVar1-5)
(00004854 4 1 6		UpVar1-6)
(00004857 47 3 74 0 32 32		_vars-dialog-track-menu)
(0000485D 12 226 1		'(18506 nil))
(00004860 9 73 0		':SORT-P)
(00004863 5 6		UnVar6)
(00004865 35		not)
(00004866 9 72 0		':PROMPT)
(00004869 9 194 1		"VLMSG.DLL")
(0000486C 51 196 119 0 0		30660)
(00004871 81 2 193 1 1 0		string-resource)
(00004877 5 2		UnVar2)
(00004879 81 1 192 1 1 0		string)
(0000487F 81 2 191 1 1 0		_win-format-message)
(00004885 95 10 42 96 0 0		sorted-list-box)
(0000488B 15 88 0		JMP 000048E6)
(0000488E 5 7		UnVar7)
(00004890 14 5 0		T->JMP 00004898)
(00004893 51 100 0 120 0		7864420)
(00004898 9 76 0		'(("Quux")))
(0000489B 9 75 0		':MULTIPLE-SELECTION)
(0000489E 2		T)
(0000489F 9 112 1		':COMMAND)
(000048A2 15 19 0		JMP 000048B8)
(000048A5 20 1 1 1 0)
(000048AA 5 0		UnVar0)
(000048AC 4 1 5		UpVar1-5)
(000048AF 4 1 6		UpVar1-6)
(000048B2 47 3 74 0 32 32		_vars-dialog-track-menu)
(000048B8 12 225 1		'(18597 nil))
(000048BB 9 71 0		':SORT)
(000048BE 5 6		UnVar6)
(000048C0 35		not)
(000048C1 9 72 0		':PROMPT)
(000048C4 9 194 1		"VLMSG.DLL")
(000048C7 51 196 119 0 0		30660)
(000048CC 81 2 193 1 1 0		string-resource)
(000048D2 5 2		UnVar2)
(000048D4 81 1 192 1 1 0		string)
(000048DA 81 2 191 1 1 0		_win-format-message)
(000048E0 95 10 52 98 0 0		shaded-list-box)
(000048E6 8 13		UnVar13)
(000048E8 51 33 0 12 0		786465)
(000048ED 9 194 1		"VLMSG.DLL")
(000048F0 51 250 95 0 0		24570)
(000048F5 81 2 193 1 1 0		string-resource)
(000048FB 15 19 0		JMP 00004911)
(000048FE 20 1 1 1 0)
(00004903 5 0		UnVar0)
(00004905 4 1 5		UpVar1-5)
(00004908 4 1 6		UpVar1-6)
(0000490B 96 3 245 75 0 0		func 00004BF5)
(00004911 12 224 1		'(18686 nil))
(00004914 9 194 1		"VLMSG.DLL")
(00004917 51 4 96 0 0		24580)
(0000491C 81 2 193 1 1 0		string-resource)
(00004922 95 4 44 18 0 0		push-button)
(00004928 8 15		UnVar15)
(0000492A 51 33 0 12 0		786465)
(0000492F 9 194 1		"VLMSG.DLL")
(00004932 51 14 96 0 0		24590)
(00004937 81 2 193 1 1 0		string-resource)
(0000493D 9 223 1		'(19609 _del-items-from-list))
(00004940 9 194 1		"VLMSG.DLL")
(00004943 51 24 96 0 0		24600)
(00004948 81 2 193 1 1 0		string-resource)
(0000494E 95 4 44 18 0 0		push-button)
(00004954 8 16		UnVar16)
(00004956 51 33 0 12 0		786465)
(0000495B 9 194 1		"VLMSG.DLL")
(0000495E 51 84 61 0 0		15700)
(00004963 81 2 193 1 1 0		string-resource)
(00004969 15 22 0		JMP 00004982)
(0000496C 20 1 1 1 0)
(00004971 5 0		UnVar0)
(00004973 4 1 1		UpVar1-1)
(00004976 4 1 5		UpVar1-5)
(00004979 4 1 6		UpVar1-6)
(0000497C 96 4 209 76 0 0		func 00004CD1)
(00004982 12 222 1		'(18796 nil))
(00004985 9 194 1		"VLMSG.DLL")
(00004988 51 34 96 0 0		24610)
(0000498D 81 2 193 1 1 0		string-resource)
(00004993 95 4 44 18 0 0		push-button)
(00004999 8 17		UnVar17)
(0000499B 51 33 0 12 0		786465)
(000049A0 9 194 1		"VLMSG.DLL")
(000049A3 51 228 82 0 0		21220)
(000049A8 81 2 193 1 1 0		string-resource)
(000049AE 9 221 1		'(197 destroy-host-spouse))
(000049B1 9 194 1		"VLMSG.DLL")
(000049B4 51 44 96 0 0		24620)
(000049B9 81 2 193 1 1 0		string-resource)
(000049BF 95 4 44 18 0 0		push-button)
(000049C5 8 18		UnVar18)
(000049C7 1		nil)
(000049C8 1		nil)
(000049C9 5 0		UnVar0)
(000049CB 9 111 0		':H)
(000049CE 50 2		2)
(000049D0 9 103 0		':V)
(000049D3 50 2		2)
(000049D5 5 12		UnVar12)
(000049D7 50 2		2)
(000049D9 5 13		UnVar13)
(000049DB 50 2		2)
(000049DD 57 6 0		list)
(000049E0 50 4		4)
(000049E2 9 103 0		':V)
(000049E5 50 4		4)
(000049E7 5 15		UnVar15)
(000049E9 50 4		4)
(000049EB 5 16		UnVar16)
(000049ED 50 4		4)
(000049EF 5 17		UnVar17)
(000049F1 50 4		4)
(000049F3 5 18		UnVar18)
(000049F5 50 4		4)
(000049F7 57 10 0		list)
(000049FA 50 2		2)
(000049FC 57 6 0		list)
(000049FF 9 157 0		':LABELS)
(00004A02 9 70 0		':SHOW-LIST)
(00004A05 5 13		UnVar13)
(00004A07 9 69 0		':ADD-BOX)
(00004A0A 5 12		UnVar12)
(00004A0C 57 4 0		list)
(00004A0F 9 71 1		':DEFAULT-PUSH-BUTTON)
(00004A12 5 17		UnVar17)
(00004A14 9 72 1		':PARENT)
(00004A17 5 10		UnVar10)
(00004A19 9 75 1		':FONT)
(00004A1C 3 85 0		*inspector-font*)
(00004A1F 9 73 1		':PITCH)
(00004A22 3 84 0		*inspector-pitch*)
(00004A25 9 170 0		':STATUS)
(00004A28 5 9		UnVar9)
(00004A2A 14 2 0		T->JMP 00004A2F)
(00004A2D 50 1		1)
(00004A2F 95 16 50 49 0 0		dialog-fmt)
(00004A35 8 11		UnVar11)
(00004A37 5 13		UnVar13)
(00004A39 5 1		UnVar1)
(00004A3B 95 1 161 53 0 0		accessed-value)
(00004A41 95 2 170 88 0 0		list-box-contents<-)
(00004A47 10)
(00004A48 5 11		UnVar11)
(00004A4A 47 1 177 0 32 32		modal-dialog!!)
;;;def nil 19024
(00004A50 20 0 0 0 0)
(00004A55 9 194 1		"VLMSG.DLL")
(00004A58 51 54 96 0 0		24630)
(00004A5D 81 2 193 1 1 0		string-resource)
(00004A63 9 150 1		"")
(00004A66 53 2 68 0 1 32		menu)
(00004A6C 6 78 0		*vars-dialog-popup-menu*)
(00004A6F 9 194 1		"VLMSG.DLL")
(00004A72 51 64 96 0 0		24640)
(00004A77 81 2 193 1 1 0		string-resource)
(00004A7D 1		nil)
(00004A7E 9 194 1		"VLMSG.DLL")
(00004A81 51 74 96 0 0		24650)
(00004A86 81 2 193 1 1 0		string-resource)
(00004A8C 53 3 67 0 1 32		menu-item)
(00004A92 6 66 0		*vars-dialog-add-before-menu-item*)
(00004A95 9 194 1		"VLMSG.DLL")
(00004A98 51 84 96 0 0		24660)
(00004A9D 81 2 193 1 1 0		string-resource)
(00004AA3 9 194 1		"VLMSG.DLL")
(00004AA6 51 94 96 0 0		24670)
(00004AAB 81 2 193 1 1 0		string-resource)
(00004AB1 53 2 67 0 1 32		menu-item)
(00004AB7 6 65 0		*vars-dialog-add-after-menu-item*)
(00004ABA 9 194 1		"VLMSG.DLL")
(00004ABD 51 104 96 0 0		24680)
(00004AC2 81 2 193 1 1 0		string-resource)
(00004AC8 15 47 0		JMP 00004AFA)
(00004ACB 20 4 1 1 0)
(00004AD0 5 0		UnVar0)
(00004AD2 8 1		UnVar1)
(00004AD4 5 1		UnVar1)
(00004AD6 44 11		IDFun11)
(00004AD8 8 2		UnVar2)
(00004ADA 5 1		UnVar1)
(00004ADC 5 2		UnVar2)
(00004ADE 9 70 0		':SHOW-LIST)
(00004AE1 53 3 164 0 1 32		_label-getf)
(00004AE7 8 3		UnVar3)
(00004AE9 5 3		UnVar3)
(00004AEB 95 1 110 90 0 0		list-box-select-all)
(00004AF1 10)
(00004AF2 5 3		UnVar3)
(00004AF4 96 1 67 0 0 0		update-host-spouse)
(00004AFA 9 220 1		'(19147 nil))
(00004AFD 9 194 1		"VLMSG.DLL")
(00004B00 51 114 96 0 0		24690)
(00004B05 81 2 193 1 1 0		string-resource)
(00004B0B 53 3 67 0 1 32		menu-item)
(00004B11 11)
(00004B12 6 64 0		*vars-dialog-select-all-menu-item*)
(00004B15 22		ret)
;;;def _vars-dialog-track-menu 19222
(00004B16 21 7 3 3 0)
(00004B1B 5 0		UnVar0)
(00004B1D 8 3		UnVar3)
(00004B1F 5 3		UnVar3)
(00004B21 44 11		IDFun11)
(00004B23 8 4		UnVar4)
(00004B25 5 3		UnVar3)
(00004B27 5 4		UnVar4)
(00004B29 9 70 0		':SHOW-LIST)
(00004B2C 53 3 164 0 1 32		_label-getf)
(00004B32 8 5		UnVar5)
(00004B34 5 3		UnVar3)
(00004B36 5 4		UnVar4)
(00004B38 9 69 0		':ADD-BOX)
(00004B3B 53 3 164 0 1 32		_label-getf)
(00004B41 8 6		UnVar6)
(00004B43 5 2		UnVar2)
(00004B45 61 25 0		nil->JMP 00004B61)
(00004B48 5 5		UnVar5)
(00004B4A 95 1 97 87 0 0		list-box-selection)
(00004B50 61 14 0		nil->JMP 00004B61)
(00004B53 5 6		UnVar6)
(00004B55 95 1 134 54 0 0		editable-text.text)
(00004B5B 53 1 83 0 1 32		_fine-stringp)
(00004B61 13 114 0		nil->JMP 00004BD6)
(00004B64 3 66 0		*vars-dialog-add-before-menu-item*)
(00004B67 15 19 0		JMP 00004B7D)
(00004B6A 20 1 1 1 0)
(00004B6F 5 0		UnVar0)
(00004B71 4 1 1		UpVar1-1)
(00004B74 4 1 2		UpVar1-2)
(00004B77 96 3 245 75 0 0		func 00004BF5)
(00004B7D 12 219 1		'(19306 nil))
(00004B80 9 224 0		'command)
(00004B83 81 3 239 0 1 0		slot-value<-)
(00004B89 10)
(00004B8A 3 65 0		*vars-dialog-add-after-menu-item*)
(00004B8D 15 20 0		JMP 00004BA4)
(00004B90 20 1 1 1 0)
(00004B95 5 0		UnVar0)
(00004B97 4 1 1		UpVar1-1)
(00004B9A 4 1 2		UpVar1-2)
(00004B9D 2		T)
(00004B9E 96 4 245 75 0 0		func 00004BF5)
(00004BA4 12 218 1		'(19344 nil))
(00004BA7 9 224 0		'command)
(00004BAA 81 3 239 0 1 0		slot-value<-)
(00004BB0 10)
(00004BB1 3 78 0		*vars-dialog-popup-menu*)
(00004BB4 3 66 0		*vars-dialog-add-before-menu-item*)
(00004BB7 3 65 0		*vars-dialog-add-after-menu-item*)
(00004BBA 3 64 0		*vars-dialog-select-all-menu-item*)
(00004BBD 57 3 0		list)
(00004BC0 9 225 0		'items)
(00004BC3 81 3 239 0 1 0		slot-value<-)
(00004BC9 10)
(00004BCA 3 78 0		*vars-dialog-popup-menu*)
(00004BCD 5 0		UnVar0)
(00004BCF 81 2 63 0 1 0		track-popup-menu)
(00004BD5 22		ret)
(00004BD6 3 78 0		*vars-dialog-popup-menu*)
(00004BD9 3 64 0		*vars-dialog-select-all-menu-item*)
(00004BDC 57 1 0		list)
(00004BDF 9 225 0		'items)
(00004BE2 81 3 239 0 1 0		slot-value<-)
(00004BE8 10)
(00004BE9 3 78 0		*vars-dialog-popup-menu*)
(00004BEC 5 0		UnVar0)
(00004BEE 81 2 63 0 1 0		track-popup-menu)
(00004BF4 22		ret)
;;;def nil 19445
(00004BF5 20 11 3 4 0)
(00004BFA 100 4		UNVar4)
(00004BFC 100 5		UNVar5)
(00004BFE 100 6		UNVar6)
(00004C00 9 77 0		'*mds-expr*)
(00004C03 3 152 0		_%err%)
(00004C06 24 2 0)
(00004C09 5 0		UnVar0)
(00004C0B 95 1 131 49 0 0		verified-sync-down)
(00004C11 13 4 0		nil->JMP 00004C18)
(00004C14 1		nil)
(00004C15 15 125 0		JMP 00004C95)
(00004C18 5 0		UnVar0)
(00004C1A 8 7		UnVar7)
(00004C1C 5 7		UnVar7)
(00004C1E 44 11		IDFun11)
(00004C20 8 8		UnVar8)
(00004C22 5 7		UnVar7)
(00004C24 5 8		UnVar8)
(00004C26 9 70 0		':SHOW-LIST)
(00004C29 53 3 164 0 1 32		_label-getf)
(00004C2F 8 9		UnVar9)
(00004C31 5 7		UnVar7)
(00004C33 5 8		UnVar8)
(00004C35 9 69 0		':ADD-BOX)
(00004C38 53 3 164 0 1 32		_label-getf)
(00004C3E 8 10		UnVar10)
(00004C40 5 9		UnVar9)
(00004C42 3 77 0		*mds-expr*)
(00004C45 57 1 0		list)
(00004C48 5 3		UnVar3)
(00004C4A 95 3 237 87 0 0		list-box-add-items)
(00004C50 8 4		UnVar4)
(00004C52 5 4		UnVar4)
(00004C54 13 27 0		nil->JMP 00004C72)
(00004C57 5 0		UnVar0)
(00004C59 5 10		UnVar10)
(00004C5B 9 194 1		"VLMSG.DLL")
(00004C5E 51 124 96 0 0		24700)
(00004C63 81 2 193 1 1 0		string-resource)
(00004C69 95 3 191 50 0 0		dialog.reinput)
(00004C6F 15 35 0		JMP 00004C95)
(00004C72 5 10		UnVar10)
(00004C74 9 150 1		"")
(00004C77 9 182 0		'text)
(00004C7A 81 3 239 0 1 0		slot-value<-)
(00004C80 10)
(00004C81 5 0		UnVar0)
(00004C83 9 150 1		"")
(00004C86 95 2 0 45 0 0		set-dialog-status)
(00004C8C 10)
(00004C8D 5 0		UnVar0)
(00004C8F 95 1 67 0 0 0		update-host-spouse)
(00004C95 25 1 0)
(00004C98 22		ret)
;;;def _del-items-from-list 19609
(00004C99 20 4 1 1 0)
(00004C9E 5 0		UnVar0)
(00004CA0 8 1		UnVar1)
(00004CA2 5 1		UnVar1)
(00004CA4 44 11		IDFun11)
(00004CA6 8 2		UnVar2)
(00004CA8 5 1		UnVar1)
(00004CAA 5 2		UnVar2)
(00004CAC 9 70 0		':SHOW-LIST)
(00004CAF 53 3 164 0 1 32		_label-getf)
(00004CB5 8 3		UnVar3)
(00004CB7 5 3		UnVar3)
(00004CB9 95 1 141 87 0 0		list-box-erase-selection)
(00004CBF 10)
(00004CC0 5 0		UnVar0)
(00004CC2 95 1 0 45 0 0		set-dialog-status)
(00004CC8 10)
(00004CC9 5 3		UnVar3)
(00004CCB 96 1 67 0 0 0		update-host-spouse)
;;;def nil 19665
(00004CD1 20 8 4 4 0)
(00004CD6 5 0		UnVar0)
(00004CD8 8 4		UnVar4)
(00004CDA 5 4		UnVar4)
(00004CDC 44 11		IDFun11)
(00004CDE 8 5		UnVar5)
(00004CE0 5 4		UnVar4)
(00004CE2 5 5		UnVar5)
(00004CE4 9 70 0		':SHOW-LIST)
(00004CE7 53 3 164 0 1 32		_label-getf)
(00004CED 8 6		UnVar6)
(00004CEF 5 4		UnVar4)
(00004CF1 5 5		UnVar5)
(00004CF3 9 69 0		':ADD-BOX)
(00004CF6 53 3 164 0 1 32		_label-getf)
(00004CFC 8 7		UnVar7)
(00004CFE 5 7		UnVar7)
(00004D00 9 182 0		'text)
(00004D03 81 2 60 1 1 0		slot-value)
(00004D09 53 1 83 0 1 32		_fine-stringp)
(00004D0F 13 12 0		nil->JMP 00004D1E)
(00004D12 5 0		UnVar0)
(00004D14 5 2		UnVar2)
(00004D16 5 3		UnVar3)
(00004D18 96 3 245 75 0 0		func 00004BF5)
(00004D1E 5 1		UnVar1)
(00004D20 5 6		UnVar6)
(00004D22 95 1 126 88 0 0		list-box-contents)
(00004D28 95 2 209 53 0 0		accessed-value<-)
(00004D2E 10)
(00004D2F 5 0		UnVar0)
(00004D31 97 1 202 0 0 0		offset 000000CA)
;;;def p-get-expr-dialog-show 19767
(00004D37 21 17 6 7 0)
(00004D3C 100 7		UNVar7)
(00004D3E 100 8		UNVar8)
(00004D40 100 9		UNVar9)
(00004D42 51 150 0 12 0		786582)
(00004D47 9 77 0		'*mds-expr*)
(00004D4A 9 194 1		"VLMSG.DLL")
(00004D4D 51 166 89 0 0		22950)
(00004D52 81 2 193 1 1 0		string-resource)
(00004D58 1		nil)
(00004D59 50 15		15)
(00004D5B 3 62 0		*mds-history*)
(00004D5E 1		nil)
(00004D5F 5 4		UnVar4)
(00004D61 95 8 190 59 0 0		accessed-drop-down-list-box)
(00004D67 8 10		UnVar10)
(00004D69 51 36 0 13 0		852004)
(00004D6E 9 194 1		"VLMSG.DLL")
(00004D71 51 84 61 0 0		15700)
(00004D76 81 2 193 1 1 0		string-resource)
(00004D7C 15 16 0		JMP 00004D8F)
(00004D7F 20 1 1 1 0)
(00004D84 5 0		UnVar0)
(00004D86 4 1 5		UpVar1-5)
(00004D89 96 2 34 79 0 0		_modal-dialog-ok)
(00004D8F 12 217 1		'(19839 nil))
(00004D92 9 194 1		"VLMSG.DLL")
(00004D95 51 246 94 0 0		24310)
(00004D9A 81 2 193 1 1 0		string-resource)
(00004DA0 95 4 44 18 0 0		push-button)
(00004DA6 8 11		UnVar11)
(00004DA8 1		nil)
(00004DA9 1		nil)
(00004DAA 5 1		UnVar1)
(00004DAC 14 14 0		T->JMP 00004DBD)
(00004DAF 9 194 1		"VLMSG.DLL")
(00004DB2 51 0 95 0 0		24320)
(00004DB7 81 2 193 1 1 0		string-resource)
(00004DBD 9 103 0		':V)
(00004DC0 50 4		4)
(00004DC2 9 111 0		':H)
(00004DC5 50 5		5)
(00004DC7 5 10		UnVar10)
(00004DC9 50 5		5)
(00004DCB 57 4 0		list)
(00004DCE 50 8		8)
(00004DD0 9 111 0		':H)
(00004DD3 50 40		40)
(00004DD5 5 11		UnVar11)
(00004DD7 50 10		10)
(00004DD9 3 86 0		*parms-dialog-cancel-button*)
(00004DDC 57 5 0		list)
(00004DDF 50 4		4)
(00004DE1 57 6 0		list)
(00004DE4 9 71 1		':DEFAULT-PUSH-BUTTON)
(00004DE7 5 11		UnVar11)
(00004DE9 9 68 1		':L-CONTEXT)
(00004DEC 5 0		UnVar0)
(00004DEE 9 75 1		':FONT)
(00004DF1 3 85 0		*inspector-font*)
(00004DF4 9 73 1		':PITCH)
(00004DF7 3 84 0		*inspector-pitch*)
(00004DFA 9 170 0		':STATUS)
(00004DFD 5 3		UnVar3)
(00004DFF 13 8 0		nil->JMP 00004E0A)
(00004E02 50 1		1)
(00004E04 5 3		UnVar3)
(00004E06 42		cons)
(00004E07 15 2 0		JMP 00004E0C)
(00004E0A 50 1		1)
(00004E0C 95 14 50 49 0 0		dialog-fmt)
(00004E12 8 9		UnVar9)
(00004E14 5 6		UnVar6)
(00004E16 13 238 0		nil->JMP 00004F07)
(00004E19 5 6		UnVar6)
(00004E1B 50 102		102)
(00004E1D 38		=)
(00004E1E 13 20 0		nil->JMP 00004E35)
(00004E21 51 239 3 0 0		1007)
(00004E26 50 1		1)
(00004E28 50 2		2)
(00004E2A 51 231 3 0 0		999)
(00004E2F 57 4 0		list)
(00004E32 15 119 0		JMP 00004EAC)
(00004E35 5 6		UnVar6)
(00004E37 51 135 0 0 0		135)
(00004E3C 38		=)
(00004E3D 13 20 0		nil->JMP 00004E54)
(00004E40 51 194 4 0 0		1218)
(00004E45 50 1		1)
(00004E47 50 2		2)
(00004E49 51 195 4 0 0		1219)
(00004E4E 57 4 0		list)
(00004E51 15 88 0		JMP 00004EAC)
(00004E54 5 6		UnVar6)
(00004E56 50 109		109)
(00004E58 38		=)
(00004E59 13 20 0		nil->JMP 00004E70)
(00004E5C 51 197 4 0 0		1221)
(00004E61 50 1		1)
(00004E63 50 2		2)
(00004E65 51 242 3 0 0		1010)
(00004E6A 57 4 0		list)
(00004E6D 15 60 0		JMP 00004EAC)
(00004E70 5 6		UnVar6)
(00004E72 51 137 0 0 0		137)
(00004E77 38		=)
(00004E78 13 20 0		nil->JMP 00004E8F)
(00004E7B 51 255 4 0 0		1279)
(00004E80 50 1		1)
(00004E82 50 2		2)
(00004E84 51 0 5 0 0		1280)
(00004E89 57 4 0		list)
(00004E8C 15 29 0		JMP 00004EAC)
(00004E8F 5 6		UnVar6)
(00004E91 50 127		127)
(00004E93 38		=)
(00004E94 13 20 0		nil->JMP 00004EAB)
(00004E97 51 161 4 0 0		1185)
(00004E9C 50 1		1)
(00004E9E 50 2		2)
(00004EA0 51 162 4 0 0		1186)
(00004EA5 57 4 0		list)
(00004EA8 15 1 0		JMP 00004EAC)
(00004EAB 1		nil)
(00004EAC 8 8		UnVar8)
(00004EAE 5 9		UnVar9)
(00004EB0 9 225 0		'items)
(00004EB3 81 2 60 1 1 0		slot-value)
(00004EB9 8 12		UnVar12)
(00004EBB 5 8		UnVar8)
(00004EBD 8 13		UnVar13)
(00004EBF 100 14		UNVar14)
(00004EC1 15 31 0		JMP 00004EE3)
(00004EC4 5 12		UnVar12)
(00004EC6 40		car)
(00004EC7 8 15		UnVar15)
(00004EC9 5 13		UnVar13)
(00004ECB 40		car)
(00004ECC 8 16		UnVar16)
(00004ECE 5 15		UnVar15)
(00004ED0 40		car)
(00004ED1 5 16		UnVar16)
(00004ED3 42		cons)
(00004ED4 5 14		UnVar14)
(00004ED6 42		cons)
(00004ED7 8 14		UnVar14)
(00004ED9 5 12		UnVar12)
(00004EDB 41		cdr)
(00004EDC 8 12		UnVar12)
(00004EDE 5 13		UnVar13)
(00004EE0 41		cdr)
(00004EE1 8 13		UnVar13)
(00004EE3 5 12		UnVar12)
(00004EE5 61 2 0		nil->JMP 00004EEA)
(00004EE8 5 13		UnVar13)
(00004EEA 60 215 255		T->JMP 00004EC4)
(00004EED 5 14		UnVar14)
(00004EEF 81 1 196 1 1 0		nreverse)
(00004EF5 8 7		UnVar7)
(00004EF7 5 9		UnVar9)
(00004EF9 9 61 0		"vldlg.dll")
(00004EFC 5 6		UnVar6)
(00004EFE 5 7		UnVar7)
(00004F00 95 4 86 21 0 0		dialog-update-from-res)
(00004F06 10)
(00004F07 5 2		UnVar2)
(00004F09 13 14 0		nil->JMP 00004F1A)
(00004F0C 5 10		UnVar10)
(00004F0E 5 2		UnVar2)
(00004F10 9 182 0		'text)
(00004F13 81 3 239 0 1 0		slot-value<-)
(00004F19 10)
(00004F1A 5 9		UnVar9)
(00004F1C 47 1 177 0 32 32		modal-dialog!!)
;;;def _modal-dialog-ok 20258
(00004F22 20 4 2 2 0)
(00004F27 100 2		UNVar2)
(00004F29 100 3		UNVar3)
(00004F2B 5 0		UnVar0)
(00004F2D 5 1		UnVar1)
(00004F2F 95 2 131 49 0 0		verified-sync-down)
(00004F35 13 2 0		nil->JMP 00004F3A)
(00004F38 1		nil)
(00004F39 22		ret)
(00004F3A 5 0		UnVar0)
(00004F3C 95 1 197 0 0 0		destroy-host-spouse)
(00004F42 10)
(00004F43 9 232 0		':OK)
(00004F46 22		ret)
;;;def p-get-expr-dialog 20295
(00004F47 20 11 2 8 0)
(00004F4C 100 8		UNVar8)
(00004F4E 100 9		UNVar9)
(00004F50 100 10		UNVar10)
(00004F52 5 3		UnVar3)
(00004F54 14 3 0		T->JMP 00004F5A)
(00004F57 3 238 0		_%curr-rep-cntx%)
(00004F5A 8 3		UnVar3)
(00004F5C 5 4		UnVar4)
(00004F5E 13 7 0		nil->JMP 00004F68)
(00004F61 5 4		UnVar4)
(00004F63 37 4		stringp)
(00004F65 15 1 0		JMP 00004F69)
(00004F68 2		T)
(00004F69 9 60 0		"Internal error: Bad initv")
(00004F6C 53 2 66 1 1 32		assert)
(00004F72 10)
(00004F73 5 2		UnVar2)
(00004F75 13 3 0		nil->JMP 00004F7B)
(00004F78 15 5 0		JMP 00004F80)
(00004F7B 9 216 1		'(13540 _protected-read))
(00004F7E 8 2		UnVar2)
(00004F80 5 4		UnVar4)
(00004F82 61 3 0		nil->JMP 00004F88)
(00004F85 5 5		UnVar5)
(00004F87 35		not)
(00004F88 13 14 0		nil->JMP 00004F99)
(00004F8B 1		nil)
(00004F8C 5 3		UnVar3)
(00004F8E 5 4		UnVar4)
(00004F90 5 1		UnVar1)
(00004F92 5 2		UnVar2)
(00004F94 52 4 1		)
(00004F97 8 8		UnVar8)
(00004F99 5 4		UnVar4)
(00004F9B 61 15 0		nil->JMP 00004FAD)
(00004F9E 5 5		UnVar5)
(00004FA0 13 4 0		nil->JMP 00004FA7)
(00004FA3 1		nil)
(00004FA4 15 6 0		JMP 00004FAD)
(00004FA7 5 1		UnVar1)
(00004FA9 5 8		UnVar8)
(00004FAB 38		=)
(00004FAC 35		not)
(00004FAD 13 3 0		nil->JMP 00004FB3)
(00004FB0 5 8		UnVar8)
(00004FB2 22		ret)
(00004FB3 9 77 0		'*mds-expr*)
(00004FB6 5 1		UnVar1)
(00004FB8 9 62 0		'*mds-history*)
(00004FBB 5 6		UnVar6)
(00004FBD 9 152 0		'_%err%)
(00004FC0 5 1		UnVar1)
(00004FC2 24 6 0)
(00004FC5 5 3		UnVar3)
(00004FC7 5 0		UnVar0)
(00004FC9 5 4		UnVar4)
(00004FCB 5 8		UnVar8)
(00004FCD 13 11 0		nil->JMP 00004FDB)
(00004FD0 5 8		UnVar8)
(00004FD2 81 1 151 0 1 0		unbox)
(00004FD8 15 2 0		JMP 00004FDD)
(00004FDB 5 5		UnVar5)
(00004FDD 5 2		UnVar2)
(00004FDF 5 1		UnVar1)
(00004FE1 5 7		UnVar7)
(00004FE3 53 7 59 0 1 32		p-get-expr-dialog-show)
(00004FE9 8 8		UnVar8)
(00004FEB 5 8		UnVar8)
(00004FED 9 232 0		':OK)
(00004FF0 38		=)
(00004FF1 13 6 0		nil->JMP 00004FFA)
(00004FF4 3 77 0		*mds-expr*)
(00004FF7 15 2 0		JMP 00004FFC)
(00004FFA 5 1		UnVar1)
(00004FFC 25 3 0)
(00004FFF 22		ret)
;;;def _traced-service-eval-call 20480
(00005000 20 4 3 4 0)
(00005005 9 58 0		':SERVICE-EVAL)
(00005008 5 0		UnVar0)
(0000500A 5 3		UnVar3)
(0000500C 53 2 57 0 1 32		make-tsf-info)
(00005012 5 1		UnVar1)
(00005014 5 2		UnVar2)
(00005016 81 4 56 0 1 0		_spec-traced-apply)
(0000501C 22		ret)
;;;def eval-and-check-type 20509
(0000501D 20 6 5 5 0)
(00005022 100 5		UNVar5)
(00005024 5 0		UnVar0)
(00005026 5 1		UnVar1)
(00005028 5 2		UnVar2)
(0000502A 5 3		UnVar3)
(0000502C 53 4 55 0 1 32		_protected-read-eval)
(00005032 8 5		UnVar5)
(00005034 5 5		UnVar5)
(00005036 5 3		UnVar3)
(00005038 38		=)
(00005039 13 3 0		nil->JMP 0000503F)
(0000503C 5 3		UnVar3)
(0000503E 22		ret)
(0000503F 5 5		UnVar5)
(00005041 81 1 246 0 1 0		type-of)
(00005047 5 4		UnVar4)
(00005049 53 2 54 0 1 32		type-spec-p)
(0000504F 13 3 0		nil->JMP 00005055)
(00005052 5 5		UnVar5)
(00005054 22		ret)
(00005055 5 3		UnVar3)
(00005057 1		nil)
(00005058 9 194 1		"VLMSG.DLL")
(0000505B 51 10 95 0 0		24330)
(00005060 81 2 193 1 1 0		string-resource)
(00005066 5 4		UnVar4)
(00005068 53 3 178 0 1 32		format)
(0000506E 81 2 140 0 1 0		unbox<-)
(00005074 10)
(00005075 5 0		UnVar0)
(00005077 6 15 1		_%reinput%)
(0000507A 5 3		UnVar3)
(0000507C 22		ret)
;;;def p-get-value-dialog 20605
(0000507D 21 8 3 8 0)
(00005082 5 2		UnVar2)
(00005084 2		T)
(00005085 38		=)
(00005086 13 5 0		nil->JMP 0000508E)
(00005089 5 0		UnVar0)
(0000508B 15 46 0		JMP 000050BC)
(0000508E 5 0		UnVar0)
(00005090 5 2		UnVar2)
(00005092 36		atom)
(00005093 13 6 0		nil->JMP 0000509C)
(00005096 9 53 0		" [")
(00005099 15 3 0		JMP 0000509F)
(0000509C 9 150 1		"")
(0000509F 5 2		UnVar2)
(000050A1 81 1 149 0 1 0		prin1-to-string)
(000050A7 5 2		UnVar2)
(000050A9 36		atom)
(000050AA 13 6 0		nil->JMP 000050B3)
(000050AD 9 52 0		"]")
(000050B0 15 3 0		JMP 000050B6)
(000050B3 9 150 1		"")
(000050B6 81 4 187 1 1 0		concat)
(000050BC 5 1		UnVar1)
(000050BE 5 2		UnVar2)
(000050C0 2		T)
(000050C1 38		=)
(000050C2 13 6 0		nil->JMP 000050CB)
(000050C5 9 55 0		'_protected-read-eval)
(000050C8 15 28 0		JMP 000050E7)
(000050CB 15 22 0		JMP 000050E4)
(000050CE 20 4 4 4 0)
(000050D3 5 0		UnVar0)
(000050D5 5 1		UnVar1)
(000050D7 5 2		UnVar2)
(000050D9 5 3		UnVar3)
(000050DB 4 1 2		UpVar1-2)
(000050DE 96 5 29 80 0 0		eval-and-check-type)
(000050E4 12 215 1		'(20686 nil))
(000050E7 5 3		UnVar3)
(000050E9 5 4		UnVar4)
(000050EB 5 5		UnVar5)
(000050ED 5 6		UnVar6)
(000050EF 5 7		UnVar7)
(000050F1 96 8 71 79 0 0		p-get-expr-dialog)
;;;def directory-browse-files 20727
(000050F7 21 4 1 3 0)
(000050FC 5 2		UnVar2)
(000050FE 13 200 0		nil->JMP 000051C9)
(00005101 5 0		UnVar0)
(00005103 5 1		UnVar1)
(00005105 50 1		1)
(00005107 81 3 51 0 1 0		directory-files)
(0000510D 81 0 50 0 1 0		chdir)
(00005113 8 3		UnVar3)
(00005115 5 0		UnVar0)
(00005117 81 1 50 0 1 0		chdir)
(0000511D 10)
(0000511E 15 15 0		JMP 00005130)
(00005121 20 0 0 0 0)
(00005126 4 1 3		UpVar1-3)
(00005129 81 1 50 0 1 0		chdir)
(0000512F 22		ret)
(00005130 12 214 1		'(20769 -unwind-cleanup-))
(00005133 15 130 0		JMP 000051B8)
(00005136 20 6 0 0 0)
(0000513B 9 49 0		"..")
(0000513E 9 162 1		".")
(00005141 9 162 1		".")
(00005144 1		nil)
(00005145 50 255		-1)
(00005147 81 3 51 0 1 0		directory-files)
(0000514D 81 2 117 0 1 0		delete)
(00005153 81 2 117 0 1 0		delete)
(00005159 8 0		UnVar0)
(0000515B 100 1		UNVar1)
(0000515D 15 80 0		JMP 000051B0)
(00005160 5 1		UnVar1)
(00005162 5 0		UnVar0)
(00005164 40		car)
(00005165 8 2		UnVar2)
(00005167 5 2		UnVar2)
(00005169 4 1 1		UpVar1-1)
(0000516C 2		T)
(0000516D 53 3 48 0 1 32		directory-browse-files)
(00005173 8 3		UnVar3)
(00005175 100 4		UNVar4)
(00005177 15 28 0		JMP 00005196)
(0000517A 5 3		UnVar3)
(0000517C 40		car)
(0000517D 8 5		UnVar5)
(0000517F 5 2		UnVar2)
(00005181 9 47 0		"/")
(00005184 5 5		UnVar5)
(00005186 81 3 187 1 1 0		concat)
(0000518C 5 4		UnVar4)
(0000518E 42		cons)
(0000518F 8 4		UnVar4)
(00005191 5 3		UnVar3)
(00005193 41		cdr)
(00005194 8 3		UnVar3)
(00005196 5 3		UnVar3)
(00005198 60 223 255		T->JMP 0000517A)
(0000519B 5 4		UnVar4)
(0000519D 81 1 196 1 1 0		nreverse)
(000051A3 81 2 195 1 1 0		nconc)
(000051A9 8 1		UnVar1)
(000051AB 5 0		UnVar0)
(000051AD 41		cdr)
(000051AE 8 0		UnVar0)
(000051B0 5 0		UnVar0)
(000051B2 60 171 255		T->JMP 00005160)
(000051B5 5 1		UnVar1)
(000051B7 22		ret)
(000051B8 12 213 1		'(20790 -unwind-protect-))
(000051BB 1		nil)
(000051BC 81 3 131 1 1 0		_unwinded-apply)
(000051C2 81 2 195 1 1 0		nconc)
(000051C8 22		ret)
(000051C9 5 0		UnVar0)
(000051CB 5 1		UnVar1)
(000051CD 50 1		1)
(000051CF 81 3 51 0 1 0		directory-files)
(000051D5 22		ret)
;;;def filename-pattern 20950
(000051D6 20 1 1 1 0)
(000051DB 5 0		UnVar0)
(000051DD 63		nil->ret)
(000051DE 9 147 0		" \t\n\r")
(000051E1 5 0		UnVar0)
(000051E3 81 2 46 0 1 0		string-right-trim)
(000051E9 53 1 45 0 1 32		filename-beautify)
(000051EF 8 0		UnVar0)
(000051F1 5 0		UnVar0)
(000051F3 9 150 1		"")
(000051F6 81 2 0 1 1 0		equal)
(000051FC 13 2 0		nil->JMP 00005201)
(000051FF 1		nil)
(00005200 22		ret)
(00005201 5 0		UnVar0)
(00005203 22		ret)
;;;def try-chdir 20996
(00005204 20 2 2 2 0)
(00005209 5 1		UnVar1)
(0000520B 53 1 83 0 1 32		_fine-stringp)
(00005211 13 56 0		nil->JMP 0000524C)
(00005214 5 1		UnVar1)
(00005216 81 1 44 0 1 0		filename-absolute-p)
(0000521C 14 8 0		T->JMP 00005227)
(0000521F 5 1		UnVar1)
(00005221 95 1 91 82 0 0		filename-drive-char)
(00005227 13 19 0		nil->JMP 0000523D)
(0000522A 5 1		UnVar1)
(0000522C 81 1 160 1 1 0		file-directory-p)
(00005232 13 3 0		nil->JMP 00005238)
(00005235 15 2 0		JMP 0000523A)
(00005238 100 1		UNVar1)
(0000523A 15 12 0		JMP 00005249)
(0000523D 5 1		UnVar1)
(0000523F 5 0		UnVar0)
(00005241 81 2 43 0 1 0		find-file)
(00005247 8 1		UnVar1)
(00005249 15 4 0		JMP 00005250)
(0000524C 5 0		UnVar0)
(0000524E 8 1		UnVar1)
(00005250 5 1		UnVar1)
(00005252 63		nil->ret)
(00005253 5 1		UnVar1)
(00005255 47 1 42 0 32 32		file-absolute-name?)
;;;def filename-drive-char 21083
(0000525B 20 2 1 1 0)
(00005260 100 1		UNVar1)
(00005262 5 0		UnVar0)
(00005264 81 1 184 0 1 0		string-length)
(0000526A 50 2		2)
(0000526C 77		>=)
(0000526D 61 35 0		nil->JMP 00005293)
(00005270 5 0		UnVar0)
(00005272 50 1		1)
(00005274 81 2 176 1 1 0		char)
(0000527A 50 58		58)
(0000527C 38		=)
(0000527D 61 19 0		nil->JMP 00005293)
(00005280 5 0		UnVar0)
(00005282 50 0		0)
(00005284 81 2 176 1 1 0		char)
(0000528A 11)
(0000528B 8 1		UnVar1)
(0000528D 53 1 41 0 1 32		alpha-char-p)
(00005293 63		nil->ret)
(00005294 5 1		UnVar1)
(00005296 22		ret)
;;;def drive-char-exists-p 21143
(00005297 20 1 1 1 0)
(0000529C 5 0		UnVar0)
(0000529E 53 1 40 0 1 32		char-upcase)
(000052A4 81 0 39 0 1 0		get-logical-drives)
(000052AA 81 1 188 1 1 0		nstring-upcase)
(000052B0 81 2 38 0 1 0		string-position)
(000052B6 63		nil->ret)
(000052B7 2		T)
(000052B8 22		ret)
;;;def filename-unc-name 21177
(000052B9 20 3 1 1 0)
(000052BE 100 1		UNVar1)
(000052C0 100 2		UNVar2)
(000052C2 5 0		UnVar0)
(000052C4 9 37 0		"//")
(000052C7 81 2 36 0 1 0		string-mismatch)
(000052CD 50 2		2)
(000052CF 38		=)
(000052D0 61 34 0		nil->JMP 000052F5)
(000052D3 50 47		47)
(000052D5 5 0		UnVar0)
(000052D7 50 2		2)
(000052D9 81 3 38 0 1 0		string-position)
(000052DF 11)
(000052E0 8 2		UnVar2)
(000052E2 61 16 0		nil->JMP 000052F5)
(000052E5 50 47		47)
(000052E7 5 0		UnVar0)
(000052E9 5 2		UnVar2)
(000052EB 79		1+)
(000052EC 81 3 38 0 1 0		string-position)
(000052F2 11)
(000052F3 8 1		UnVar1)
(000052F5 63		nil->ret)
(000052F6 5 0		UnVar0)
(000052F8 50 0		0)
(000052FA 5 1		UnVar1)
(000052FC 81 3 35 0 1 0		string-subseq)
(00005302 22		ret)
;;;def filename-compress 21251
(00005303 20 7 2 2 0)
(00005308 100 2		UNVar2)
(0000530A 100 3		UNVar3)
(0000530C 100 4		UNVar4)
(0000530E 100 5		UNVar5)
(00005310 100 6		UNVar6)
(00005312 5 0		UnVar0)
(00005314 53 1 45 0 1 32		filename-beautify)
(0000531A 8 0		UnVar0)
(0000531C 5 0		UnVar0)
(0000531E 81 1 184 0 1 0		string-length)
(00005324 8 4		UnVar4)
(00005326 5 4		UnVar4)
(00005328 8 5		UnVar5)
(0000532A 5 5		UnVar5)
(0000532C 5 1		UnVar1)
(0000532E 78		<=)
(0000532F 60 141 0		T->JMP 000053BF)
(00005332 5 0		UnVar0)
(00005334 95 1 91 82 0 0		filename-drive-char)
(0000533A 13 113 0		nil->JMP 000053AE)
(0000533D 5 0		UnVar0)
(0000533F 50 2		2)
(00005341 81 2 176 1 1 0		char)
(00005347 50 47		47)
(00005349 38		=)
(0000534A 13 7 0		nil->JMP 00005354)
(0000534D 50 3		3)
(0000534F 8 3		UnVar3)
(00005351 15 4 0		JMP 00005358)
(00005354 50 3		3)
(00005356 8 3		UnVar3)
(00005358 5 0		UnVar0)
(0000535A 50 0		0)
(0000535C 5 3		UnVar3)
(0000535E 81 3 161 1 1 0		substr)
(00005364 9 148 0		"...")
(00005367 81 2 187 1 1 0		concat)
(0000536D 8 6		UnVar6)
(0000536F 5 5		UnVar5)
(00005371 5 3		UnVar3)
(00005373 81 2 151 1 1 0		-)
(00005379 8 5		UnVar5)
(0000537B 5 0		UnVar0)
(0000537D 5 3		UnVar3)
(0000537F 81 2 35 0 1 0		string-subseq)
(00005385 8 0		UnVar0)
(00005387 5 4		UnVar4)
(00005389 50 3		3)
(0000538B 81 2 151 1 1 0		-)
(00005391 8 4		UnVar4)
(00005393 5 1		UnVar1)
(00005395 50 3		3)
(00005397 81 2 151 1 1 0		-)
(0000539D 8 1		UnVar1)
(0000539F 5 1		UnVar1)
(000053A1 5 3		UnVar3)
(000053A3 81 2 151 1 1 0		-)
(000053A9 8 1		UnVar1)
(000053AB 15 17 0		JMP 000053BF)
(000053AE 9 148 0		"...")
(000053B1 8 6		UnVar6)
(000053B3 5 1		UnVar1)
(000053B5 50 3		3)
(000053B7 81 2 151 1 1 0		-)
(000053BD 8 1		UnVar1)
(000053BF 5 6		UnVar6)
(000053C1 13 90 0		nil->JMP 0000541E)
(000053C4 5 0		UnVar0)
(000053C6 50 47		47)
(000053C8 53 2 34 0 1 32		string-by-char-to-list)
(000053CE 8 2		UnVar2)
(000053D0 15 29 0		JMP 000053F0)
(000053D3 5 5		UnVar5)
(000053D5 80		1-)
(000053D6 8 5		UnVar5)
(000053D8 5 5		UnVar5)
(000053DA 5 2		UnVar2)
(000053DC 40		car)
(000053DD 81 1 184 0 1 0		string-length)
(000053E3 81 2 151 1 1 0		-)
(000053E9 8 5		UnVar5)
(000053EB 5 2		UnVar2)
(000053ED 41		cdr)
(000053EE 8 2		UnVar2)
(000053F0 5 2		UnVar2)
(000053F2 41		cdr)
(000053F3 61 5 0		nil->JMP 000053FB)
(000053F6 5 5		UnVar5)
(000053F8 5 1		UnVar1)
(000053FA 77		>=)
(000053FB 60 213 255		T->JMP 000053D3)
(000053FE 5 5		UnVar5)
(00005400 79		1+)
(00005401 8 5		UnVar5)
(00005403 5 6		UnVar6)
(00005405 5 0		UnVar0)
(00005407 5 4		UnVar4)
(00005409 5 5		UnVar5)
(0000540B 81 2 151 1 1 0		-)
(00005411 81 2 35 0 1 0		string-subseq)
(00005417 81 2 187 1 1 0		concat)
(0000541D 22		ret)
(0000541E 5 0		UnVar0)
(00005420 22		ret)
;;;def filespec-find-dir 21537
(00005421 20 5 2 3 0)
(00005426 100 3		UNVar3)
(00005428 100 4		UNVar4)
(0000542A 5 1		UnVar1)
(0000542C 1		nil)
(0000542D 81 2 140 0 1 0		unbox<-)
(00005433 10)
(00005434 5 0		UnVar0)
(00005436 61 8 0		nil->JMP 00005441)
(00005439 5 0		UnVar0)
(0000543B 53 1 45 0 1 32		filename-beautify)
(00005441 8 0		UnVar0)
(00005443 5 0		UnVar0)
(00005445 53 1 83 0 1 32		_fine-stringp)
(0000544B 13 226 0		nil->JMP 00005530)
(0000544E 5 0		UnVar0)
(00005450 95 1 91 82 0 0		filename-drive-char)
(00005456 11)
(00005457 8 3		UnVar3)
(00005459 13 107 0		nil->JMP 000054C7)
(0000545C 5 3		UnVar3)
(0000545E 95 1 151 82 0 0		drive-char-exists-p)
(00005464 13 61 0		nil->JMP 000054A4)
(00005467 5 0		UnVar0)
(00005469 53 1 42 0 1 32		file-absolute-name?)
(0000546F 11)
(00005470 8 4		UnVar4)
(00005472 13 7 0		nil->JMP 0000547C)
(00005475 5 4		UnVar4)
(00005477 8 0		UnVar0)
(00005479 15 37 0		JMP 000054A1)
(0000547C 5 1		UnVar1)
(0000547E 9 194 1		"VLMSG.DLL")
(00005481 51 156 119 0 0		30620)
(00005486 81 2 193 1 1 0		string-resource)
(0000548C 5 0		UnVar0)
(0000548E 81 1 192 1 1 0		string)
(00005494 81 2 191 1 1 0		_win-format-message)
(0000549A 81 2 140 0 1 0		unbox<-)
(000054A0 10)
(000054A1 15 32 0		JMP 000054C4)
(000054A4 5 1		UnVar1)
(000054A6 1		nil)
(000054A7 9 194 1		"VLMSG.DLL")
(000054AA 51 174 96 0 0		24750)
(000054AF 81 2 193 1 1 0		string-resource)
(000054B5 5 3		UnVar3)
(000054B7 53 3 178 0 1 32		format)
(000054BD 81 2 140 0 1 0		unbox<-)
(000054C3 10)
(000054C4 15 102 0		JMP 0000552D)
(000054C7 5 0		UnVar0)
(000054C9 81 1 44 0 1 0		filename-absolute-p)
(000054CF 13 5 0		nil->JMP 000054D7)
(000054D2 5 0		UnVar0)
(000054D4 15 26 0		JMP 000054F1)
(000054D7 5 2		UnVar2)
(000054D9 13 13 0		nil->JMP 000054E9)
(000054DC 5 2		UnVar2)
(000054DE 5 0		UnVar0)
(000054E0 95 2 4 82 0 0		try-chdir)
(000054E6 15 8 0		JMP 000054F1)
(000054E9 5 0		UnVar0)
(000054EB 53 1 42 0 1 32		file-absolute-name?)
(000054F1 8 4		UnVar4)
(000054F3 5 4		UnVar4)
(000054F5 61 8 0		nil->JMP 00005500)
(000054F8 5 4		UnVar4)
(000054FA 81 1 160 1 1 0		file-directory-p)
(00005500 13 3 0		nil->JMP 00005506)
(00005503 15 39 0		JMP 0000552D)
(00005506 5 1		UnVar1)
(00005508 9 194 1		"VLMSG.DLL")
(0000550B 51 166 119 0 0		30630)
(00005510 81 2 193 1 1 0		string-resource)
(00005516 5 0		UnVar0)
(00005518 81 1 192 1 1 0		string)
(0000551E 81 2 191 1 1 0		_win-format-message)
(00005524 81 2 140 0 1 0		unbox<-)
(0000552A 10)
(0000552B 100 4		UNVar4)
(0000552D 15 18 0		JMP 00005542)
(00005530 5 2		UnVar2)
(00005532 14 6 0		T->JMP 0000553B)
(00005535 81 0 50 0 1 0		chdir)
(0000553B 8 4		UnVar4)
(0000553D 9 150 1		"")
(00005540 8 0		UnVar0)
(00005542 5 4		UnVar4)
(00005544 5 0		UnVar0)
(00005546 42		cons)
(00005547 22		ret)
;;;def filespec-find-filelist 21832
(00005548 20 10 2 4 0)
(0000554D 100 4		UNVar4)
(0000554F 100 5		UNVar5)
(00005551 100 6		UNVar6)
(00005553 100 7		UNVar7)
(00005555 100 8		UNVar8)
(00005557 5 0		UnVar0)
(00005559 13 10 0		nil->JMP 00005566)
(0000555C 5 0		UnVar0)
(0000555E 95 1 214 81 0 0		filename-pattern)
(00005564 8 0		UnVar0)
(00005566 5 0		UnVar0)
(00005568 13 10 0		nil->JMP 00005575)
(0000556B 5 0		UnVar0)
(0000556D 81 1 190 1 1 0		filename-extension)
(00005573 8 8		UnVar8)
(00005575 5 0		UnVar0)
(00005577 53 1 83 0 1 32		_fine-stringp)
(0000557D 13 35 0		nil->JMP 000055A3)
(00005580 5 8		UnVar8)
(00005582 13 25 0		nil->JMP 0000559E)
(00005585 5 0		UnVar0)
(00005587 81 1 33 0 1 0		filename-directory)
(0000558D 8 9		UnVar9)
(0000558F 5 0		UnVar0)
(00005591 81 1 32 0 1 0		filename-non-directory)
(00005597 8 6		UnVar6)
(00005599 5 9		UnVar9)
(0000559B 15 2 0		JMP 000055A0)
(0000559E 5 0		UnVar0)
(000055A0 15 1 0		JMP 000055A4)
(000055A3 1		nil)
(000055A4 8 7		UnVar7)
(000055A6 5 7		UnVar7)
(000055A8 5 1		UnVar1)
(000055AA 5 2		UnVar2)
(000055AC 95 3 33 84 0 0		filespec-find-dir)
(000055B2 8 9		UnVar9)
(000055B4 5 9		UnVar9)
(000055B6 40		car)
(000055B7 8 5		UnVar5)
(000055B9 5 9		UnVar9)
(000055BB 41		cdr)
(000055BC 8 7		UnVar7)
(000055BE 5 1		UnVar1)
(000055C0 81 1 151 0 1 0		unbox)
(000055C6 13 4 0		nil->JMP 000055CD)
(000055C9 1		nil)
(000055CA 15 2 0		JMP 000055CF)
(000055CD 5 5		UnVar5)
(000055CF 13 33 0		nil->JMP 000055F3)
(000055D2 5 6		UnVar6)
(000055D4 13 3 0		nil->JMP 000055DA)
(000055D7 15 13 0		JMP 000055E7)
(000055DA 9 189 1		"*")
(000055DD 5 3		UnVar3)
(000055DF 81 2 187 1 1 0		concat)
(000055E5 8 6		UnVar6)
(000055E7 5 5		UnVar5)
(000055E9 5 6		UnVar6)
(000055EB 53 2 48 0 1 32		directory-browse-files)
(000055F1 8 4		UnVar4)
(000055F3 5 5		UnVar5)
(000055F5 5 7		UnVar7)
(000055F7 5 4		UnVar4)
(000055F9 42		cons)
(000055FA 42		cons)
(000055FB 22		ret)
;;;def file-absolute-name? 22012
(000055FC 21 2 1 1 0)
(00005601 100 1		UNVar1)
(00005603 15 14 0		JMP 00005614)
(00005606 20 0 0 0 0)
(0000560B 4 1 0		UpVar1-0)
(0000560E 47 1 31 0 32 32		file-absolute-name)
(00005614 12 212 1		'(22022 nil))
(00005617 9 194 1		"VLMSG.DLL")
(0000561A 51 204 96 0 0		24780)
(0000561F 81 2 193 1 1 0		string-resource)
(00005625 53 2 30 0 1 32		run-fast)
(0000562B 8 1		UnVar1)
(0000562D 5 1		UnVar1)
(0000562F 9 139 1		':ERROR)
(00005632 38		=)
(00005633 13 2 0		nil->JMP 00005638)
(00005636 1		nil)
(00005637 22		ret)
(00005638 5 1		UnVar1)
(0000563A 22		ret)
;;;def sort-by-car-string 22075
(0000563B 20 1 1 1 0)
(00005640 5 0		UnVar0)
(00005642 15 18 0		JMP 00005657)
(00005645 20 2 2 2 0)
(0000564A 5 0		UnVar0)
(0000564C 40		car)
(0000564D 5 1		UnVar1)
(0000564F 40		car)
(00005650 81 2 182 1 1 0		string-lessp)
(00005656 22		ret)
(00005657 9 211 1		'(22085 nil))
(0000565A 81 2 181 1 1 0		sort)
(00005660 22		ret)
;;;def sort-by-cadr-string 22113
(00005661 20 1 1 1 0)
(00005666 5 0		UnVar0)
(00005668 15 20 0		JMP 0000567F)
(0000566B 20 2 2 2 0)
(00005670 5 0		UnVar0)
(00005672 41		cdr)
(00005673 40		car)
(00005674 5 1		UnVar1)
(00005676 41		cdr)
(00005677 40		car)
(00005678 81 2 182 1 1 0		string-lessp)
(0000567E 22		ret)
(0000567F 9 210 1		'(22123 nil))
(00005682 81 2 181 1 1 0		sort)
(00005688 22		ret)
;;;def nil 22153
(00005689 20 6 2 2 0)
(0000568E 100 2		UNVar2)
(00005690 100 3		UNVar3)
(00005692 5 0		UnVar0)
(00005694 8 4		UnVar4)
(00005696 100 5		UNVar5)
(00005698 15 40 0		JMP 000056C3)
(0000569B 5 4		UnVar4)
(0000569D 40		car)
(0000569E 8 5		UnVar5)
(000056A0 5 4		UnVar4)
(000056A2 41		cdr)
(000056A3 8 4		UnVar4)
(000056A5 5 5		UnVar5)
(000056A7 5 1		UnVar1)
(000056A9 81 2 29 0 1 0		assoc)
(000056AF 13 10 0		nil->JMP 000056BC)
(000056B2 5 5		UnVar5)
(000056B4 5 3		UnVar3)
(000056B6 42		cons)
(000056B7 8 3		UnVar3)
(000056B9 15 7 0		JMP 000056C3)
(000056BC 5 5		UnVar5)
(000056BE 5 2		UnVar2)
(000056C0 42		cons)
(000056C1 8 2		UnVar2)
(000056C3 5 4		UnVar4)
(000056C5 60 211 255		T->JMP 0000569B)
(000056C8 5 2		UnVar2)
(000056CA 81 1 196 1 1 0		nreverse)
(000056D0 5 3		UnVar3)
(000056D2 81 1 196 1 1 0		nreverse)
(000056D8 42		cons)
(000056D9 22		ret)
;;;def ninsert-list 22234
(000056DA 20 4 3 4 0)
(000056DF 5 1		UnVar1)
(000056E1 13 3 0		nil->JMP 000056E7)
(000056E4 15 22 0		JMP 000056FD)
(000056E7 5 3		UnVar3)
(000056E9 13 13 0		nil->JMP 000056F9)
(000056EC 5 0		UnVar0)
(000056EE 81 1 115 0 1 0		last)
(000056F4 8 1		UnVar1)
(000056F6 15 4 0		JMP 000056FD)
(000056F9 5 0		UnVar0)
(000056FB 8 1		UnVar1)
(000056FD 5 1		UnVar1)
(000056FF 13 88 0		nil->JMP 0000575A)
(00005702 5 2		UnVar2)
(00005704 13 80 0		nil->JMP 00005757)
(00005707 5 3		UnVar3)
(00005709 13 23 0		nil->JMP 00005723)
(0000570C 5 1		UnVar1)
(0000570E 5 2		UnVar2)
(00005710 5 1		UnVar1)
(00005712 41		cdr)
(00005713 81 2 195 1 1 0		nconc)
(00005719 81 2 211 0 1 0		setcdr)
(0000571F 10)
(00005720 15 49 0		JMP 00005754)
(00005723 5 1		UnVar1)
(00005725 5 1		UnVar1)
(00005727 40		car)
(00005728 5 1		UnVar1)
(0000572A 41		cdr)
(0000572B 42		cons)
(0000572C 81 2 211 0 1 0		setcdr)
(00005732 10)
(00005733 5 1		UnVar1)
(00005735 5 2		UnVar2)
(00005737 40		car)
(00005738 81 2 127 1 1 0		setcar)
(0000573E 10)
(0000573F 5 1		UnVar1)
(00005741 5 2		UnVar2)
(00005743 41		cdr)
(00005744 5 1		UnVar1)
(00005746 41		cdr)
(00005747 81 2 195 1 1 0		nconc)
(0000574D 81 2 211 0 1 0		setcdr)
(00005753 10)
(00005754 15 0 0		JMP 00005757)
(00005757 15 4 0		JMP 0000575E)
(0000575A 5 2		UnVar2)
(0000575C 8 0		UnVar0)
(0000575E 5 0		UnVar0)
(00005760 22		ret)
;;;def list-box-selection 22369
(00005761 20 2 1 1 0)
(00005766 9 28 0		'list-box-selection)
(00005769 5 0		UnVar0)
(0000576B 81 2 204 1 1 0		compute-applicable-methods)
(00005771 8 1		UnVar1)
(00005773 5 1		UnVar1)
(00005775 13 3 0		nil->JMP 0000577B)
(00005778 15 12 0		JMP 00005787)
(0000577B 9 28 0		'list-box-selection)
(0000577E 5 0		UnVar0)
(00005780 81 2 202 1 1 0		no-applicable-method)
(00005786 10)
(00005787 5 0		UnVar0)
(00005789 5 1		UnVar1)
(0000578B 46 1		invoke+ret)
;;;def list-box-erase-selection 22413
(0000578D 20 2 1 1 0)
(00005792 9 27 0		'list-box-erase-selection)
(00005795 5 0		UnVar0)
(00005797 81 2 204 1 1 0		compute-applicable-methods)
(0000579D 8 1		UnVar1)
(0000579F 5 1		UnVar1)
(000057A1 13 3 0		nil->JMP 000057A7)
(000057A4 15 12 0		JMP 000057B3)
(000057A7 9 27 0		'list-box-erase-selection)
(000057AA 5 0		UnVar0)
(000057AC 81 2 202 1 1 0		no-applicable-method)
(000057B2 10)
(000057B3 5 0		UnVar0)
(000057B5 5 1		UnVar1)
(000057B7 46 1		invoke+ret)
;;;def list-box-set-selection 22457
(000057B9 20 4 3 3 0)
(000057BE 9 26 0		'list-box-set-selection)
(000057C1 5 0		UnVar0)
(000057C3 81 2 204 1 1 0		compute-applicable-methods)
(000057C9 8 3		UnVar3)
(000057CB 5 3		UnVar3)
(000057CD 13 3 0		nil->JMP 000057D3)
(000057D0 15 16 0		JMP 000057E3)
(000057D3 9 26 0		'list-box-set-selection)
(000057D6 5 0		UnVar0)
(000057D8 5 1		UnVar1)
(000057DA 5 2		UnVar2)
(000057DC 81 4 202 1 1 0		no-applicable-method)
(000057E2 10)
(000057E3 5 0		UnVar0)
(000057E5 5 1		UnVar1)
(000057E7 5 2		UnVar2)
(000057E9 5 3		UnVar3)
(000057EB 46 3		invoke+ret)
;;;def list-box-add-items 22509
(000057ED 20 3 1 1 1)
(000057F2 100 2		UNVar2)
(000057F4 9 25 0		'list-box-add-items)
(000057F7 5 0		UnVar0)
(000057F9 81 2 204 1 1 0		compute-applicable-methods)
(000057FF 11)
(00005800 8 2		UnVar2)
(00005802 13 3 0		nil->JMP 00005808)
(00005805 15 18 0		JMP 0000581A)
(00005808 9 202 1		'no-applicable-method)
(0000580B 9 25 0		'list-box-add-items)
(0000580E 5 0		UnVar0)
(00005810 5 1		UnVar1)
(00005812 81 3 203 1 1 0		list*)
(00005818 83		apply)
(00005819 10)
(0000581A 5 2		UnVar2)
(0000581C 5 0		UnVar0)
(0000581E 5 1		UnVar1)
(00005820 42		cons)
(00005821 84		apply+ret)
;;;def list-box-items 22562
(00005822 20 2 1 1 0)
(00005827 9 24 0		'list-box-items)
(0000582A 5 0		UnVar0)
(0000582C 81 2 204 1 1 0		compute-applicable-methods)
(00005832 8 1		UnVar1)
(00005834 5 1		UnVar1)
(00005836 13 3 0		nil->JMP 0000583C)
(00005839 15 12 0		JMP 00005848)
(0000583C 9 24 0		'list-box-items)
(0000583F 5 0		UnVar0)
(00005841 81 2 202 1 1 0		no-applicable-method)
(00005847 10)
(00005848 5 0		UnVar0)
(0000584A 5 1		UnVar1)
(0000584C 46 1		invoke+ret)
;;;def list-box-items<- 22606
(0000584E 20 3 2 2 0)
(00005853 9 23 0		'list-box-items<-)
(00005856 5 0		UnVar0)
(00005858 81 2 204 1 1 0		compute-applicable-methods)
(0000585E 8 2		UnVar2)
(00005860 5 2		UnVar2)
(00005862 13 3 0		nil->JMP 00005868)
(00005865 15 14 0		JMP 00005876)
(00005868 9 23 0		'list-box-items<-)
(0000586B 5 0		UnVar0)
(0000586D 5 1		UnVar1)
(0000586F 81 3 202 1 1 0		no-applicable-method)
(00005875 10)
(00005876 5 0		UnVar0)
(00005878 5 1		UnVar1)
(0000587A 5 2		UnVar2)
(0000587C 46 2		invoke+ret)
;;;def list-box-contents 22654
(0000587E 20 2 1 1 0)
(00005883 9 22 0		'list-box-contents)
(00005886 5 0		UnVar0)
(00005888 81 2 204 1 1 0		compute-applicable-methods)
(0000588E 8 1		UnVar1)
(00005890 5 1		UnVar1)
(00005892 13 3 0		nil->JMP 00005898)
(00005895 15 12 0		JMP 000058A4)
(00005898 9 22 0		'list-box-contents)
(0000589B 5 0		UnVar0)
(0000589D 81 2 202 1 1 0		no-applicable-method)
(000058A3 10)
(000058A4 5 0		UnVar0)
(000058A6 5 1		UnVar1)
(000058A8 46 1		invoke+ret)
;;;def list-box-contents<- 22698
(000058AA 20 3 2 2 0)
(000058AF 9 21 0		'list-box-contents<-)
(000058B2 5 0		UnVar0)
(000058B4 81 2 204 1 1 0		compute-applicable-methods)
(000058BA 8 2		UnVar2)
(000058BC 5 2		UnVar2)
(000058BE 13 3 0		nil->JMP 000058C4)
(000058C1 15 14 0		JMP 000058D2)
(000058C4 9 21 0		'list-box-contents<-)
(000058C7 5 0		UnVar0)
(000058C9 5 1		UnVar1)
(000058CB 81 3 202 1 1 0		no-applicable-method)
(000058D1 10)
(000058D2 5 0		UnVar0)
(000058D4 5 1		UnVar1)
(000058D6 5 2		UnVar2)
(000058D8 46 2		invoke+ret)
;;;def list-box-sort 22746
(000058DA 20 2 1 1 0)
(000058DF 9 20 0		'list-box-sort)
(000058E2 5 0		UnVar0)
(000058E4 81 2 204 1 1 0		compute-applicable-methods)
(000058EA 8 1		UnVar1)
(000058EC 5 1		UnVar1)
(000058EE 13 3 0		nil->JMP 000058F4)
(000058F1 15 12 0		JMP 00005900)
(000058F4 9 20 0		'list-box-sort)
(000058F7 5 0		UnVar0)
(000058F9 81 2 202 1 1 0		no-applicable-method)
(000058FF 10)
(00005900 5 0		UnVar0)
(00005902 5 1		UnVar1)
(00005904 46 1		invoke+ret)
;;;def list-box-sort-order<- 22790
(00005906 20 3 2 2 0)
(0000590B 9 19 0		'list-box-sort-order<-)
(0000590E 5 0		UnVar0)
(00005910 81 2 204 1 1 0		compute-applicable-methods)
(00005916 8 2		UnVar2)
(00005918 5 2		UnVar2)
(0000591A 13 3 0		nil->JMP 00005920)
(0000591D 15 14 0		JMP 0000592E)
(00005920 9 19 0		'list-box-sort-order<-)
(00005923 5 0		UnVar0)
(00005925 5 1		UnVar1)
(00005927 81 3 202 1 1 0		no-applicable-method)
(0000592D 10)
(0000592E 5 0		UnVar0)
(00005930 5 1		UnVar1)
(00005932 5 2		UnVar2)
(00005934 46 2		invoke+ret)
;;;def list-box-sort-order 22838
(00005936 20 2 1 1 0)
(0000593B 9 18 0		'list-box-sort-order)
(0000593E 5 0		UnVar0)
(00005940 81 2 204 1 1 0		compute-applicable-methods)
(00005946 8 1		UnVar1)
(00005948 5 1		UnVar1)
(0000594A 13 3 0		nil->JMP 00005950)
(0000594D 15 12 0		JMP 0000595C)
(00005950 9 18 0		'list-box-sort-order)
(00005953 5 0		UnVar0)
(00005955 81 2 202 1 1 0		no-applicable-method)
(0000595B 10)
(0000595C 5 0		UnVar0)
(0000595E 5 1		UnVar1)
(00005960 46 1		invoke+ret)
;;;def list-box-empty 22882
(00005962 20 2 1 1 0)
(00005967 9 17 0		'list-box-empty)
(0000596A 5 0		UnVar0)
(0000596C 81 2 204 1 1 0		compute-applicable-methods)
(00005972 8 1		UnVar1)
(00005974 5 1		UnVar1)
(00005976 13 3 0		nil->JMP 0000597C)
(00005979 15 12 0		JMP 00005988)
(0000597C 9 17 0		'list-box-empty)
(0000597F 5 0		UnVar0)
(00005981 81 2 202 1 1 0		no-applicable-method)
(00005987 10)
(00005988 5 0		UnVar0)
(0000598A 5 1		UnVar1)
(0000598C 46 1		invoke+ret)
;;;def LIST-BOX-ITEMS-UP 22926
(0000598E 20 2 1 1 0)
(00005993 9 16 0		'LIST-BOX-ITEMS-UP)
(00005996 5 0		UnVar0)
(00005998 81 2 204 1 1 0		compute-applicable-methods)
(0000599E 8 1		UnVar1)
(000059A0 5 1		UnVar1)
(000059A2 13 3 0		nil->JMP 000059A8)
(000059A5 15 12 0		JMP 000059B4)
(000059A8 9 16 0		'LIST-BOX-ITEMS-UP)
(000059AB 5 0		UnVar0)
(000059AD 81 2 202 1 1 0		no-applicable-method)
(000059B3 10)
(000059B4 5 0		UnVar0)
(000059B6 5 1		UnVar1)
(000059B8 46 1		invoke+ret)
;;;def LIST-BOX-ITEMS-DOWN 22970
(000059BA 20 2 1 1 0)
(000059BF 9 15 0		'LIST-BOX-ITEMS-DOWN)
(000059C2 5 0		UnVar0)
(000059C4 81 2 204 1 1 0		compute-applicable-methods)
(000059CA 8 1		UnVar1)
(000059CC 5 1		UnVar1)
(000059CE 13 3 0		nil->JMP 000059D4)
(000059D1 15 12 0		JMP 000059E0)
(000059D4 9 15 0		'LIST-BOX-ITEMS-DOWN)
(000059D7 5 0		UnVar0)
(000059D9 81 2 202 1 1 0		no-applicable-method)
(000059DF 10)
(000059E0 5 0		UnVar0)
(000059E2 5 1		UnVar1)
(000059E4 46 1		invoke+ret)
;;;def LIST-BOX-ITEMS-TOP 23014
(000059E6 20 2 1 1 0)
(000059EB 9 14 0		'LIST-BOX-ITEMS-TOP)
(000059EE 5 0		UnVar0)
(000059F0 81 2 204 1 1 0		compute-applicable-methods)
(000059F6 8 1		UnVar1)
(000059F8 5 1		UnVar1)
(000059FA 13 3 0		nil->JMP 00005A00)
(000059FD 15 12 0		JMP 00005A0C)
(00005A00 9 14 0		'LIST-BOX-ITEMS-TOP)
(00005A03 5 0		UnVar0)
(00005A05 81 2 202 1 1 0		no-applicable-method)
(00005A0B 10)
(00005A0C 5 0		UnVar0)
(00005A0E 5 1		UnVar1)
(00005A10 46 1		invoke+ret)
;;;def LIST-BOX-ITEMS-BOTTOM 23058
(00005A12 20 2 1 1 0)
(00005A17 9 13 0		'LIST-BOX-ITEMS-BOTTOM)
(00005A1A 5 0		UnVar0)
(00005A1C 81 2 204 1 1 0		compute-applicable-methods)
(00005A22 8 1		UnVar1)
(00005A24 5 1		UnVar1)
(00005A26 13 3 0		nil->JMP 00005A2C)
(00005A29 15 12 0		JMP 00005A38)
(00005A2C 9 13 0		'LIST-BOX-ITEMS-BOTTOM)
(00005A2F 5 0		UnVar0)
(00005A31 81 2 202 1 1 0		no-applicable-method)
(00005A37 10)
(00005A38 5 0		UnVar0)
(00005A3A 5 1		UnVar1)
(00005A3C 46 1		invoke+ret)
;;;def LIST-BOX-MOVEABLE-P 23102
(00005A3E 20 3 2 2 0)
(00005A43 9 12 0		'LIST-BOX-MOVEABLE-P)
(00005A46 5 0		UnVar0)
(00005A48 81 2 204 1 1 0		compute-applicable-methods)
(00005A4E 8 2		UnVar2)
(00005A50 5 2		UnVar2)
(00005A52 13 3 0		nil->JMP 00005A58)
(00005A55 15 14 0		JMP 00005A66)
(00005A58 9 12 0		'LIST-BOX-MOVEABLE-P)
(00005A5B 5 0		UnVar0)
(00005A5D 5 1		UnVar1)
(00005A5F 81 3 202 1 1 0		no-applicable-method)
(00005A65 10)
(00005A66 5 0		UnVar0)
(00005A68 5 1		UnVar1)
(00005A6A 5 2		UnVar2)
(00005A6C 46 2		invoke+ret)
;;;def list-box-select-all 23150
(00005A6E 20 5 1 1 0)
(00005A73 100 1		UNVar1)
(00005A75 100 2		UNVar2)
(00005A77 5 0		UnVar0)
(00005A79 44 4		IDFun4)
(00005A7B 8 2		UnVar2)
(00005A7D 5 2		UnVar2)
(00005A7F 8 3		UnVar3)
(00005A81 100 4		UNVar4)
(00005A83 15 5 0		JMP 00005A8B)
(00005A86 5 3		UnVar3)
(00005A88 41		cdr)
(00005A89 8 3		UnVar3)
(00005A8B 5 3		UnVar3)
(00005A8D 61 8 0		nil->JMP 00005A98)
(00005A90 5 3		UnVar3)
(00005A92 40		car)
(00005A93 41		cdr)
(00005A94 11)
(00005A95 8 4		UnVar4)
(00005A97 35		not)
(00005A98 60 235 255		T->JMP 00005A86)
(00005A9B 5 4		UnVar4)
(00005A9D 35		not)
(00005A9E 8 1		UnVar1)
(00005AA0 5 2		UnVar2)
(00005AA2 8 3		UnVar3)
(00005AA4 100 4		UNVar4)
(00005AA6 15 21 0		JMP 00005ABE)
(00005AA9 5 3		UnVar3)
(00005AAB 40		car)
(00005AAC 8 4		UnVar4)
(00005AAE 5 3		UnVar3)
(00005AB0 41		cdr)
(00005AB1 8 3		UnVar3)
(00005AB3 5 4		UnVar4)
(00005AB5 5 1		UnVar1)
(00005AB7 81 2 211 0 1 0		setcdr)
(00005ABD 10)
(00005ABE 5 3		UnVar3)
(00005AC0 60 230 255		T->JMP 00005AA9)
(00005AC3 5 1		UnVar1)
(00005AC5 22		ret)
;;;def list-box.list-box-selection 23238
(00005AC6 20 4 1 1 0)
(00005ACB 5 0		UnVar0)
(00005ACD 8 1		UnVar1)
(00005ACF 9 11 0		'cdr)
(00005AD2 5 1		UnVar1)
(00005AD4 44 4		IDFun4)
(00005AD6 81 2 10 0 1 0		remove-if-not)
(00005ADC 8 2		UnVar2)
(00005ADE 100 3		UNVar3)
(00005AE0 15 14 0		JMP 00005AF1)
(00005AE3 5 2		UnVar2)
(00005AE5 40		car)
(00005AE6 40		car)
(00005AE7 5 3		UnVar3)
(00005AE9 42		cons)
(00005AEA 8 3		UnVar3)
(00005AEC 5 2		UnVar2)
(00005AEE 41		cdr)
(00005AEF 8 2		UnVar2)
(00005AF1 5 2		UnVar2)
(00005AF3 60 237 255		T->JMP 00005AE3)
(00005AF6 5 3		UnVar3)
(00005AF8 81 1 196 1 1 0		nreverse)
(00005AFE 22		ret)
;;;def list-box.list-box-erase-selection 23295
(00005AFF 20 2 1 1 0)
(00005B04 5 0		UnVar0)
(00005B06 8 1		UnVar1)
(00005B08 9 11 0		'cdr)
(00005B0B 5 1		UnVar1)
(00005B0D 44 4		IDFun4)
(00005B0F 81 2 9 0 1 0		delete-if)
(00005B15 5 1		UnVar1)
(00005B17 45 4		IDFun4)
(00005B19 10)
(00005B1A 5 0		UnVar0)
(00005B1C 22		ret)
;;;def list-box.list-box-set-selection 23325
(00005B1D 20 7 3 3 0)
(00005B22 100 3		UNVar3)
(00005B24 5 0		UnVar0)
(00005B26 8 4		UnVar4)
(00005B28 5 1		UnVar1)
(00005B2A 8 5		UnVar5)
(00005B2C 100 6		UNVar6)
(00005B2E 15 39 0		JMP 00005B58)
(00005B31 5 5		UnVar5)
(00005B33 40		car)
(00005B34 8 6		UnVar6)
(00005B36 5 5		UnVar5)
(00005B38 41		cdr)
(00005B39 8 5		UnVar5)
(00005B3B 5 6		UnVar6)
(00005B3D 5 4		UnVar4)
(00005B3F 44 4		IDFun4)
(00005B41 81 2 29 0 1 0		assoc)
(00005B47 11)
(00005B48 8 3		UnVar3)
(00005B4A 13 11 0		nil->JMP 00005B58)
(00005B4D 5 3		UnVar3)
(00005B4F 5 2		UnVar2)
(00005B51 81 2 211 0 1 0		setcdr)
(00005B57 10)
(00005B58 5 5		UnVar5)
(00005B5A 60 212 255		T->JMP 00005B31)
(00005B5D 5 0		UnVar0)
(00005B5F 22		ret)
;;;def list-box.list-box-add-items 23392
(00005B60 20 13 2 4 0)
(00005B65 100 4		UNVar4)
(00005B67 100 5		UNVar5)
(00005B69 100 6		UNVar6)
(00005B6B 100 7		UNVar7)
(00005B6D 100 8		UNVar8)
(00005B6F 5 0		UnVar0)
(00005B71 8 9		UnVar9)
(00005B73 5 1		UnVar1)
(00005B75 5 9		UnVar9)
(00005B77 44 4		IDFun4)
(00005B79 95 2 137 86 0 0		func 00005689)
(00005B7F 8 10		UnVar10)
(00005B81 5 10		UnVar10)
(00005B83 40		car)
(00005B84 8 7		UnVar7)
(00005B86 5 10		UnVar10)
(00005B88 41		cdr)
(00005B89 8 8		UnVar8)
(00005B8B 5 7		UnVar7)
(00005B8D 13 99 0		nil->JMP 00005BF3)
(00005B90 5 9		UnVar9)
(00005B92 44 4		IDFun4)
(00005B94 8 4		UnVar4)
(00005B96 9 11 0		'cdr)
(00005B99 5 4		UnVar4)
(00005B9B 81 2 8 0 1 0		member-if)
(00005BA1 8 5		UnVar5)
(00005BA3 5 7		UnVar7)
(00005BA5 8 10		UnVar10)
(00005BA7 5 3		UnVar3)
(00005BA9 53 1 245 0 1 32		circle-list)
(00005BAF 8 11		UnVar11)
(00005BB1 100 12		UNVar12)
(00005BB3 15 22 0		JMP 00005BCC)
(00005BB6 5 10		UnVar10)
(00005BB8 40		car)
(00005BB9 5 11		UnVar11)
(00005BBB 40		car)
(00005BBC 42		cons)
(00005BBD 5 12		UnVar12)
(00005BBF 42		cons)
(00005BC0 8 12		UnVar12)
(00005BC2 5 10		UnVar10)
(00005BC4 41		cdr)
(00005BC5 8 10		UnVar10)
(00005BC7 5 11		UnVar11)
(00005BC9 41		cdr)
(00005BCA 8 11		UnVar11)
(00005BCC 5 10		UnVar10)
(00005BCE 61 2 0		nil->JMP 00005BD3)
(00005BD1 5 11		UnVar11)
(00005BD3 60 224 255		T->JMP 00005BB6)
(00005BD6 5 12		UnVar12)
(00005BD8 81 1 196 1 1 0		nreverse)
(00005BDE 8 6		UnVar6)
(00005BE0 5 4		UnVar4)
(00005BE2 5 5		UnVar5)
(00005BE4 5 6		UnVar6)
(00005BE6 5 2		UnVar2)
(00005BE8 95 4 218 86 0 0		ninsert-list)
(00005BEE 5 9		UnVar9)
(00005BF0 45 4		IDFun4)
(00005BF2 10)
(00005BF3 5 8		UnVar8)
(00005BF5 63		nil->ret)
(00005BF6 5 7		UnVar7)
(00005BF8 5 8		UnVar8)
(00005BFA 42		cons)
(00005BFB 22		ret)
;;;def list-box.list-box-items 23548
(00005BFC 20 2 1 1 0)
(00005C01 5 0		UnVar0)
(00005C03 8 1		UnVar1)
(00005C05 5 1		UnVar1)
(00005C07 44 4		IDFun4)
(00005C09 22		ret)
;;;def list-box.list-box-items<- 23562
(00005C0A 20 3 2 2 0)
(00005C0F 5 0		UnVar0)
(00005C11 8 2		UnVar2)
(00005C13 5 1		UnVar1)
(00005C15 5 2		UnVar2)
(00005C17 45 4		IDFun4)
(00005C19 10)
(00005C1A 5 0		UnVar0)
(00005C1C 22		ret)
;;;def list-box.list-box-contents 23581
(00005C1D 20 4 1 1 0)
(00005C22 5 0		UnVar0)
(00005C24 8 1		UnVar1)
(00005C26 5 1		UnVar1)
(00005C28 44 4		IDFun4)
(00005C2A 8 2		UnVar2)
(00005C2C 100 3		UNVar3)
(00005C2E 15 14 0		JMP 00005C3F)
(00005C31 5 2		UnVar2)
(00005C33 40		car)
(00005C34 40		car)
(00005C35 5 3		UnVar3)
(00005C37 42		cons)
(00005C38 8 3		UnVar3)
(00005C3A 5 2		UnVar2)
(00005C3C 41		cdr)
(00005C3D 8 2		UnVar2)
(00005C3F 5 2		UnVar2)
(00005C41 60 237 255		T->JMP 00005C31)
(00005C44 5 3		UnVar3)
(00005C46 81 1 196 1 1 0		nreverse)
(00005C4C 22		ret)
;;;def list-box.list-box-contents<- 23629
(00005C4D 20 5 2 2 0)
(00005C52 5 0		UnVar0)
(00005C54 8 2		UnVar2)
(00005C56 5 1		UnVar1)
(00005C58 8 3		UnVar3)
(00005C5A 100 4		UNVar4)
(00005C5C 15 19 0		JMP 00005C72)
(00005C5F 5 3		UnVar3)
(00005C61 40		car)
(00005C62 81 1 7 0 1 0		ncons)
(00005C68 5 4		UnVar4)
(00005C6A 42		cons)
(00005C6B 8 4		UnVar4)
(00005C6D 5 3		UnVar3)
(00005C6F 41		cdr)
(00005C70 8 3		UnVar3)
(00005C72 5 3		UnVar3)
(00005C74 60 232 255		T->JMP 00005C5F)
(00005C77 5 4		UnVar4)
(00005C79 81 1 196 1 1 0		nreverse)
(00005C7F 5 2		UnVar2)
(00005C81 45 4		IDFun4)
(00005C83 10)
(00005C84 5 0		UnVar0)
(00005C86 22		ret)
;;;def list-box.list-box-sort 23687
(00005C87 20 2 1 1 0)
(00005C8C 5 0		UnVar0)
(00005C8E 8 1		UnVar1)
(00005C90 5 1		UnVar1)
(00005C92 44 4		IDFun4)
(00005C94 95 1 59 86 0 0		sort-by-car-string)
(00005C9A 5 1		UnVar1)
(00005C9C 45 4		IDFun4)
(00005C9E 22		ret)
;;;def list-box.list-box-empty 23711
(00005C9F 20 2 1 1 0)
(00005CA4 5 0		UnVar0)
(00005CA6 8 1		UnVar1)
(00005CA8 1		nil)
(00005CA9 5 1		UnVar1)
(00005CAB 45 4		IDFun4)
(00005CAD 22		ret)
;;;def list-box.list-box-items-up 23726
(00005CAE 20 8 1 1 0)
(00005CB3 100 1		UNVar1)
(00005CB5 100 2		UNVar2)
(00005CB7 100 3		UNVar3)
(00005CB9 5 0		UnVar0)
(00005CBB 8 4		UnVar4)
(00005CBD 5 0		UnVar0)
(00005CBF 1		nil)
(00005CC0 95 2 62 90 0 0		LIST-BOX-MOVEABLE-P)
(00005CC6 11)
(00005CC7 8 1		UnVar1)
(00005CC9 63		nil->ret)
(00005CCA 5 4		UnVar4)
(00005CCC 44 4		IDFun4)
(00005CCE 8 2		UnVar2)
(00005CD0 15 37 0		JMP 00005CF8)
(00005CD3 5 2		UnVar2)
(00005CD5 41		cdr)
(00005CD6 40		car)
(00005CD7 40		car)
(00005CD8 5 1		UnVar1)
(00005CDA 40		car)
(00005CDB 81 2 0 1 1 0		equal)
(00005CE1 13 7 0		nil->JMP 00005CEB)
(00005CE4 5 2		UnVar2)
(00005CE6 8 3		UnVar3)
(00005CE8 15 13 0		JMP 00005CF8)
(00005CEB 5 2		UnVar2)
(00005CED 8 5		UnVar5)
(00005CEF 5 5		UnVar5)
(00005CF1 41		cdr)
(00005CF2 8 2		UnVar2)
(00005CF4 5 5		UnVar5)
(00005CF6 40		car)
(00005CF7 10)
(00005CF8 5 2		UnVar2)
(00005CFA 61 9 0		nil->JMP 00005D06)
(00005CFD 5 2		UnVar2)
(00005CFF 41		cdr)
(00005D00 61 3 0		nil->JMP 00005D06)
(00005D03 5 3		UnVar3)
(00005D05 35		not)
(00005D06 60 202 255		T->JMP 00005CD3)
(00005D09 5 0		UnVar0)
(00005D0B 95 1 141 87 0 0		list-box-erase-selection)
(00005D11 10)
(00005D12 5 4		UnVar4)
(00005D14 44 4		IDFun4)
(00005D16 5 3		UnVar3)
(00005D18 5 1		UnVar1)
(00005D1A 8 5		UnVar5)
(00005D1C 2		T)
(00005D1D 53 1 245 0 1 32		circle-list)
(00005D23 8 6		UnVar6)
(00005D25 100 7		UNVar7)
(00005D27 15 22 0		JMP 00005D40)
(00005D2A 5 5		UnVar5)
(00005D2C 40		car)
(00005D2D 5 6		UnVar6)
(00005D2F 40		car)
(00005D30 42		cons)
(00005D31 5 7		UnVar7)
(00005D33 42		cons)
(00005D34 8 7		UnVar7)
(00005D36 5 5		UnVar5)
(00005D38 41		cdr)
(00005D39 8 5		UnVar5)
(00005D3B 5 6		UnVar6)
(00005D3D 41		cdr)
(00005D3E 8 6		UnVar6)
(00005D40 5 5		UnVar5)
(00005D42 61 2 0		nil->JMP 00005D47)
(00005D45 5 6		UnVar6)
(00005D47 60 224 255		T->JMP 00005D2A)
(00005D4A 5 7		UnVar7)
(00005D4C 81 1 196 1 1 0		nreverse)
(00005D52 95 3 218 86 0 0		ninsert-list)
(00005D58 5 4		UnVar4)
(00005D5A 45 4		IDFun4)
(00005D5C 10)
(00005D5D 2		T)
(00005D5E 22		ret)
;;;def list-box.list-box-items-down 23903
(00005D5F 20 9 1 1 0)
(00005D64 100 1		UNVar1)
(00005D66 100 2		UNVar2)
(00005D68 100 3		UNVar3)
(00005D6A 100 4		UNVar4)
(00005D6C 5 0		UnVar0)
(00005D6E 8 5		UnVar5)
(00005D70 5 0		UnVar0)
(00005D72 2		T)
(00005D73 95 2 62 90 0 0		LIST-BOX-MOVEABLE-P)
(00005D79 11)
(00005D7A 8 1		UnVar1)
(00005D7C 63		nil->ret)
(00005D7D 5 5		UnVar5)
(00005D7F 44 4		IDFun4)
(00005D81 8 3		UnVar3)
(00005D83 5 1		UnVar1)
(00005D85 81 1 115 0 1 0		last)
(00005D8B 40		car)
(00005D8C 8 2		UnVar2)
(00005D8E 15 35 0		JMP 00005DB4)
(00005D91 5 3		UnVar3)
(00005D93 40		car)
(00005D94 40		car)
(00005D95 5 2		UnVar2)
(00005D97 81 2 0 1 1 0		equal)
(00005D9D 13 7 0		nil->JMP 00005DA7)
(00005DA0 5 3		UnVar3)
(00005DA2 8 4		UnVar4)
(00005DA4 15 13 0		JMP 00005DB4)
(00005DA7 5 3		UnVar3)
(00005DA9 8 6		UnVar6)
(00005DAB 5 6		UnVar6)
(00005DAD 41		cdr)
(00005DAE 8 3		UnVar3)
(00005DB0 5 6		UnVar6)
(00005DB2 40		car)
(00005DB3 10)
(00005DB4 5 3		UnVar3)
(00005DB6 61 9 0		nil->JMP 00005DC2)
(00005DB9 5 3		UnVar3)
(00005DBB 41		cdr)
(00005DBC 61 3 0		nil->JMP 00005DC2)
(00005DBF 5 4		UnVar4)
(00005DC1 35		not)
(00005DC2 60 204 255		T->JMP 00005D91)
(00005DC5 5 4		UnVar4)
(00005DC7 8 6		UnVar6)
(00005DC9 5 6		UnVar6)
(00005DCB 41		cdr)
(00005DCC 8 4		UnVar4)
(00005DCE 5 6		UnVar6)
(00005DD0 40		car)
(00005DD1 10)
(00005DD2 5 0		UnVar0)
(00005DD4 95 1 141 87 0 0		list-box-erase-selection)
(00005DDA 10)
(00005DDB 5 5		UnVar5)
(00005DDD 44 4		IDFun4)
(00005DDF 5 4		UnVar4)
(00005DE1 5 1		UnVar1)
(00005DE3 8 6		UnVar6)
(00005DE5 2		T)
(00005DE6 53 1 245 0 1 32		circle-list)
(00005DEC 8 7		UnVar7)
(00005DEE 100 8		UNVar8)
(00005DF0 15 22 0		JMP 00005E09)
(00005DF3 5 6		UnVar6)
(00005DF5 40		car)
(00005DF6 5 7		UnVar7)
(00005DF8 40		car)
(00005DF9 42		cons)
(00005DFA 5 8		UnVar8)
(00005DFC 42		cons)
(00005DFD 8 8		UnVar8)
(00005DFF 5 6		UnVar6)
(00005E01 41		cdr)
(00005E02 8 6		UnVar6)
(00005E04 5 7		UnVar7)
(00005E06 41		cdr)
(00005E07 8 7		UnVar7)
(00005E09 5 6		UnVar6)
(00005E0B 61 2 0		nil->JMP 00005E10)
(00005E0E 5 7		UnVar7)
(00005E10 60 224 255		T->JMP 00005DF3)
(00005E13 5 8		UnVar8)
(00005E15 81 1 196 1 1 0		nreverse)
(00005E1B 2		T)
(00005E1C 95 4 218 86 0 0		ninsert-list)
(00005E22 5 5		UnVar5)
(00005E24 45 4		IDFun4)
(00005E26 10)
(00005E27 2		T)
(00005E28 22		ret)
;;;def list-box.list-box-items-top 24105
(00005E29 20 6 1 1 0)
(00005E2E 100 1		UNVar1)
(00005E30 5 0		UnVar0)
(00005E32 8 2		UnVar2)
(00005E34 5 0		UnVar0)
(00005E36 1		nil)
(00005E37 95 2 62 90 0 0		LIST-BOX-MOVEABLE-P)
(00005E3D 11)
(00005E3E 8 1		UnVar1)
(00005E40 63		nil->ret)
(00005E41 5 0		UnVar0)
(00005E43 95 1 141 87 0 0		list-box-erase-selection)
(00005E49 10)
(00005E4A 5 1		UnVar1)
(00005E4C 8 3		UnVar3)
(00005E4E 2		T)
(00005E4F 53 1 245 0 1 32		circle-list)
(00005E55 8 4		UnVar4)
(00005E57 100 5		UNVar5)
(00005E59 15 22 0		JMP 00005E72)
(00005E5C 5 3		UnVar3)
(00005E5E 40		car)
(00005E5F 5 4		UnVar4)
(00005E61 40		car)
(00005E62 42		cons)
(00005E63 5 5		UnVar5)
(00005E65 42		cons)
(00005E66 8 5		UnVar5)
(00005E68 5 3		UnVar3)
(00005E6A 41		cdr)
(00005E6B 8 3		UnVar3)
(00005E6D 5 4		UnVar4)
(00005E6F 41		cdr)
(00005E70 8 4		UnVar4)
(00005E72 5 3		UnVar3)
(00005E74 61 2 0		nil->JMP 00005E79)
(00005E77 5 4		UnVar4)
(00005E79 60 224 255		T->JMP 00005E5C)
(00005E7C 5 5		UnVar5)
(00005E7E 81 1 196 1 1 0		nreverse)
(00005E84 5 2		UnVar2)
(00005E86 44 4		IDFun4)
(00005E88 81 2 195 1 1 0		nconc)
(00005E8E 5 2		UnVar2)
(00005E90 45 4		IDFun4)
(00005E92 10)
(00005E93 2		T)
(00005E94 22		ret)
;;;def list-box.list-box-items-bottom 24213
(00005E95 20 6 1 1 0)
(00005E9A 100 1		UNVar1)
(00005E9C 5 0		UnVar0)
(00005E9E 8 2		UnVar2)
(00005EA0 5 0		UnVar0)
(00005EA2 2		T)
(00005EA3 95 2 62 90 0 0		LIST-BOX-MOVEABLE-P)
(00005EA9 11)
(00005EAA 8 1		UnVar1)
(00005EAC 63		nil->ret)
(00005EAD 5 0		UnVar0)
(00005EAF 95 1 141 87 0 0		list-box-erase-selection)
(00005EB5 10)
(00005EB6 5 2		UnVar2)
(00005EB8 44 4		IDFun4)
(00005EBA 5 1		UnVar1)
(00005EBC 8 3		UnVar3)
(00005EBE 2		T)
(00005EBF 53 1 245 0 1 32		circle-list)
(00005EC5 8 4		UnVar4)
(00005EC7 100 5		UNVar5)
(00005EC9 15 22 0		JMP 00005EE2)
(00005ECC 5 3		UnVar3)
(00005ECE 40		car)
(00005ECF 5 4		UnVar4)
(00005ED1 40		car)
(00005ED2 42		cons)
(00005ED3 5 5		UnVar5)
(00005ED5 42		cons)
(00005ED6 8 5		UnVar5)
(00005ED8 5 3		UnVar3)
(00005EDA 41		cdr)
(00005EDB 8 3		UnVar3)
(00005EDD 5 4		UnVar4)
(00005EDF 41		cdr)
(00005EE0 8 4		UnVar4)
(00005EE2 5 3		UnVar3)
(00005EE4 61 2 0		nil->JMP 00005EE9)
(00005EE7 5 4		UnVar4)
(00005EE9 60 224 255		T->JMP 00005ECC)
(00005EEC 5 5		UnVar5)
(00005EEE 81 1 196 1 1 0		nreverse)
(00005EF4 81 2 195 1 1 0		nconc)
(00005EFA 5 2		UnVar2)
(00005EFC 45 4		IDFun4)
(00005EFE 10)
(00005EFF 2		T)
(00005F00 22		ret)
;;;def list-box.list-box-moveable-p 24321
(00005F01 20 6 2 2 0)
(00005F06 100 2		UNVar2)
(00005F08 100 3		UNVar3)
(00005F0A 5 0		UnVar0)
(00005F0C 8 4		UnVar4)
(00005F0E 50 255		-1)
(00005F10 8 2		UnVar2)
(00005F12 5 4		UnVar4)
(00005F14 44 4		IDFun4)
(00005F16 8 5		UnVar5)
(00005F18 15 32 0		JMP 00005F3B)
(00005F1B 5 5		UnVar5)
(00005F1D 40		car)
(00005F1E 41		cdr)
(00005F1F 61 3 0		nil->JMP 00005F25)
(00005F22 5 3		UnVar3)
(00005F24 35		not)
(00005F25 13 8 0		nil->JMP 00005F30)
(00005F28 5 2		UnVar2)
(00005F2A 79		1+)
(00005F2B 8 2		UnVar2)
(00005F2D 15 0 0		JMP 00005F30)
(00005F30 5 5		UnVar5)
(00005F32 40		car)
(00005F33 41		cdr)
(00005F34 8 3		UnVar3)
(00005F36 5 5		UnVar5)
(00005F38 41		cdr)
(00005F39 8 5		UnVar5)
(00005F3B 5 5		UnVar5)
(00005F3D 13 13 0		nil->JMP 00005F4D)
(00005F40 5 2		UnVar2)
(00005F42 50 1		1)
(00005F44 81 2 6 0 1 0		>)
(00005F4A 15 1 0		JMP 00005F4E)
(00005F4D 2		T)
(00005F4E 35		not)
(00005F4F 60 201 255		T->JMP 00005F1B)
(00005F52 5 4		UnVar4)
(00005F54 44 4		IDFun4)
(00005F56 13 47 0		nil->JMP 00005F88)
(00005F59 5 2		UnVar2)
(00005F5B 50 0		0)
(00005F5D 38		=)
(00005F5E 13 37 0		nil->JMP 00005F86)
(00005F61 5 1		UnVar1)
(00005F63 13 13 0		nil->JMP 00005F73)
(00005F66 5 4		UnVar4)
(00005F68 44 4		IDFun4)
(00005F6A 81 1 115 0 1 0		last)
(00005F70 15 4 0		JMP 00005F77)
(00005F73 5 4		UnVar4)
(00005F75 44 4		IDFun4)
(00005F77 40		car)
(00005F78 41		cdr)
(00005F79 13 2 0		nil->JMP 00005F7E)
(00005F7C 1		nil)
(00005F7D 22		ret)
(00005F7E 5 0		UnVar0)
(00005F80 97 1 102 87 0 0		offset 00005766)
(00005F86 1		nil)
(00005F87 22		ret)
(00005F88 1		nil)
(00005F89 22		ret)
;;;def sorted-list-box.new-instance 24458
(00005F8A 20 11 3 3 1)
(00005F8F 5 3		UnVar3)
(00005F91 8 4		UnVar4)
(00005F93 5 4		UnVar4)
(00005F95 9 75 0		':MULTIPLE-SELECTION)
(00005F98 1		nil)
(00005F99 81 3 74 1 1 0		getf)
(00005F9F 8 5		UnVar5)
(00005FA1 5 4		UnVar4)
(00005FA3 9 112 1		':COMMAND)
(00005FA6 1		nil)
(00005FA7 81 3 74 1 1 0		getf)
(00005FAD 8 6		UnVar6)
(00005FAF 5 4		UnVar4)
(00005FB1 9 73 0		':SORT-P)
(00005FB4 1		nil)
(00005FB5 81 3 74 1 1 0		getf)
(00005FBB 8 7		UnVar7)
(00005FBD 5 4		UnVar4)
(00005FBF 9 72 0		':PROMPT)
(00005FC2 1		nil)
(00005FC3 81 3 74 1 1 0		getf)
(00005FC9 8 8		UnVar8)
(00005FCB 5 4		UnVar4)
(00005FCD 9 5 0		':SORT-FUN)
(00005FD0 1		nil)
(00005FD1 81 3 74 1 1 0		getf)
(00005FD7 8 9		UnVar9)
(00005FD9 5 0		UnVar0)
(00005FDB 8 10		UnVar10)
(00005FDD 5 0		UnVar0)
(00005FDF 5 1		UnVar1)
(00005FE1 9 150 1		"")
(00005FE4 5 6		UnVar6)
(00005FE6 95 4 216 14 0 0		dialog-item.new-instance)
(00005FEC 10)
(00005FED 5 9		UnVar9)
(00005FEF 14 3 0		T->JMP 00005FF5)
(00005FF2 9 209 1		'(22075 sort-by-car-string))
(00005FF5 5 10		UnVar10)
(00005FF7 45 7		IDFun7)
(00005FF9 10)
(00005FFA 5 7		UnVar7)
(00005FFC 5 10		UnVar10)
(00005FFE 45 8		IDFun8)
(00006000 10)
(00006001 5 5		UnVar5)
(00006003 5 10		UnVar10)
(00006005 45 5		IDFun5)
(00006007 10)
(00006008 5 8		UnVar8)
(0000600A 5 10		UnVar10)
(0000600C 45 3		IDFun3)
(0000600E 10)
(0000600F 5 7		UnVar7)
(00006011 13 12 0		nil->JMP 00006020)
(00006014 5 2		UnVar2)
(00006016 5 10		UnVar10)
(00006018 44 7		IDFun7)
(0000601A 52 1 1		)
(0000601D 15 2 0		JMP 00006022)
(00006020 5 2		UnVar2)
(00006022 5 10		UnVar10)
(00006024 45 4		IDFun4)
(00006026 10)
(00006027 5 0		UnVar0)
(00006029 22		ret)
;;;def sorted-list-box 24618
(0000602A 20 1 0 0 1)
(0000602F 9 208 1		'(24458 sorted-list-box.new-instance))
(00006032 9 4 0		'sorted-list-box)
(00006035 53 1 52 1 1 32		allocate-instance)
(0000603B 5 0		UnVar0)
(0000603D 42		cons)
(0000603E 84		apply+ret)
;;;def sorted-list-box.list-box-add-items 24639
(0000603F 20 11 2 4 0)
(00006044 5 0		UnVar0)
(00006046 8 4		UnVar4)
(00006048 5 4		UnVar4)
(0000604A 44 8		IDFun8)
(0000604C 13 129 0		nil->JMP 000060D0)
(0000604F 100 5		UNVar5)
(00006051 100 6		UNVar6)
(00006053 100 7		UNVar7)
(00006055 5 1		UnVar1)
(00006057 5 4		UnVar4)
(00006059 44 4		IDFun4)
(0000605B 95 2 137 86 0 0		func 00005689)
(00006061 8 8		UnVar8)
(00006063 5 8		UnVar8)
(00006065 40		car)
(00006066 8 6		UnVar6)
(00006068 5 8		UnVar8)
(0000606A 41		cdr)
(0000606B 8 7		UnVar7)
(0000606D 5 6		UnVar6)
(0000606F 13 85 0		nil->JMP 000060C7)
(00006072 5 6		UnVar6)
(00006074 8 8		UnVar8)
(00006076 5 3		UnVar3)
(00006078 53 1 245 0 1 32		circle-list)
(0000607E 8 9		UnVar9)
(00006080 100 10		UNVar10)
(00006082 15 22 0		JMP 0000609B)
(00006085 5 8		UnVar8)
(00006087 40		car)
(00006088 5 9		UnVar9)
(0000608A 40		car)
(0000608B 42		cons)
(0000608C 5 10		UnVar10)
(0000608E 42		cons)
(0000608F 8 10		UnVar10)
(00006091 5 8		UnVar8)
(00006093 41		cdr)
(00006094 8 8		UnVar8)
(00006096 5 9		UnVar9)
(00006098 41		cdr)
(00006099 8 9		UnVar9)
(0000609B 5 8		UnVar8)
(0000609D 61 2 0		nil->JMP 000060A2)
(000060A0 5 9		UnVar9)
(000060A2 60 224 255		T->JMP 00006085)
(000060A5 5 10		UnVar10)
(000060A7 81 1 196 1 1 0		nreverse)
(000060AD 8 5		UnVar5)
(000060AF 5 5		UnVar5)
(000060B1 5 4		UnVar4)
(000060B3 44 4		IDFun4)
(000060B5 81 2 195 1 1 0		nconc)
(000060BB 5 4		UnVar4)
(000060BD 44 7		IDFun7)
(000060BF 52 1 1		)
(000060C2 5 4		UnVar4)
(000060C4 45 4		IDFun4)
(000060C6 10)
(000060C7 5 7		UnVar7)
(000060C9 63		nil->ret)
(000060CA 5 6		UnVar6)
(000060CC 5 7		UnVar7)
(000060CE 42		cons)
(000060CF 22		ret)
(000060D0 5 0		UnVar0)
(000060D2 5 1		UnVar1)
(000060D4 5 2		UnVar2)
(000060D6 5 3		UnVar3)
(000060D8 96 4 96 91 0 0		list-box.list-box-add-items)
;;;def sorted-list-box.list-box-sort 24798
(000060DE 20 2 1 1 0)
(000060E3 5 0		UnVar0)
(000060E5 8 1		UnVar1)
(000060E7 5 1		UnVar1)
(000060E9 44 4		IDFun4)
(000060EB 5 1		UnVar1)
(000060ED 44 7		IDFun7)
(000060EF 52 1 1		)
(000060F2 5 1		UnVar1)
(000060F4 45 4		IDFun4)
(000060F6 10)
(000060F7 5 0		UnVar0)
(000060F9 22		ret)
;;;def sorted-list-box.list-box-sort-order 24826
(000060FA 20 2 1 1 0)
(000060FF 5 0		UnVar0)
(00006101 8 1		UnVar1)
(00006103 5 1		UnVar1)
(00006105 44 7		IDFun7)
(00006107 22		ret)
;;;def sorted-list-box.list-box-sort-order<- 24840
(00006108 20 3 2 2 0)
(0000610D 5 0		UnVar0)
(0000610F 8 2		UnVar2)
(00006111 5 1		UnVar1)
(00006113 5 2		UnVar2)
(00006115 45 7		IDFun7)
(00006117 10)
(00006118 5 2		UnVar2)
(0000611A 44 8		IDFun8)
(0000611C 13 14 0		nil->JMP 0000612D)
(0000611F 5 2		UnVar2)
(00006121 44 4		IDFun4)
(00006123 5 1		UnVar1)
(00006125 52 1 1		)
(00006128 5 2		UnVar2)
(0000612A 45 4		IDFun4)
(0000612C 10)
(0000612D 5 0		UnVar0)
(0000612F 22		ret)
;;;def sorted-list-box.LIST-BOX-MOVEABLE-P 24880
(00006130 20 3 2 2 0)
(00006135 5 0		UnVar0)
(00006137 8 2		UnVar2)
(00006139 5 2		UnVar2)
(0000613B 44 8		IDFun8)
(0000613D 13 2 0		nil->JMP 00006142)
(00006140 1		nil)
(00006141 22		ret)
(00006142 5 0		UnVar0)
(00006144 5 1		UnVar1)
(00006146 96 2 1 95 0 0		list-box.list-box-moveable-p)
;;;def shaded-list-box.new-instance 24908
(0000614C 20 14 3 3 1)
(00006151 5 3		UnVar3)
(00006153 8 4		UnVar4)
(00006155 5 4		UnVar4)
(00006157 9 75 0		':MULTIPLE-SELECTION)
(0000615A 1		nil)
(0000615B 81 3 74 1 1 0		getf)
(00006161 8 5		UnVar5)
(00006163 5 4		UnVar4)
(00006165 9 112 1		':COMMAND)
(00006168 1		nil)
(00006169 81 3 74 1 1 0		getf)
(0000616F 8 6		UnVar6)
(00006171 5 4		UnVar4)
(00006173 9 73 0		':SORT-P)
(00006176 1		nil)
(00006177 81 3 74 1 1 0		getf)
(0000617D 8 7		UnVar7)
(0000617F 5 4		UnVar4)
(00006181 9 72 0		':PROMPT)
(00006184 1		nil)
(00006185 81 3 74 1 1 0		getf)
(0000618B 8 8		UnVar8)
(0000618D 5 4		UnVar4)
(0000618F 9 5 0		':SORT-FUN)
(00006192 9 207 1		'(22113 sort-by-cadr-string))
(00006195 81 3 74 1 1 0		getf)
(0000619B 8 9		UnVar9)
(0000619D 5 4		UnVar4)
(0000619F 9 3 0		':SHOW-FUN)
(000061A2 9 149 0		'prin1-to-string)
(000061A5 81 3 74 1 1 0		getf)
(000061AB 8 10		UnVar10)
(000061AD 5 0		UnVar0)
(000061AF 8 11		UnVar11)
(000061B1 5 0		UnVar0)
(000061B3 5 1		UnVar1)
(000061B5 9 150 1		"")
(000061B8 5 6		UnVar6)
(000061BA 95 4 216 14 0 0		dialog-item.new-instance)
(000061C0 10)
(000061C1 5 9		UnVar9)
(000061C3 5 11		UnVar11)
(000061C5 45 7		IDFun7)
(000061C7 10)
(000061C8 5 5		UnVar5)
(000061CA 5 11		UnVar11)
(000061CC 45 5		IDFun5)
(000061CE 10)
(000061CF 5 7		UnVar7)
(000061D1 5 11		UnVar11)
(000061D3 45 8		IDFun8)
(000061D5 10)
(000061D6 5 8		UnVar8)
(000061D8 5 11		UnVar11)
(000061DA 45 3		IDFun3)
(000061DC 10)
(000061DD 5 10		UnVar10)
(000061DF 5 11		UnVar11)
(000061E1 45 9		IDFun9)
(000061E3 10)
(000061E4 5 0		UnVar0)
(000061E6 5 2		UnVar2)
(000061E8 95 2 41 99 0 0		func 00006329)
(000061EE 5 11		UnVar11)
(000061F0 45 10		IDFun10)
(000061F2 10)
(000061F3 5 7		UnVar7)
(000061F5 13 14 0		nil->JMP 00006206)
(000061F8 5 11		UnVar11)
(000061FA 44 10		IDFun10)
(000061FC 5 9		UnVar9)
(000061FE 52 1 1		)
(00006201 5 11		UnVar11)
(00006203 45 10		IDFun10)
(00006205 10)
(00006206 5 11		UnVar11)
(00006208 44 10		IDFun10)
(0000620A 8 12		UnVar12)
(0000620C 100 13		UNVar13)
(0000620E 15 14 0		JMP 0000621F)
(00006211 5 12		UnVar12)
(00006213 40		car)
(00006214 41		cdr)
(00006215 5 13		UnVar13)
(00006217 42		cons)
(00006218 8 13		UnVar13)
(0000621A 5 12		UnVar12)
(0000621C 41		cdr)
(0000621D 8 12		UnVar12)
(0000621F 5 12		UnVar12)
(00006221 60 237 255		T->JMP 00006211)
(00006224 5 13		UnVar13)
(00006226 81 1 196 1 1 0		nreverse)
(0000622C 5 11		UnVar11)
(0000622E 45 4		IDFun4)
(00006230 10)
(00006231 5 0		UnVar0)
(00006233 22		ret)
;;;def shaded-list-box 25140
(00006234 20 1 0 0 1)
(00006239 9 206 1		'(24908 shaded-list-box.new-instance))
(0000623C 9 2 0		'shaded-list-box)
(0000623F 53 1 52 1 1 32		allocate-instance)
(00006245 5 0		UnVar0)
(00006247 42		cons)
(00006248 84		apply+ret)
;;;def shaded-list-box.list-box-selection 25161
(00006249 20 4 1 1 0)
(0000624E 5 0		UnVar0)
(00006250 8 1		UnVar1)
(00006252 9 1 0		'cddr)
(00006255 5 1		UnVar1)
(00006257 44 10		IDFun10)
(00006259 81 2 10 0 1 0		remove-if-not)
(0000625F 8 2		UnVar2)
(00006261 100 3		UNVar3)
(00006263 15 14 0		JMP 00006274)
(00006266 5 2		UnVar2)
(00006268 40		car)
(00006269 40		car)
(0000626A 5 3		UnVar3)
(0000626C 42		cons)
(0000626D 8 3		UnVar3)
(0000626F 5 2		UnVar2)
(00006271 41		cdr)
(00006272 8 2		UnVar2)
(00006274 5 2		UnVar2)
(00006276 60 237 255		T->JMP 00006266)
(00006279 5 3		UnVar3)
(0000627B 81 1 196 1 1 0		nreverse)
(00006281 22		ret)
;;;def shaded-list-box.list-box-erase-selection 25218
(00006282 20 4 1 1 0)
(00006287 5 0		UnVar0)
(00006289 8 1		UnVar1)
(0000628B 9 1 0		'cddr)
(0000628E 5 1		UnVar1)
(00006290 44 10		IDFun10)
(00006292 81 2 9 0 1 0		delete-if)
(00006298 5 1		UnVar1)
(0000629A 45 10		IDFun10)
(0000629C 10)
(0000629D 5 1		UnVar1)
(0000629F 44 10		IDFun10)
(000062A1 8 2		UnVar2)
(000062A3 100 3		UNVar3)
(000062A5 15 14 0		JMP 000062B6)
(000062A8 5 2		UnVar2)
(000062AA 40		car)
(000062AB 41		cdr)
(000062AC 5 3		UnVar3)
(000062AE 42		cons)
(000062AF 8 3		UnVar3)
(000062B1 5 2		UnVar2)
(000062B3 41		cdr)
(000062B4 8 2		UnVar2)
(000062B6 5 2		UnVar2)
(000062B8 60 237 255		T->JMP 000062A8)
(000062BB 5 3		UnVar3)
(000062BD 81 1 196 1 1 0		nreverse)
(000062C3 5 1		UnVar1)
(000062C5 45 4		IDFun4)
(000062C7 10)
(000062C8 5 0		UnVar0)
(000062CA 22		ret)
;;;def shaded-list-box.list-box-set-selection 25291
(000062CB 20 7 3 3 0)
(000062D0 100 3		UNVar3)
(000062D2 5 0		UnVar0)
(000062D4 8 4		UnVar4)
(000062D6 5 1		UnVar1)
(000062D8 8 5		UnVar5)
(000062DA 100 6		UNVar6)
(000062DC 15 40 0		JMP 00006307)
(000062DF 5 5		UnVar5)
(000062E1 40		car)
(000062E2 8 6		UnVar6)
(000062E4 5 5		UnVar5)
(000062E6 41		cdr)
(000062E7 8 5		UnVar5)
(000062E9 5 6		UnVar6)
(000062EB 5 4		UnVar4)
(000062ED 44 10		IDFun10)
(000062EF 81 2 29 0 1 0		assoc)
(000062F5 11)
(000062F6 8 3		UnVar3)
(000062F8 13 12 0		nil->JMP 00006307)
(000062FB 5 3		UnVar3)
(000062FD 41		cdr)
(000062FE 5 2		UnVar2)
(00006300 81 2 211 0 1 0		setcdr)
(00006306 10)
(00006307 5 5		UnVar5)
(00006309 60 211 255		T->JMP 000062DF)
(0000630C 5 0		UnVar0)
(0000630E 22		ret)
;;;def nil 25359
(0000630F 20 2 2 2 0)
(00006314 5 1		UnVar1)
(00006316 40		car)
(00006317 5 1		UnVar1)
(00006319 40		car)
(0000631A 5 0		UnVar0)
(0000631C 52 1 1		)
(0000631F 5 1		UnVar1)
(00006321 41		cdr)
(00006322 81 3 203 1 1 0		list*)
(00006328 22		ret)
;;;def nil 25385
(00006329 20 6 2 2 0)
(0000632E 5 0		UnVar0)
(00006330 8 2		UnVar2)
(00006332 5 2		UnVar2)
(00006334 44 9		IDFun9)
(00006336 53 1 245 0 1 32		circle-list)
(0000633C 8 3		UnVar3)
(0000633E 5 1		UnVar1)
(00006340 8 4		UnVar4)
(00006342 100 5		UNVar5)
(00006344 15 27 0		JMP 00006362)
(00006347 5 3		UnVar3)
(00006349 40		car)
(0000634A 5 4		UnVar4)
(0000634C 40		car)
(0000634D 95 2 15 99 0 0		func 0000630F)
(00006353 5 5		UnVar5)
(00006355 42		cons)
(00006356 8 5		UnVar5)
(00006358 5 3		UnVar3)
(0000635A 41		cdr)
(0000635B 8 3		UnVar3)
(0000635D 5 4		UnVar4)
(0000635F 41		cdr)
(00006360 8 4		UnVar4)
(00006362 5 3		UnVar3)
(00006364 61 2 0		nil->JMP 00006369)
(00006367 5 4		UnVar4)
(00006369 60 219 255		T->JMP 00006347)
(0000636C 5 5		UnVar5)
(0000636E 81 1 196 1 1 0		nreverse)
(00006374 22		ret)
;;;def nil 25461
(00006375 20 6 2 2 0)
(0000637A 100 2		UNVar2)
(0000637C 100 3		UNVar3)
(0000637E 5 0		UnVar0)
(00006380 8 4		UnVar4)
(00006382 100 5		UNVar5)
(00006384 15 42 0		JMP 000063B1)
(00006387 5 4		UnVar4)
(00006389 40		car)
(0000638A 8 5		UnVar5)
(0000638C 5 4		UnVar4)
(0000638E 41		cdr)
(0000638F 8 4		UnVar4)
(00006391 5 5		UnVar5)
(00006393 41		cdr)
(00006394 40		car)
(00006395 5 1		UnVar1)
(00006397 81 2 29 0 1 0		assoc)
(0000639D 13 10 0		nil->JMP 000063AA)
(000063A0 5 5		UnVar5)
(000063A2 5 3		UnVar3)
(000063A4 42		cons)
(000063A5 8 3		UnVar3)
(000063A7 15 7 0		JMP 000063B1)
(000063AA 5 5		UnVar5)
(000063AC 5 2		UnVar2)
(000063AE 42		cons)
(000063AF 8 2		UnVar2)
(000063B1 5 4		UnVar4)
(000063B3 60 209 255		T->JMP 00006387)
(000063B6 5 2		UnVar2)
(000063B8 81 1 196 1 1 0		nreverse)
(000063BE 5 3		UnVar3)
(000063C0 81 1 196 1 1 0		nreverse)
(000063C6 42		cons)
(000063C7 22		ret)
;;;def shaded-list-box.list-box-add-items 25544
(000063C8 20 13 2 4 0)
(000063CD 100 4		UNVar4)
(000063CF 100 5		UNVar5)
(000063D1 100 6		UNVar6)
(000063D3 100 7		UNVar7)
(000063D5 100 8		UNVar8)
(000063D7 5 0		UnVar0)
(000063D9 8 9		UnVar9)
(000063DB 5 9		UnVar9)
(000063DD 44 10		IDFun10)
(000063DF 8 4		UnVar4)
(000063E1 5 0		UnVar0)
(000063E3 5 1		UnVar1)
(000063E5 8 10		UnVar10)
(000063E7 5 3		UnVar3)
(000063E9 53 1 245 0 1 32		circle-list)
(000063EF 8 11		UnVar11)
(000063F1 100 12		UNVar12)
(000063F3 15 22 0		JMP 0000640C)
(000063F6 5 10		UnVar10)
(000063F8 40		car)
(000063F9 5 11		UnVar11)
(000063FB 40		car)
(000063FC 42		cons)
(000063FD 5 12		UnVar12)
(000063FF 42		cons)
(00006400 8 12		UnVar12)
(00006402 5 10		UnVar10)
(00006404 41		cdr)
(00006405 8 10		UnVar10)
(00006407 5 11		UnVar11)
(00006409 41		cdr)
(0000640A 8 11		UnVar11)
(0000640C 5 10		UnVar10)
(0000640E 61 2 0		nil->JMP 00006413)
(00006411 5 11		UnVar11)
(00006413 60 224 255		T->JMP 000063F6)
(00006416 5 12		UnVar12)
(00006418 81 1 196 1 1 0		nreverse)
(0000641E 95 2 41 99 0 0		func 00006329)
(00006424 8 6		UnVar6)
(00006426 5 6		UnVar6)
(00006428 5 9		UnVar9)
(0000642A 44 4		IDFun4)
(0000642C 95 2 117 99 0 0		func 00006375)
(00006432 8 10		UnVar10)
(00006434 5 10		UnVar10)
(00006436 40		car)
(00006437 8 7		UnVar7)
(00006439 5 10		UnVar10)
(0000643B 41		cdr)
(0000643C 8 8		UnVar8)
(0000643E 5 7		UnVar7)
(00006440 13 75 0		nil->JMP 0000648E)
(00006443 9 1 0		'cddr)
(00006446 5 4		UnVar4)
(00006448 81 2 8 0 1 0		member-if)
(0000644E 8 5		UnVar5)
(00006450 5 4		UnVar4)
(00006452 5 5		UnVar5)
(00006454 5 7		UnVar7)
(00006456 5 2		UnVar2)
(00006458 95 4 218 86 0 0		ninsert-list)
(0000645E 5 9		UnVar9)
(00006460 45 10		IDFun10)
(00006462 10)
(00006463 5 9		UnVar9)
(00006465 44 10		IDFun10)
(00006467 8 10		UnVar10)
(00006469 100 11		UNVar11)
(0000646B 15 14 0		JMP 0000647C)
(0000646E 5 10		UnVar10)
(00006470 40		car)
(00006471 41		cdr)
(00006472 5 11		UnVar11)
(00006474 42		cons)
(00006475 8 11		UnVar11)
(00006477 5 10		UnVar10)
(00006479 41		cdr)
(0000647A 8 10		UnVar10)
(0000647C 5 10		UnVar10)
(0000647E 60 237 255		T->JMP 0000646E)
(00006481 5 11		UnVar11)
(00006483 81 1 196 1 1 0		nreverse)
(00006489 5 9		UnVar9)
(0000648B 45 4		IDFun4)
(0000648D 10)
(0000648E 5 8		UnVar8)
(00006490 63		nil->ret)
(00006491 5 7		UnVar7)
(00006493 8 10		UnVar10)
(00006495 100 11		UNVar11)
(00006497 15 14 0		JMP 000064A8)
(0000649A 5 10		UnVar10)
(0000649C 40		car)
(0000649D 40		car)
(0000649E 5 11		UnVar11)
(000064A0 42		cons)
(000064A1 8 11		UnVar11)
(000064A3 5 10		UnVar10)
(000064A5 41		cdr)
(000064A6 8 10		UnVar10)
(000064A8 5 10		UnVar10)
(000064AA 60 237 255		T->JMP 0000649A)
(000064AD 5 11		UnVar11)
(000064AF 81 1 196 1 1 0		nreverse)
(000064B5 5 8		UnVar8)
(000064B7 8 10		UnVar10)
(000064B9 100 11		UNVar11)
(000064BB 15 14 0		JMP 000064CC)
(000064BE 5 10		UnVar10)
(000064C0 40		car)
(000064C1 40		car)
(000064C2 5 11		UnVar11)
(000064C4 42		cons)
(000064C5 8 11		UnVar11)
(000064C7 5 10		UnVar10)
(000064C9 41		cdr)
(000064CA 8 10		UnVar10)
(000064CC 5 10		UnVar10)
(000064CE 60 237 255		T->JMP 000064BE)
(000064D1 5 11		UnVar11)
(000064D3 81 1 196 1 1 0		nreverse)
(000064D9 42		cons)
(000064DA 22		ret)
;;;def shaded-list-box.list-box-items 25819
(000064DB 20 5 1 1 0)
(000064E0 5 0		UnVar0)
(000064E2 8 1		UnVar1)
(000064E4 5 1		UnVar1)
(000064E6 44 10		IDFun10)
(000064E8 8 2		UnVar2)
(000064EA 100 3		UNVar3)
(000064EC 15 23 0		JMP 00006506)
(000064EF 5 2		UnVar2)
(000064F1 40		car)
(000064F2 8 4		UnVar4)
(000064F4 5 4		UnVar4)
(000064F6 40		car)
(000064F7 5 4		UnVar4)
(000064F9 41		cdr)
(000064FA 41		cdr)
(000064FB 42		cons)
(000064FC 5 3		UnVar3)
(000064FE 42		cons)
(000064FF 8 3		UnVar3)
(00006501 5 2		UnVar2)
(00006503 41		cdr)
(00006504 8 2		UnVar2)
(00006506 5 2		UnVar2)
(00006508 60 228 255		T->JMP 000064EF)
(0000650B 5 3		UnVar3)
(0000650D 81 1 196 1 1 0		nreverse)
(00006513 22		ret)
;;;def shaded-list-box.list-box-items<- 25876
(00006514 20 5 2 2 0)
(00006519 5 0		UnVar0)
(0000651B 8 2		UnVar2)
(0000651D 5 0		UnVar0)
(0000651F 5 1		UnVar1)
(00006521 95 2 41 99 0 0		func 00006329)
(00006527 5 2		UnVar2)
(00006529 45 10		IDFun10)
(0000652B 10)
(0000652C 5 2		UnVar2)
(0000652E 44 10		IDFun10)
(00006530 8 3		UnVar3)
(00006532 100 4		UNVar4)
(00006534 15 14 0		JMP 00006545)
(00006537 5 3		UnVar3)
(00006539 40		car)
(0000653A 41		cdr)
(0000653B 5 4		UnVar4)
(0000653D 42		cons)
(0000653E 8 4		UnVar4)
(00006540 5 3		UnVar3)
(00006542 41		cdr)
(00006543 8 3		UnVar3)
(00006545 5 3		UnVar3)
(00006547 60 237 255		T->JMP 00006537)
(0000654A 5 4		UnVar4)
(0000654C 81 1 196 1 1 0		nreverse)
(00006552 5 2		UnVar2)
(00006554 45 4		IDFun4)
(00006556 10)
(00006557 5 0		UnVar0)
(00006559 22		ret)
;;;def shaded-list-box.list-box-sort 25946
(0000655A 20 4 1 1 0)
(0000655F 5 0		UnVar0)
(00006561 8 1		UnVar1)
(00006563 5 1		UnVar1)
(00006565 44 10		IDFun10)
(00006567 5 1		UnVar1)
(00006569 44 7		IDFun7)
(0000656B 52 1 1		)
(0000656E 5 1		UnVar1)
(00006570 45 10		IDFun10)
(00006572 10)
(00006573 5 1		UnVar1)
(00006575 44 10		IDFun10)
(00006577 8 2		UnVar2)
(00006579 100 3		UNVar3)
(0000657B 15 14 0		JMP 0000658C)
(0000657E 5 2		UnVar2)
(00006580 40		car)
(00006581 41		cdr)
(00006582 5 3		UnVar3)
(00006584 42		cons)
(00006585 8 3		UnVar3)
(00006587 5 2		UnVar2)
(00006589 41		cdr)
(0000658A 8 2		UnVar2)
(0000658C 5 2		UnVar2)
(0000658E 60 237 255		T->JMP 0000657E)
(00006591 5 3		UnVar3)
(00006593 81 1 196 1 1 0		nreverse)
(00006599 5 1		UnVar1)
(0000659B 45 4		IDFun4)
(0000659D 10)
(0000659E 5 0		UnVar0)
(000065A0 22		ret)
;;;def shaded-list-box.list-box-empty 26017
(000065A1 20 2 1 1 0)
(000065A6 5 0		UnVar0)
(000065A8 8 1		UnVar1)
(000065AA 1		nil)
(000065AB 5 1		UnVar1)
(000065AD 45 10		IDFun10)
(000065AF 10)
(000065B0 1		nil)
(000065B1 5 1		UnVar1)
(000065B3 45 4		IDFun4)
(000065B5 10)
(000065B6 5 0		UnVar0)
(000065B8 22		ret)
;;;def shaded-list-box.list-box-contents 26041
(000065B9 20 4 1 1 0)
(000065BE 5 0		UnVar0)
(000065C0 8 1		UnVar1)
(000065C2 5 1		UnVar1)
(000065C4 44 10		IDFun10)
(000065C6 8 2		UnVar2)
(000065C8 100 3		UNVar3)
(000065CA 15 14 0		JMP 000065DB)
(000065CD 5 2		UnVar2)
(000065CF 40		car)
(000065D0 40		car)
(000065D1 5 3		UnVar3)
(000065D3 42		cons)
(000065D4 8 3		UnVar3)
(000065D6 5 2		UnVar2)
(000065D8 41		cdr)
(000065D9 8 2		UnVar2)
(000065DB 5 2		UnVar2)
(000065DD 60 237 255		T->JMP 000065CD)
(000065E0 5 3		UnVar3)
(000065E2 81 1 196 1 1 0		nreverse)
(000065E8 22		ret)
;;;def shaded-list-box.list-box-contents<- 26089
(000065E9 20 7 2 2 0)
(000065EE 100 2		UNVar2)
(000065F0 5 0		UnVar0)
(000065F2 8 3		UnVar3)
(000065F4 5 3		UnVar3)
(000065F6 44 9		IDFun9)
(000065F8 8 2		UnVar2)
(000065FA 5 1		UnVar1)
(000065FC 8 4		UnVar4)
(000065FE 100 5		UNVar5)
(00006600 15 27 0		JMP 0000661E)
(00006603 5 4		UnVar4)
(00006605 40		car)
(00006606 8 6		UnVar6)
(00006608 5 6		UnVar6)
(0000660A 5 6		UnVar6)
(0000660C 5 2		UnVar2)
(0000660E 52 1 1		)
(00006611 57 2 0		list)
(00006614 5 5		UnVar5)
(00006616 42		cons)
(00006617 8 5		UnVar5)
(00006619 5 4		UnVar4)
(0000661B 41		cdr)
(0000661C 8 4		UnVar4)
(0000661E 5 4		UnVar4)
(00006620 60 224 255		T->JMP 00006603)
(00006623 5 5		UnVar5)
(00006625 81 1 196 1 1 0		nreverse)
(0000662B 5 3		UnVar3)
(0000662D 45 10		IDFun10)
(0000662F 10)
(00006630 5 3		UnVar3)
(00006632 44 10		IDFun10)
(00006634 8 4		UnVar4)
(00006636 100 5		UNVar5)
(00006638 15 14 0		JMP 00006649)
(0000663B 5 4		UnVar4)
(0000663D 40		car)
(0000663E 41		cdr)
(0000663F 5 5		UnVar5)
(00006641 42		cons)
(00006642 8 5		UnVar5)
(00006644 5 4		UnVar4)
(00006646 41		cdr)
(00006647 8 4		UnVar4)
(00006649 5 4		UnVar4)
(0000664B 60 237 255		T->JMP 0000663B)
(0000664E 5 5		UnVar5)
(00006650 81 1 196 1 1 0		nreverse)
(00006656 5 3		UnVar3)
(00006658 45 4		IDFun4)
(0000665A 10)
(0000665B 5 0		UnVar0)
(0000665D 22		ret)
;;;def shaded-list-box.list-box-sort-order<- 26206
(0000665E 20 5 2 2 0)
(00006663 5 0		UnVar0)
(00006665 8 2		UnVar2)
(00006667 5 1		UnVar1)
(00006669 5 2		UnVar2)
(0000666B 45 7		IDFun7)
(0000666D 10)
(0000666E 5 2		UnVar2)
(00006670 44 8		IDFun8)
(00006672 13 14 0		nil->JMP 00006683)
(00006675 5 2		UnVar2)
(00006677 44 10		IDFun10)
(00006679 5 1		UnVar1)
(0000667B 52 1 1		)
(0000667E 5 2		UnVar2)
(00006680 45 10		IDFun10)
(00006682 10)
(00006683 5 2		UnVar2)
(00006685 44 10		IDFun10)
(00006687 8 3		UnVar3)
(00006689 100 4		UNVar4)
(0000668B 15 14 0		JMP 0000669C)
(0000668E 5 3		UnVar3)
(00006690 40		car)
(00006691 41		cdr)
(00006692 5 4		UnVar4)
(00006694 42		cons)
(00006695 8 4		UnVar4)
(00006697 5 3		UnVar3)
(00006699 41		cdr)
(0000669A 8 3		UnVar3)
(0000669C 5 3		UnVar3)
(0000669E 60 237 255		T->JMP 0000668E)
(000066A1 5 4		UnVar4)
(000066A3 81 1 196 1 1 0		nreverse)
(000066A9 5 2		UnVar2)
(000066AB 45 4		IDFun4)
(000066AD 10)
(000066AE 5 0		UnVar0)
(000066B0 22		ret)
;;;def shaded-list-box.LIST-BOX-ITEMS-UP 26289
(000066B1 20 8 1 1 0)
(000066B6 100 1		UNVar1)
(000066B8 100 2		UNVar2)
(000066BA 100 3		UNVar3)
(000066BC 5 0		UnVar0)
(000066BE 8 4		UnVar4)
(000066C0 5 0		UnVar0)
(000066C2 1		nil)
(000066C3 95 2 62 90 0 0		LIST-BOX-MOVEABLE-P)
(000066C9 11)
(000066CA 8 1		UnVar1)
(000066CC 63		nil->ret)
(000066CD 5 4		UnVar4)
(000066CF 44 10		IDFun10)
(000066D1 8 2		UnVar2)
(000066D3 15 37 0		JMP 000066FB)
(000066D6 5 2		UnVar2)
(000066D8 41		cdr)
(000066D9 40		car)
(000066DA 40		car)
(000066DB 5 1		UnVar1)
(000066DD 40		car)
(000066DE 81 2 0 1 1 0		equal)
(000066E4 13 7 0		nil->JMP 000066EE)
(000066E7 5 2		UnVar2)
(000066E9 8 3		UnVar3)
(000066EB 15 13 0		JMP 000066FB)
(000066EE 5 2		UnVar2)
(000066F0 8 5		UnVar5)
(000066F2 5 5		UnVar5)
(000066F4 41		cdr)
(000066F5 8 2		UnVar2)
(000066F7 5 5		UnVar5)
(000066F9 40		car)
(000066FA 10)
(000066FB 5 2		UnVar2)
(000066FD 61 9 0		nil->JMP 00006709)
(00006700 5 2		UnVar2)
(00006702 41		cdr)
(00006703 61 3 0		nil->JMP 00006709)
(00006706 5 3		UnVar3)
(00006708 35		not)
(00006709 60 202 255		T->JMP 000066D6)
(0000670C 5 0		UnVar0)
(0000670E 95 1 141 87 0 0		list-box-erase-selection)
(00006714 10)
(00006715 5 4		UnVar4)
(00006717 44 10		IDFun10)
(00006719 5 3		UnVar3)
(0000671B 5 0		UnVar0)
(0000671D 5 1		UnVar1)
(0000671F 8 5		UnVar5)
(00006721 2		T)
(00006722 53 1 245 0 1 32		circle-list)
(00006728 8 6		UnVar6)
(0000672A 100 7		UNVar7)
(0000672C 15 22 0		JMP 00006745)
(0000672F 5 5		UnVar5)
(00006731 40		car)
(00006732 5 6		UnVar6)
(00006734 40		car)
(00006735 42		cons)
(00006736 5 7		UnVar7)
(00006738 42		cons)
(00006739 8 7		UnVar7)
(0000673B 5 5		UnVar5)
(0000673D 41		cdr)
(0000673E 8 5		UnVar5)
(00006740 5 6		UnVar6)
(00006742 41		cdr)
(00006743 8 6		UnVar6)
(00006745 5 5		UnVar5)
(00006747 61 2 0		nil->JMP 0000674C)
(0000674A 5 6		UnVar6)
(0000674C 60 224 255		T->JMP 0000672F)
(0000674F 5 7		UnVar7)
(00006751 81 1 196 1 1 0		nreverse)
(00006757 95 2 41 99 0 0		func 00006329)
(0000675D 95 3 218 86 0 0		ninsert-list)
(00006763 5 4		UnVar4)
(00006765 45 10		IDFun10)
(00006767 10)
(00006768 5 4		UnVar4)
(0000676A 44 10		IDFun10)
(0000676C 8 5		UnVar5)
(0000676E 100 6		UNVar6)
(00006770 15 14 0		JMP 00006781)
(00006773 5 5		UnVar5)
(00006775 40		car)
(00006776 41		cdr)
(00006777 5 6		UnVar6)
(00006779 42		cons)
(0000677A 8 6		UnVar6)
(0000677C 5 5		UnVar5)
(0000677E 41		cdr)
(0000677F 8 5		UnVar5)
(00006781 5 5		UnVar5)
(00006783 60 237 255		T->JMP 00006773)
(00006786 5 6		UnVar6)
(00006788 81 1 196 1 1 0		nreverse)
(0000678E 5 4		UnVar4)
(00006790 45 4		IDFun4)
(00006792 10)
(00006793 2		T)
(00006794 22		ret)
;;;def shaded-list-box.LIST-BOX-ITEMS-DOWN 26517
(00006795 20 9 1 1 0)
(0000679A 100 1		UNVar1)
(0000679C 100 2		UNVar2)
(0000679E 100 3		UNVar3)
(000067A0 100 4		UNVar4)
(000067A2 5 0		UnVar0)
(000067A4 8 5		UnVar5)
(000067A6 5 0		UnVar0)
(000067A8 2		T)
(000067A9 95 2 62 90 0 0		LIST-BOX-MOVEABLE-P)
(000067AF 11)
(000067B0 8 1		UnVar1)
(000067B2 63		nil->ret)
(000067B3 5 5		UnVar5)
(000067B5 44 10		IDFun10)
(000067B7 8 3		UnVar3)
(000067B9 5 1		UnVar1)
(000067BB 81 1 115 0 1 0		last)
(000067C1 40		car)
(000067C2 8 2		UnVar2)
(000067C4 15 35 0		JMP 000067EA)
(000067C7 5 3		UnVar3)
(000067C9 40		car)
(000067CA 40		car)
(000067CB 5 2		UnVar2)
(000067CD 81 2 0 1 1 0		equal)
(000067D3 13 7 0		nil->JMP 000067DD)
(000067D6 5 3		UnVar3)
(000067D8 8 4		UnVar4)
(000067DA 15 13 0		JMP 000067EA)
(000067DD 5 3		UnVar3)
(000067DF 8 6		UnVar6)
(000067E1 5 6		UnVar6)
(000067E3 41		cdr)
(000067E4 8 3		UnVar3)
(000067E6 5 6		UnVar6)
(000067E8 40		car)
(000067E9 10)
(000067EA 5 3		UnVar3)
(000067EC 61 9 0		nil->JMP 000067F8)
(000067EF 5 3		UnVar3)
(000067F1 41		cdr)
(000067F2 61 3 0		nil->JMP 000067F8)
(000067F5 5 4		UnVar4)
(000067F7 35		not)
(000067F8 60 204 255		T->JMP 000067C7)
(000067FB 5 4		UnVar4)
(000067FD 8 6		UnVar6)
(000067FF 5 6		UnVar6)
(00006801 41		cdr)
(00006802 8 4		UnVar4)
(00006804 5 6		UnVar6)
(00006806 40		car)
(00006807 10)
(00006808 5 0		UnVar0)
(0000680A 95 1 141 87 0 0		list-box-erase-selection)
(00006810 10)
(00006811 5 5		UnVar5)
(00006813 44 10		IDFun10)
(00006815 5 4		UnVar4)
(00006817 5 0		UnVar0)
(00006819 5 1		UnVar1)
(0000681B 8 6		UnVar6)
(0000681D 2		T)
(0000681E 53 1 245 0 1 32		circle-list)
(00006824 8 7		UnVar7)
(00006826 100 8		UNVar8)
(00006828 15 22 0		JMP 00006841)
(0000682B 5 6		UnVar6)
(0000682D 40		car)
(0000682E 5 7		UnVar7)
(00006830 40		car)
(00006831 42		cons)
(00006832 5 8		UnVar8)
(00006834 42		cons)
(00006835 8 8		UnVar8)
(00006837 5 6		UnVar6)
(00006839 41		cdr)
(0000683A 8 6		UnVar6)
(0000683C 5 7		UnVar7)
(0000683E 41		cdr)
(0000683F 8 7		UnVar7)
(00006841 5 6		UnVar6)
(00006843 61 2 0		nil->JMP 00006848)
(00006846 5 7		UnVar7)
(00006848 60 224 255		T->JMP 0000682B)
(0000684B 5 8		UnVar8)
(0000684D 81 1 196 1 1 0		nreverse)
(00006853 95 2 41 99 0 0		func 00006329)
(00006859 2		T)
(0000685A 95 4 218 86 0 0		ninsert-list)
(00006860 5 5		UnVar5)
(00006862 45 10		IDFun10)
(00006864 10)
(00006865 5 5		UnVar5)
(00006867 44 10		IDFun10)
(00006869 8 6		UnVar6)
(0000686B 100 7		UNVar7)
(0000686D 15 14 0		JMP 0000687E)
(00006870 5 6		UnVar6)
(00006872 40		car)
(00006873 41		cdr)
(00006874 5 7		UnVar7)
(00006876 42		cons)
(00006877 8 7		UnVar7)
(00006879 5 6		UnVar6)
(0000687B 41		cdr)
(0000687C 8 6		UnVar6)
(0000687E 5 6		UnVar6)
(00006880 60 237 255		T->JMP 00006870)
(00006883 5 7		UnVar7)
(00006885 81 1 196 1 1 0		nreverse)
(0000688B 5 5		UnVar5)
(0000688D 45 4		IDFun4)
(0000688F 10)
(00006890 2		T)
(00006891 22		ret)
;;;def shaded-list-box.LIST-BOX-ITEMS-TOP 26770
(00006892 20 6 1 1 0)
(00006897 100 1		UNVar1)
(00006899 5 0		UnVar0)
(0000689B 8 2		UnVar2)
(0000689D 5 0		UnVar0)
(0000689F 1		nil)
(000068A0 95 2 62 90 0 0		LIST-BOX-MOVEABLE-P)
(000068A6 11)
(000068A7 8 1		UnVar1)
(000068A9 63		nil->ret)
(000068AA 5 0		UnVar0)
(000068AC 95 1 141 87 0 0		list-box-erase-selection)
(000068B2 10)
(000068B3 5 0		UnVar0)
(000068B5 5 1		UnVar1)
(000068B7 8 3		UnVar3)
(000068B9 2		T)
(000068BA 53 1 245 0 1 32		circle-list)
(000068C0 8 4		UnVar4)
(000068C2 100 5		UNVar5)
(000068C4 15 22 0		JMP 000068DD)
(000068C7 5 3		UnVar3)
(000068C9 40		car)
(000068CA 5 4		UnVar4)
(000068CC 40		car)
(000068CD 42		cons)
(000068CE 5 5		UnVar5)
(000068D0 42		cons)
(000068D1 8 5		UnVar5)
(000068D3 5 3		UnVar3)
(000068D5 41		cdr)
(000068D6 8 3		UnVar3)
(000068D8 5 4		UnVar4)
(000068DA 41		cdr)
(000068DB 8 4		UnVar4)
(000068DD 5 3		UnVar3)
(000068DF 61 2 0		nil->JMP 000068E4)
(000068E2 5 4		UnVar4)
(000068E4 60 224 255		T->JMP 000068C7)
(000068E7 5 5		UnVar5)
(000068E9 81 1 196 1 1 0		nreverse)
(000068EF 95 2 41 99 0 0		func 00006329)
(000068F5 5 2		UnVar2)
(000068F7 44 10		IDFun10)
(000068F9 81 2 195 1 1 0		nconc)
(000068FF 5 2		UnVar2)
(00006901 45 10		IDFun10)
(00006903 10)
(00006904 5 2		UnVar2)
(00006906 44 10		IDFun10)
(00006908 8 3		UnVar3)
(0000690A 100 4		UNVar4)
(0000690C 15 14 0		JMP 0000691D)
(0000690F 5 3		UnVar3)
(00006911 40		car)
(00006912 41		cdr)
(00006913 5 4		UnVar4)
(00006915 42		cons)
(00006916 8 4		UnVar4)
(00006918 5 3		UnVar3)
(0000691A 41		cdr)
(0000691B 8 3		UnVar3)
(0000691D 5 3		UnVar3)
(0000691F 60 237 255		T->JMP 0000690F)
(00006922 5 4		UnVar4)
(00006924 81 1 196 1 1 0		nreverse)
(0000692A 5 2		UnVar2)
(0000692C 45 4		IDFun4)
(0000692E 10)
(0000692F 2		T)
(00006930 22		ret)
;;;def shaded-list-box.LIST-BOX-ITEMS-BOTTOM 26929
(00006931 20 6 1 1 0)
(00006936 100 1		UNVar1)
(00006938 5 0		UnVar0)
(0000693A 8 2		UnVar2)
(0000693C 5 0		UnVar0)
(0000693E 2		T)
(0000693F 95 2 62 90 0 0		LIST-BOX-MOVEABLE-P)
(00006945 11)
(00006946 8 1		UnVar1)
(00006948 63		nil->ret)
(00006949 5 0		UnVar0)
(0000694B 95 1 141 87 0 0		list-box-erase-selection)
(00006951 10)
(00006952 5 2		UnVar2)
(00006954 44 10		IDFun10)
(00006956 5 0		UnVar0)
(00006958 5 1		UnVar1)
(0000695A 8 3		UnVar3)
(0000695C 2		T)
(0000695D 53 1 245 0 1 32		circle-list)
(00006963 8 4		UnVar4)
(00006965 100 5		UNVar5)
(00006967 15 22 0		JMP 00006980)
(0000696A 5 3		UnVar3)
(0000696C 40		car)
(0000696D 5 4		UnVar4)
(0000696F 40		car)
(00006970 42		cons)
(00006971 5 5		UnVar5)
(00006973 42		cons)
(00006974 8 5		UnVar5)
(00006976 5 3		UnVar3)
(00006978 41		cdr)
(00006979 8 3		UnVar3)
(0000697B 5 4		UnVar4)
(0000697D 41		cdr)
(0000697E 8 4		UnVar4)
(00006980 5 3		UnVar3)
(00006982 61 2 0		nil->JMP 00006987)
(00006985 5 4		UnVar4)
(00006987 60 224 255		T->JMP 0000696A)
(0000698A 5 5		UnVar5)
(0000698C 81 1 196 1 1 0		nreverse)
(00006992 95 2 41 99 0 0		func 00006329)
(00006998 81 2 195 1 1 0		nconc)
(0000699E 5 2		UnVar2)
(000069A0 45 10		IDFun10)
(000069A2 10)
(000069A3 5 2		UnVar2)
(000069A5 44 10		IDFun10)
(000069A7 8 3		UnVar3)
(000069A9 100 4		UNVar4)
(000069AB 15 14 0		JMP 000069BC)
(000069AE 5 3		UnVar3)
(000069B0 40		car)
(000069B1 41		cdr)
(000069B2 5 4		UnVar4)
(000069B4 42		cons)
(000069B5 8 4		UnVar4)
(000069B7 5 3		UnVar3)
(000069B9 41		cdr)
(000069BA 8 3		UnVar3)
(000069BC 5 3		UnVar3)
(000069BE 60 237 255		T->JMP 000069AE)
(000069C1 5 4		UnVar4)
(000069C3 81 1 196 1 1 0		nreverse)
(000069C9 5 2		UnVar2)
(000069CB 45 4		IDFun4)
(000069CD 10)
(000069CE 2		T)
(000069CF 22		ret)
;;;==========Main==========
(00000000 20 0 0 0 0)
(00000005 1		nil)
(00000006 10)
(00000007 9 120 3		"3/5/18 10:08 PM")
(0000000A 26 119 3		*windlg-date*)
(0000000D 9 119 3		'*windlg-date*)
(00000010 10)
(00000011 9 118 3		'windlg)
(00000014 81 1 117 3 0 0		provide)
(0000001A 10)
(0000001B 9 116 3		'los)
(0000001E 81 1 115 3 0 0		require)
(00000024 10)
(00000025 9 114 3		'lcx)
(00000028 81 1 115 3 0 0		require)
(0000002E 28		[ret])
(0000002F 20 0 0 0 0)
(00000034 1		nil)
(00000035 10)
(00000036 50 101		101)
(00000038 26 113 3		IDD_APROPOS1)
(0000003B 9 113 3		'IDD_APROPOS1)
(0000003E 10)
(0000003F 50 102		102)
(00000041 26 112 3		IDD_ADDWATCH)
(00000044 9 112 3		'IDD_ADDWATCH)
(00000047 10)
(00000048 50 104		104)
(0000004A 26 111 3		IDD_REVIEWSELECTIONS)
(0000004D 9 111 3		'IDD_REVIEWSELECTIONS)
(00000050 10)
(00000051 50 107		107)
(00000053 26 110 3		IDD_FIND)
(00000056 9 110 3		'IDD_FIND)
(00000059 10)
(0000005A 50 108		108)
(0000005C 26 109 3		IDD_INSPECTSYM)
(0000005F 9 109 3		'IDD_INSPECTSYM)
(00000062 10)
(00000063 50 109		109)
(00000065 26 108 3		IDD_INSPECT)
(00000068 9 108 3		'IDD_INSPECT)
(0000006B 10)
(0000006C 50 112		112)
(0000006E 26 107 3		IDD_PROJECTNAME)
(00000071 9 107 3		'IDD_PROJECTNAME)
(00000074 10)
(00000075 50 114		114)
(00000077 26 106 3		IDD_GENERALOPTIONS_CHILD1)
(0000007A 9 106 3		'IDD_GENERALOPTIONS_CHILD1)
(0000007D 10)
(0000007E 50 115		115)
(00000080 26 105 3		IDD_GENERALOPTIONS_CHILD2)
(00000083 9 105 3		'IDD_GENERALOPTIONS_CHILD2)
(00000086 10)
(00000087 50 117		117)
(00000089 26 104 3		IDD_PROJECTPROPERTIES_CHILD1)
(0000008C 9 104 3		'IDD_PROJECTPROPERTIES_CHILD1)
(0000008F 10)
(00000090 50 118		118)
(00000092 26 103 3		IDD_PROJECTPROPERTIES_CHILD2)
(00000095 9 103 3		'IDD_PROJECTPROPERTIES_CHILD2)
(00000098 10)
(00000099 50 119		119)
(0000009B 26 102 3		IDD_TRACESTACK)
(0000009E 9 102 3		'IDD_TRACESTACK)
(000000A1 10)
(000000A2 50 120		120)
(000000A4 26 101 3		IDD_ERRORTRACE)
(000000A7 9 101 3		'IDD_ERRORTRACE)
(000000AA 10)
(000000AB 50 121		121)
(000000AD 26 100 3		IDD_SYMBOLSERVICE2)
(000000B0 9 100 3		'IDD_SYMBOLSERVICE2)
(000000B3 10)
(000000B4 50 123		123)
(000000B6 26 99 3		IDD_DATEANDTIME)
(000000B9 9 99 3		'IDD_DATEANDTIME)
(000000BC 10)
(000000BD 50 124		124)
(000000BF 26 98 3		IDD_INDENTBLOCKBYSTRING)
(000000C2 9 98 3		'IDD_INDENTBLOCKBYSTRING)
(000000C5 10)
(000000C6 50 125		125)
(000000C8 26 97 3		IDD_APPENDSTRING)
(000000CB 9 97 3		'IDD_APPENDSTRING)
(000000CE 10)
(000000CF 50 126		126)
(000000D1 26 96 3		IDD_AUTOLISP_REVERTBUFFER)
(000000D4 9 96 3		'IDD_AUTOLISP_REVERTBUFFER)
(000000D7 10)
(000000D8 50 127		127)
(000000DA 26 95 3		IDD_ENTERDIALOGNAME)
(000000DD 9 95 3		'IDD_ENTERDIALOGNAME)
(000000E0 10)
(000000E1 51 128 0 0 0		128)
(000000E6 26 94 3		IDD_FILTERVALUE)
(000000E9 9 94 3		'IDD_FILTERVALUE)
(000000EC 10)
(000000ED 51 129 0 0 0		129)
(000000F2 26 93 3		IDD_FILTERFLAGS)
(000000F5 9 93 3		'IDD_FILTERFLAGS)
(000000F8 10)
(000000F9 51 130 0 0 0		130)
(000000FE 26 92 3		IDD_TOOLBARS)
(00000101 9 92 3		'IDD_TOOLBARS)
(00000104 10)
(00000105 51 131 0 0 0		131)
(0000010A 26 91 3		IDD_AUTOLISP_REPLACEFILE)
(0000010D 9 91 3		'IDD_AUTOLISP_REPLACEFILE)
(00000110 10)
(00000111 51 132 0 0 0		132)
(00000116 26 90 3		IDD_AUTOLISP_CALLBACKENTRY)
(00000119 9 90 3		'IDD_AUTOLISP_CALLBACKENTRY)
(0000011C 10)
(0000011D 51 133 0 0 0		133)
(00000122 26 89 3		IDD_PAGESETUP)
(00000125 9 89 3		'IDD_PAGESETUP)
(00000128 10)
(00000129 51 134 0 0 0		134)
(0000012E 26 88 3		IDD_AUTOLISP_SAVECHANGES)
(00000131 9 88 3		'IDD_AUTOLISP_SAVECHANGES)
(00000134 10)
(00000135 51 135 0 0 0		135)
(0000013A 26 87 3		IDD_GOTOLINE)
(0000013D 9 87 3		'IDD_GOTOLINE)
(00000140 10)
(00000141 51 137 0 0 0		137)
(00000146 26 86 3		IDD_SYMBOLSERVICE1)
(00000149 9 86 3		'IDD_SYMBOLSERVICE1)
(0000014C 10)
(0000014D 51 138 0 0 0		138)
(00000152 26 85 3		IDD_AUTOLISP_WRONGINPUT)
(00000155 9 85 3		'IDD_AUTOLISP_WRONGINPUT)
(00000158 10)
(00000159 51 139 0 0 0		139)
(0000015E 26 84 3		IDD_NIL)
(00000161 9 84 3		'IDD_NIL)
(00000164 10)
(00000165 51 140 0 0 0		140)
(0000016A 26 83 3		IDD_AUTOLISP_INVALIDAPP)
(0000016D 9 83 3		'IDD_AUTOLISP_INVALIDAPP)
(00000170 10)
(00000171 51 141 0 0 0		141)
(00000176 26 82 3		IDD_AUTOLISP_FILEEXISTS)
(00000179 9 82 3		'IDD_AUTOLISP_FILEEXISTS)
(0000017C 10)
(0000017D 51 142 0 0 0		142)
(00000182 26 81 3		IDD_AUTOLISP_NOFILEEXISTS)
(00000185 9 81 3		'IDD_AUTOLISP_NOFILEEXISTS)
(00000188 10)
(00000189 51 143 0 0 0		143)
(0000018E 26 80 3		IDD_X)
(00000191 9 80 3		'IDD_X)
(00000194 10)
(00000195 51 144 0 0 0		144)
(0000019A 26 79 3		IDD_WINDOWATTRIBUTES)
(0000019D 9 79 3		'IDD_WINDOWATTRIBUTES)
(000001A0 10)
(000001A1 51 145 0 0 0		145)
(000001A6 26 78 3		IDD_FILETOWRITEBLOCKTO)
(000001A9 9 78 3		'IDD_FILETOWRITEBLOCKTO)
(000001AC 10)
(000001AD 51 146 0 0 0		146)
(000001B2 26 77 3		IDD_COLORSTYLE)
(000001B5 9 77 3		'IDD_COLORSTYLE)
(000001B8 10)
(000001B9 51 147 0 0 0		147)
(000001BE 26 76 3		IDD_ENTERITEMNAME)
(000001C1 9 76 3		'IDD_ENTERITEMNAME)
(000001C4 10)
(000001C5 51 148 0 0 0		148)
(000001CA 26 75 3		IDD_REPLACE)
(000001CD 9 75 3		'IDD_REPLACE)
(000001D0 10)
(000001D1 51 149 0 0 0		149)
(000001D6 26 74 3		IDD_AUTOLISP_FORMATOPTIONS)
(000001D9 9 74 3		'IDD_AUTOLISP_FORMATOPTIONS)
(000001DC 10)
(000001DD 51 150 0 0 0		150)
(000001E2 26 73 3		IDD_AUTOLISP_FORMATOPTIONS_MORE)
(000001E5 9 73 3		'IDD_AUTOLISP_FORMATOPTIONS_MORE)
(000001E8 10)
(000001E9 51 151 0 0 0		151)
(000001EE 26 72 3		IDD_WIZARDMODE)
(000001F1 9 72 3		'IDD_WIZARDMODE)
(000001F4 10)
(000001F5 51 152 0 0 0		152)
(000001FA 26 71 3		IDD_APPDIRECTORY)
(000001FD 9 71 3		'IDD_APPDIRECTORY)
(00000200 10)
(00000201 51 153 0 0 0		153)
(00000206 26 70 3		IDD_LISPFILES)
(00000209 9 70 3		'IDD_LISPFILES)
(0000020C 10)
(0000020D 51 154 0 0 0		154)
(00000212 26 69 3		IDD_WATCH)
(00000215 9 69 3		'IDD_WATCH)
(00000218 10)
(00000219 51 155 0 0 0		155)
(0000021E 26 68 3		IDD_APPLICATIONOPTIONS)
(00000221 9 68 3		'IDD_APPLICATIONOPTIONS)
(00000224 10)
(00000225 51 166 0 0 0		166)
(0000022A 26 67 3		IDD_AP_APPLICATIONOPTIONS)
(0000022D 9 67 3		'IDD_AP_APPLICATIONOPTIONS)
(00000230 10)
(00000231 51 167 0 0 0		167)
(00000236 26 66 3		IDD_AP_LOADFILES)
(00000239 9 66 3		'IDD_AP_LOADFILES)
(0000023C 10)
(0000023D 51 168 0 0 0		168)
(00000242 26 65 3		IDD_AP_RESOURCEFILES)
(00000245 9 65 3		'IDD_AP_RESOURCEFILES)
(00000248 10)
(00000249 51 169 0 0 0		169)
(0000024E 26 64 3		IDD_AP_LOADCOMPILE)
(00000251 9 64 3		'IDD_AP_LOADCOMPILE)
(00000254 10)
(00000255 51 170 0 0 0		170)
(0000025A 26 63 3		IDD_AP_TUNEDIRECTORIES)
(0000025D 9 63 3		'IDD_AP_TUNEDIRECTORIES)
(00000260 10)
(00000261 51 231 3 0 0		999)
(00000266 26 62 3		IDC_ADDWATCH_STATIC)
(00000269 9 62 3		'IDC_ADDWATCH_STATIC)
(0000026C 10)
(0000026D 51 231 3 0 0		999)
(00000272 26 61 3		IDC_APROPOS1_FILTERFLAGS_BUTTON)
(00000275 9 61 3		'IDC_APROPOS1_FILTERFLAGS_BUTTON)
(00000278 10)
(00000279 51 231 3 0 0		999)
(0000027E 26 60 3		IDC_FIND_FIND_BUTTON)
(00000281 9 60 3		'IDC_FIND_FIND_BUTTON)
(00000284 10)
(00000285 51 232 3 0 0		1000)
(0000028A 26 59 3		IDC_FIND_HELP_BUTTON)
(0000028D 9 59 3		'IDC_FIND_HELP_BUTTON)
(00000290 10)
(00000291 51 232 3 0 0		1000)
(00000296 26 58 3		IDC_APROPOS1_FILTERVALUE_BUTTON)
(00000299 9 58 3		'IDC_APROPOS1_FILTERVALUE_BUTTON)
(0000029C 10)
(0000029D 51 234 3 0 0		1002)
(000002A2 26 57 3		IDC_WINDOWATTRIBUTES_WIDTH_EDIT1)
(000002A5 9 57 3		'IDC_WINDOWATTRIBUTES_WIDTH_EDIT1)
(000002A8 10)
(000002A9 51 234 3 0 0		1002)
(000002AE 26 56 3		IDC_APROPOS1_EDIT)
(000002B1 9 56 3		'IDC_APROPOS1_EDIT)
(000002B4 10)
(000002B5 51 234 3 0 0		1002)
(000002BA 26 55 3		IDC_PROJECTPROP_PARENT_EDIT)
(000002BD 9 55 3		'IDC_PROJECTPROP_PARENT_EDIT)
(000002C0 10)
(000002C1 51 235 3 0 0		1003)
(000002C6 26 54 3		IDC_FIND_SEARCH_STATIC)
(000002C9 9 54 3		'IDC_FIND_SEARCH_STATIC)
(000002CC 10)
(000002CD 51 235 3 0 0		1003)
(000002D2 26 53 3		IDC_APROPOS1_MATCH_CHECK1)
(000002D5 9 53 3		'IDC_APROPOS1_MATCH_CHECK1)
(000002D8 10)
(000002D9 51 236 3 0 0		1004)
(000002DE 26 52 3		IDC_FIND_DIRECTION_STATIC)
(000002E1 9 52 3		'IDC_FIND_DIRECTION_STATIC)
(000002E4 10)
(000002E5 51 236 3 0 0		1004)
(000002EA 26 51 3		IDC_APROPOS1_USEWCMATCH_CHECK2)
(000002ED 9 51 3		'IDC_APROPOS1_USEWCMATCH_CHECK2)
(000002F0 10)
(000002F1 51 237 3 0 0		1005)
(000002F6 26 50 3		IDC_FIND_DIRECTION_DOWN_RADIO5)
(000002F9 9 50 3		'IDC_FIND_DIRECTION_DOWN_RADIO5)
(000002FC 10)
(000002FD 51 237 3 0 0		1005)
(00000302 26 49 3		IDC_APROPOS1_LOWERCASE_CHECK3)
(00000305 9 49 3		'IDC_APROPOS1_LOWERCASE_CHECK3)
(00000308 10)
(00000309 51 238 3 0 0		1006)
(0000030E 26 48 3		IDC_FIND_DIRECTION_UP_RADIO6)
(00000311 9 48 3		'IDC_FIND_DIRECTION_UP_RADIO6)
(00000314 10)
(00000315 51 239 3 0 0		1007)
(0000031A 26 47 3		IDC_ADDWATCH_COMBO)
(0000031D 9 47 3		'IDC_ADDWATCH_COMBO)
(00000320 10)
(00000321 51 240 3 0 0		1008)
(00000326 26 46 3		IDC_WIZARDMODE_TEXT1_STATIC)
(00000329 9 46 3		'IDC_WIZARDMODE_TEXT1_STATIC)
(0000032C 10)
(0000032D 51 240 3 0 0		1008)
(00000332 26 45 3		IDC_FIND_SEARCH_CURRENTSEL_RADIO1)
(00000335 9 45 3		'IDC_FIND_SEARCH_CURRENTSEL_RADIO1)
(00000338 10)
(00000339 51 240 3 0 0		1008)
(0000033E 26 44 3		IDC_APPDIRECTORY_TEXT1_STATIC)
(00000341 9 44 3		'IDC_APPDIRECTORY_TEXT1_STATIC)
(00000344 10)
(00000345 51 241 3 0 0		1009)
(0000034A 26 43 3		IDC_WINDOWATTRIBUTES_COMBO)
(0000034D 9 43 3		'IDC_WINDOWATTRIBUTES_COMBO)
(00000350 10)
(00000351 51 241 3 0 0		1009)
(00000356 26 42 3		IDC_WIZARDMODE_CHOOSE_STATIC)
(00000359 9 42 3		'IDC_WIZARDMODE_CHOOSE_STATIC)
(0000035C 10)
(0000035D 51 241 3 0 0		1009)
(00000362 26 41 3		IDC_APPDIRECTORY_CHOOSE_STATIC)
(00000365 9 41 3		'IDC_APPDIRECTORY_CHOOSE_STATIC)
(00000368 10)
(00000369 51 241 3 0 0		1009)
(0000036E 26 40 3		IDC_FIND_SEARCH_CURRENTFI_RADIO2)
(00000371 9 40 3		'IDC_FIND_SEARCH_CURRENTFI_RADIO2)
(00000374 10)
(00000375 51 242 3 0 0		1010)
(0000037A 26 39 3		IDC_FIND_SEARCH_PROJECT_RADIO3)
(0000037D 9 39 3		'IDC_FIND_SEARCH_PROJECT_RADIO3)
(00000380 10)
(00000381 51 242 3 0 0		1010)
(00000386 26 38 3		IDC_INSPECT_STATIC)
(00000389 9 38 3		'IDC_INSPECT_STATIC)
(0000038C 10)
(0000038D 51 242 3 0 0		1010)
(00000392 26 37 3		IDC_WIZARDMODE_SIMPLE_RADIO1)
(00000395 9 37 3		'IDC_WIZARDMODE_SIMPLE_RADIO1)
(00000398 10)
(00000399 51 242 3 0 0		1010)
(0000039E 26 36 3		IDC_APPDIRECTORY_TARGETFILE_TEXT_STATIC)
(000003A1 9 36 3		'IDC_APPDIRECTORY_TARGETFILE_TEXT_STATIC)
(000003A4 10)
(000003A5 51 243 3 0 0		1011)
(000003AA 26 35 3		IDC_FIND_SEARCH_FILES_RADIO4)
(000003AD 9 35 3		'IDC_FIND_SEARCH_FILES_RADIO4)
(000003B0 10)
(000003B1 51 243 3 0 0		1011)
(000003B6 26 34 3		IDC_WIZARDMODE_EXPERT_RADIO2)
(000003B9 9 34 3		'IDC_WIZARDMODE_EXPERT_RADIO2)
(000003BC 10)
(000003BD 51 244 3 0 0		1012)
(000003C2 26 33 3		IDC_FIND_MATCHWORD_CHECK1)
(000003C5 9 33 3		'IDC_FIND_MATCHWORD_CHECK1)
(000003C8 10)
(000003C9 51 244 3 0 0		1012)
(000003CE 26 32 3		IDC_APPDIRECTORY_APPLOCATION_STATIC)
(000003D1 9 32 3		'IDC_APPDIRECTORY_APPLOCATION_STATIC)
(000003D4 10)
(000003D5 51 245 3 0 0		1013)
(000003DA 26 31 3		IDC_FIND_MATCHCASE_CHECK2)
(000003DD 9 31 3		'IDC_FIND_MATCHCASE_CHECK2)
(000003E0 10)
(000003E1 51 245 3 0 0		1013)
(000003E6 26 30 3		IDC_REVIEW_EMPTYFRAME_STATIC)
(000003E9 9 30 3		'IDC_REVIEW_EMPTYFRAME_STATIC)
(000003EC 10)
(000003ED 51 246 3 0 0		1014)
(000003F2 26 29 3		IDC_FIND_MARKINSTANCES_CHECK3)
(000003F5 9 29 3		'IDC_FIND_MARKINSTANCES_CHECK3)
(000003F8 10)
(000003F9 51 246 3 0 0		1014)
(000003FE 26 28 3		IDC_REVIEW_BACK_BUTTON)
(00000401 9 28 3		'IDC_REVIEW_BACK_BUTTON)
(00000404 10)
(00000405 51 248 3 0 0		1016)
(0000040A 26 27 3		IDC_WATCH_STATIC)
(0000040D 9 27 3		'IDC_WATCH_STATIC)
(00000410 10)
(00000411 51 248 3 0 0		1016)
(00000416 26 26 3		IDC_REVIEW_FINISH_BUTTON)
(00000419 9 26 3		'IDC_REVIEW_FINISH_BUTTON)
(0000041C 10)
(0000041D 51 250 3 0 0		1018)
(00000422 26 25 3		IDC_APPDIRECTORY_APPLOCATION_EDIT)
(00000425 9 25 3		'IDC_APPDIRECTORY_APPLOCATION_EDIT)
(00000428 10)
(00000429 51 251 3 0 0		1019)
(0000042E 26 24 3		IDC_APPDIRECTORY_APPLOCATION_BROWSE_BUTTON)
(00000431 9 24 3		'IDC_APPDIRECTORY_APPLOCATION_BROWSE_BUTTON)
(00000434 10)
(00000435 51 252 3 0 0		1020)
(0000043A 26 23 3		IDC_APPDIRECTORY_APPNAME_STATIC)
(0000043D 9 23 3		'IDC_APPDIRECTORY_APPNAME_STATIC)
(00000440 10)
(00000441 51 253 3 0 0		1021)
(00000446 26 22 3		IDC_APPDIRECTORY_TARGETFILE_STATIC)
(00000449 9 22 3		'IDC_APPDIRECTORY_TARGETFILE_STATIC)
(0000044C 10)
(0000044D 51 254 3 0 0		1022)
(00000452 26 21 3		IDC_APPDIRECTORY_APPNAME_EDIT)
(00000455 9 21 3		'IDC_APPDIRECTORY_APPNAME_EDIT)
(00000458 10)
(00000459 51 254 3 0 0		1022)
(0000045E 26 20 3		IDC_LISPFILES_SELECTFILES_STATIC)
(00000461 9 20 3		'IDC_LISPFILES_SELECTFILES_STATIC)
(00000464 10)
(00000465 51 255 3 0 0		1023)
(0000046A 26 19 3		IDC_LISPFILES_SELECTFILES_TEXT)
(0000046D 9 19 3		'IDC_LISPFILES_SELECTFILES_TEXT)
(00000470 10)
(00000471 51 0 4 0 0		1024)
(00000476 26 18 3		IDC_LISPFILES_ADD_BUTTON)
(00000479 9 18 3		'IDC_LISPFILES_ADD_BUTTON)
(0000047C 10)
(0000047D 51 1 4 0 0		1025)
(00000482 26 17 3		IDC_LISPFILES_REMOVE_BUTTON)
(00000485 9 17 3		'IDC_LISPFILES_REMOVE_BUTTON)
(00000488 10)
(00000489 51 2 4 0 0		1026)
(0000048E 26 16 3		IDC_LISPFILES_COMBO)
(00000491 9 16 3		'IDC_LISPFILES_COMBO)
(00000494 10)
(00000495 51 5 4 0 0		1029)
(0000049A 26 15 3		IDC_LISPFILES_EDIT)
(0000049D 9 15 3		'IDC_LISPFILES_EDIT)
(000004A0 10)
(000004A1 51 6 4 0 0		1030)
(000004A6 26 14 3		IDC_REVIEW_BUILDAPP_CHECK)
(000004A9 9 14 3		'IDC_REVIEW_BUILDAPP_CHECK)
(000004AC 10)
(000004AD 51 7 4 0 0		1031)
(000004B2 26 13 3		IDC_REVIEW_REVIEWSEL_STATIC)
(000004B5 9 13 3		'IDC_REVIEW_REVIEWSEL_STATIC)
(000004B8 10)
(000004B9 51 8 4 0 0		1032)
(000004BE 26 12 3		IDC_REVIEW_REVIEWSEL_TEXT1_STATIC)
(000004C1 9 12 3		'IDC_REVIEW_REVIEWSEL_TEXT1_STATIC)
(000004C4 10)
(000004C5 51 9 4 0 0		1033)
(000004CA 26 11 3		IDC_WIZARDMODE_FRAME_STATIC)
(000004CD 9 11 3		'IDC_WIZARDMODE_FRAME_STATIC)
(000004D0 10)
(000004D1 51 10 4 0 0		1034)
(000004D6 26 10 3		IDC_FIND_FINDWHAT_COMBO)
(000004D9 9 10 3		'IDC_FIND_FINDWHAT_COMBO)
(000004DC 10)
(000004DD 51 11 4 0 0		1035)
(000004E2 26 9 3		IDC_WATCH_LIST)
(000004E5 9 9 3		'IDC_WATCH_LIST)
(000004E8 10)
(000004E9 51 13 4 0 0		1037)
(000004EE 26 8 3		IDC_PROJECTNAME_BROWSE_BUTTON)
(000004F1 9 8 3		'IDC_PROJECTNAME_BROWSE_BUTTON)
(000004F4 10)
(000004F5 51 14 4 0 0		1038)
(000004FA 26 7 3		IDC_PROJECTNAME_NAME_EDIT)
(000004FD 9 7 3		'IDC_PROJECTNAME_NAME_EDIT)
(00000500 10)
(00000501 51 21 4 0 0		1045)
(00000506 26 6 3		IDC_GENERALOPTIONS_CHILD1_EDITOROPTIONS_STATIC)
(00000509 9 6 3		'IDC_GENERALOPTIONS_CHILD1_EDITOROPTIONS_STATIC)
(0000050C 10)
(0000050D 51 22 4 0 0		1046)
(00000512 26 5 3		IDC_GENERALOPTIONS_CHILD1_EDITOR_CHECK1)
(00000515 9 5 3		'IDC_GENERALOPTIONS_CHILD1_EDITOR_CHECK1)
(00000518 10)
(00000519 51 23 4 0 0		1047)
(0000051E 26 4 3		IDC_GENERALOPTIONS_CHILD1_EDITOR_CHECK2)
(00000521 9 4 3		'IDC_GENERALOPTIONS_CHILD1_EDITOR_CHECK2)
(00000524 10)
(00000525 51 24 4 0 0		1048)
(0000052A 26 3 3		IDC_GENERALOPTIONS_CHILD1_EDITOR_CHECK3)
(0000052D 9 3 3		'IDC_GENERALOPTIONS_CHILD1_EDITOR_CHECK3)
(00000530 10)
(00000531 51 25 4 0 0		1049)
(00000536 26 2 3		IDC_GENERALOPTIONS_CHILD1_DESKTOP_CHECK4)
(00000539 9 2 3		'IDC_GENERALOPTIONS_CHILD1_DESKTOP_CHECK4)
(0000053C 10)
(0000053D 51 26 4 0 0		1050)
(00000542 26 1 3		IDC_GENERALOPTIONS_CHILD1_DESKTOP_CHECK5)
(00000545 9 1 3		'IDC_GENERALOPTIONS_CHILD1_DESKTOP_CHECK5)
(00000548 10)
(00000549 51 27 4 0 0		1051)
(0000054E 26 0 3		IDC_GENERALOPTIONS_CHILD1_AUTOACAD_CHECK6)
(00000551 9 0 3		'IDC_GENERALOPTIONS_CHILD1_AUTOACAD_CHECK6)
(00000554 10)
(00000555 51 28 4 0 0		1052)
(0000055A 26 255 2		IDC_GENERALOPTIONS_CHILD1_SETQ_RADIO1)
(0000055D 9 255 2		'IDC_GENERALOPTIONS_CHILD1_SETQ_RADIO1)
(00000560 10)
(00000561 51 29 4 0 0		1053)
(00000566 26 254 2		IDC_GENERALOPTIONS_CHILD1_SETQ_RADIO2)
(00000569 9 254 2		'IDC_GENERALOPTIONS_CHILD1_SETQ_RADIO2)
(0000056C 10)
(0000056D 51 30 4 0 0		1054)
(00000572 26 253 2		IDC_GENERALOPTIONS_CHILD1_SETQ_RADIO3)
(00000575 9 253 2		'IDC_GENERALOPTIONS_CHILD1_SETQ_RADIO3)
(00000578 10)
(00000579 51 31 4 0 0		1055)
(0000057E 26 252 2		IDC_GENERALOPTIONS_CHILD1_SETQ_RADIO4)
(00000581 9 252 2		'IDC_GENERALOPTIONS_CHILD1_SETQ_RADIO4)
(00000584 10)
(00000585 51 32 4 0 0		1056)
(0000058A 26 251 2		IDC_GENERALOPTIONS_CHILD2_CHECK1)
(0000058D 9 251 2		'IDC_GENERALOPTIONS_CHILD2_CHECK1)
(00000590 10)
(00000591 51 33 4 0 0		1057)
(00000596 26 250 2		IDC_GENERALOPTIONS_CHILD2_CHECK2)
(00000599 9 250 2		'IDC_GENERALOPTIONS_CHILD2_CHECK2)
(0000059C 10)
(0000059D 51 34 4 0 0		1058)
(000005A2 26 249 2		IDC_GENERALOPTIONS_CHILD2_CHECK3)
(000005A5 9 249 2		'IDC_GENERALOPTIONS_CHILD2_CHECK3)
(000005A8 10)
(000005A9 51 35 4 0 0		1059)
(000005AE 26 248 2		IDC_GENERALOPTIONS_CHILD2_CHECK4)
(000005B1 9 248 2		'IDC_GENERALOPTIONS_CHILD2_CHECK4)
(000005B4 10)
(000005B5 51 36 4 0 0		1060)
(000005BA 26 247 2		IDC_GENERALOPTIONS_CHILD2_CHECK5)
(000005BD 9 247 2		'IDC_GENERALOPTIONS_CHILD2_CHECK5)
(000005C0 10)
(000005C1 51 37 4 0 0		1061)
(000005C6 26 246 2		IDC_GENERALOPTIONS_CHILD2_CHECK6)
(000005C9 9 246 2		'IDC_GENERALOPTIONS_CHILD2_CHECK6)
(000005CC 10)
(000005CD 51 44 4 0 0		1068)
(000005D2 26 245 2		IDC_PROJECTPROP_CHILD1_HOMEDIRECTORY_STATIC)
(000005D5 9 245 2		'IDC_PROJECTPROP_CHILD1_HOMEDIRECTORY_STATIC)
(000005D8 10)
(000005D9 51 45 4 0 0		1069)
(000005DE 26 244 2		IDC_PROJECTPROP_CHILD1_LOOKIN_STATIC)
(000005E1 9 244 2		'IDC_PROJECTPROP_CHILD1_LOOKIN_STATIC)
(000005E4 10)
(000005E5 51 47 4 0 0		1071)
(000005EA 26 243 2		IDC_WINDOWATTRIBUTES_MARGIN_EDIT2)
(000005ED 9 243 2		'IDC_WINDOWATTRIBUTES_MARGIN_EDIT2)
(000005F0 10)
(000005F1 51 48 4 0 0		1072)
(000005F6 26 242 2		IDC_AUTOLISP_SAVECHANGES_YES_BUTTON)
(000005F9 9 242 2		'IDC_AUTOLISP_SAVECHANGES_YES_BUTTON)
(000005FC 10)
(000005FD 51 49 4 0 0		1073)
(00000602 26 241 2		IDC_AUTOLISP_SAVECHANGES_NO_BUTTON)
(00000605 9 241 2		'IDC_AUTOLISP_SAVECHANGES_NO_BUTTON)
(00000608 10)
(00000609 51 51 4 0 0		1075)
(0000060E 26 240 2		IDC_PROJECTPROP_CHILD1_LIST)
(00000611 9 240 2		'IDC_PROJECTPROP_CHILD1_LIST)
(00000614 10)
(00000615 51 56 4 0 0		1080)
(0000061A 26 239 2		IDC_REPLACE_DIRECTION_DOWN_RADIO3)
(0000061D 9 239 2		'IDC_REPLACE_DIRECTION_DOWN_RADIO3)
(00000620 10)
(00000621 51 57 4 0 0		1081)
(00000626 26 238 2		IDC_REPLACE_DIRECTION_UP_RADIO4)
(00000629 9 238 2		'IDC_REPLACE_DIRECTION_UP_RADIO4)
(0000062C 10)
(0000062D 51 58 4 0 0		1082)
(00000632 26 237 2		IDC_PROJECTPROP_CHILD2_LINKMODE_RADIO5)
(00000635 9 237 2		'IDC_PROJECTPROP_CHILD2_LINKMODE_RADIO5)
(00000638 10)
(00000639 51 59 4 0 0		1083)
(0000063E 26 236 2		IDC_PROJECTPROP_CHILD2_MERGEMODE_RADIO6)
(00000641 9 236 2		'IDC_PROJECTPROP_CHILD2_MERGEMODE_RADIO6)
(00000644 10)
(00000645 51 60 4 0 0		1084)
(0000064A 26 235 2		IDC_PROJECTPROP_CHILD2_MERGEMODE_RADIO7)
(0000064D 9 235 2		'IDC_PROJECTPROP_CHILD2_MERGEMODE_RADIO7)
(00000650 10)
(00000651 51 61 4 0 0		1085)
(00000656 26 234 2		IDC_WINDOWATTRIBUTES_CHECK1)
(00000659 9 234 2		'IDC_WINDOWATTRIBUTES_CHECK1)
(0000065C 10)
(0000065D 51 62 4 0 0		1086)
(00000662 26 233 2		IDC_WINDOWATTRIBUTES_CHECK2)
(00000665 9 233 2		'IDC_WINDOWATTRIBUTES_CHECK2)
(00000668 10)
(00000669 51 63 4 0 0		1087)
(0000066E 26 232 2		IDC_PROJECTPROP_CHILD2_MESSAGEMODE_RADIO8)
(00000671 9 232 2		'IDC_PROJECTPROP_CHILD2_MESSAGEMODE_RADIO8)
(00000674 10)
(00000675 51 64 4 0 0		1088)
(0000067A 26 231 2		IDC_PROJECTPROP_CHILD2_MESSAGEMODE_RADIO9)
(0000067D 9 231 2		'IDC_PROJECTPROP_CHILD2_MESSAGEMODE_RADIO9)
(00000680 10)
(00000681 51 65 4 0 0		1089)
(00000686 26 230 2		IDC_PROJECTPROP_CHILD2_MESSAGEMODE_RADIO10)
(00000689 9 230 2		'IDC_PROJECTPROP_CHILD2_MESSAGEMODE_RADIO10)
(0000068C 10)
(0000068D 51 66 4 0 0		1090)
(00000692 26 229 2		IDC_X_LIST)
(00000695 9 229 2		'IDC_X_LIST)
(00000698 10)
(00000699 51 67 4 0 0		1091)
(0000069E 26 228 2		IDC_WINDOWATTRIBUTES_CHECK3)
(000006A1 9 228 2		'IDC_WINDOWATTRIBUTES_CHECK3)
(000006A4 10)
(000006A5 51 68 4 0 0		1092)
(000006AA 26 227 2		IDC_TOOLBARS_CHECK4)
(000006AD 9 227 2		'IDC_TOOLBARS_CHECK4)
(000006B0 10)
(000006B1 51 72 4 0 0		1096)
(000006B6 26 226 2		IDC_REPLACE_REPLACEWITH_COMBO2)
(000006B9 9 226 2		'IDC_REPLACE_REPLACEWITH_COMBO2)
(000006BC 10)
(000006BD 51 74 4 0 0		1098)
(000006C2 26 225 2		IDC_PAGESETUP_MARGINS_LEFT_EDIT3)
(000006C5 9 225 2		'IDC_PAGESETUP_MARGINS_LEFT_EDIT3)
(000006C8 10)
(000006C9 51 75 4 0 0		1099)
(000006CE 26 224 2		IDC_TOOLBARS_CHECK5)
(000006D1 9 224 2		'IDC_TOOLBARS_CHECK5)
(000006D4 10)
(000006D5 51 76 4 0 0		1100)
(000006DA 26 223 2		IDC_TOOLBARS_APPLY_BUTTON)
(000006DD 9 223 2		'IDC_TOOLBARS_APPLY_BUTTON)
(000006E0 10)
(000006E1 51 77 4 0 0		1101)
(000006E6 26 222 2		IDC_TOOLBARS_CLOSE_BUTTON)
(000006E9 9 222 2		'IDC_TOOLBARS_CLOSE_BUTTON)
(000006EC 10)
(000006ED 51 78 4 0 0		1102)
(000006F2 26 221 2		IDC_PAGESETUP_MARGINS_RIGHT_EDIT4)
(000006F5 9 221 2		'IDC_PAGESETUP_MARGINS_RIGHT_EDIT4)
(000006F8 10)
(000006F9 51 79 4 0 0		1103)
(000006FE 26 220 2		IDC_PAGESETUP_MARGINS_TOP_EDIT5)
(00000701 9 220 2		'IDC_PAGESETUP_MARGINS_TOP_EDIT5)
(00000704 10)
(00000705 51 80 4 0 0		1104)
(0000070A 26 219 2		IDC_PAGESETUP_MARGINS_BOTTOM_EDIT6)
(0000070D 9 219 2		'IDC_PAGESETUP_MARGINS_BOTTOM_EDIT6)
(00000710 10)
(00000711 51 83 4 0 0		1107)
(00000716 26 218 2		IDC_FILETOWRITEBLOCKTO_SCROLLBAR1)
(00000719 9 218 2		'IDC_FILETOWRITEBLOCKTO_SCROLLBAR1)
(0000071C 10)
(0000071D 51 90 4 0 0		1114)
(00000722 26 217 2		IDC_FORMAT_MORE_SPLIT_CHECK2)
(00000725 9 217 2		'IDC_FORMAT_MORE_SPLIT_CHECK2)
(00000728 10)
(00000729 51 92 4 0 0		1116)
(0000072E 26 216 2		IDC_CASING_U_NONE_RADIO11)
(00000731 9 216 2		'IDC_CASING_U_NONE_RADIO11)
(00000734 10)
(00000735 51 93 4 0 0		1117)
(0000073A 26 215 2		IDC_CASING_U_LOWER_RADIO12)
(0000073D 9 215 2		'IDC_CASING_U_LOWER_RADIO12)
(00000740 10)
(00000741 51 94 4 0 0		1118)
(00000746 26 214 2		IDC_CASING_U_UPPER_RADIO13)
(00000749 9 214 2		'IDC_CASING_U_UPPER_RADIO13)
(0000074C 10)
(0000074D 51 95 4 0 0		1119)
(00000752 26 213 2		IDC_APPENDSTRING_EDIT)
(00000755 9 213 2		'IDC_APPENDSTRING_EDIT)
(00000758 10)
(00000759 51 97 4 0 0		1121)
(0000075E 26 212 2		IDC_AUTOLISP_TEXT_STATIC)
(00000761 9 212 2		'IDC_AUTOLISP_TEXT_STATIC)
(00000764 10)
(00000765 51 113 4 0 0		1137)
(0000076A 26 211 2		IDC_FORMAT_FORMCLOSING_STATIC)
(0000076D 9 211 2		'IDC_FORMAT_FORMCLOSING_STATIC)
(00000770 10)
(00000771 51 115 4 0 0		1139)
(00000776 26 210 2		IDC_FORMAT_MOREOPTIONS_BUTTON)
(00000779 9 210 2		'IDC_FORMAT_MOREOPTIONS_BUTTON)
(0000077C 10)
(0000077D 51 118 4 0 0		1142)
(00000782 26 209 2		IDC_FORMAT_MORE_RIGHT_STATIC)
(00000785 9 209 2		'IDC_FORMAT_MORE_RIGHT_STATIC)
(00000788 10)
(00000789 51 119 4 0 0		1143)
(0000078E 26 208 2		IDC_FORMAT_MORE_NARROW_STATIC)
(00000791 9 208 2		'IDC_FORMAT_MORE_NARROW_STATIC)
(00000794 10)
(00000795 51 120 4 0 0		1144)
(0000079A 26 207 2		IDC_FORMAT_MORE_MAXWIDE_STATIC)
(0000079D 9 207 2		'IDC_FORMAT_MORE_MAXWIDE_STATIC)
(000007A0 10)
(000007A1 51 121 4 0 0		1145)
(000007A6 26 206 2		IDC_FORMAT_MORE_SINGLE_STATIC)
(000007A9 9 206 2		'IDC_FORMAT_MORE_SINGLE_STATIC)
(000007AC 10)
(000007AD 51 122 4 0 0		1146)
(000007B2 26 205 2		IDC_FORMAT_MORE_MAXLENGTH_STATIC)
(000007B5 9 205 2		'IDC_FORMAT_MORE_MAXLENGTH_STATIC)
(000007B8 10)
(000007B9 51 123 4 0 0		1147)
(000007BE 26 204 2		IDC_FORMAT_MORE_EDIT1)
(000007C1 9 204 2		'IDC_FORMAT_MORE_EDIT1)
(000007C4 10)
(000007C5 51 124 4 0 0		1148)
(000007CA 26 203 2		IDC_FORMAT_MORE_EDIT2)
(000007CD 9 203 2		'IDC_FORMAT_MORE_EDIT2)
(000007D0 10)
(000007D1 51 125 4 0 0		1149)
(000007D6 26 202 2		IDC_FORMAT_MORE_EDIT3)
(000007D9 9 202 2		'IDC_FORMAT_MORE_EDIT3)
(000007DC 10)
(000007DD 51 126 4 0 0		1150)
(000007E2 26 201 2		IDC_FORMAT_MORE_EDIT4)
(000007E5 9 201 2		'IDC_FORMAT_MORE_EDIT4)
(000007E8 10)
(000007E9 51 127 4 0 0		1151)
(000007EE 26 200 2		IDC_FORMAT_MORE_EDIT6)
(000007F1 9 200 2		'IDC_FORMAT_MORE_EDIT6)
(000007F4 10)
(000007F5 51 128 4 0 0		1152)
(000007FA 26 199 2		IDC_FORMAT_MORE_CLOSINGSTYLE_STATIC)
(000007FD 9 199 2		'IDC_FORMAT_MORE_CLOSINGSTYLE_STATIC)
(00000800 10)
(00000801 51 129 4 0 0		1153)
(00000806 26 198 2		IDC_CLOSING_SAME_RADIO1)
(00000809 9 198 2		'IDC_CLOSING_SAME_RADIO1)
(0000080C 10)
(0000080D 51 130 4 0 0		1154)
(00000812 26 197 2		IDC_CLOSING_INNER_RADIO2)
(00000815 9 197 2		'IDC_CLOSING_INNER_RADIO2)
(00000818 10)
(00000819 51 131 4 0 0		1155)
(0000081E 26 196 2		IDC_CLOSING_OUTER_RADIO3)
(00000821 9 196 2		'IDC_CLOSING_OUTER_RADIO3)
(00000824 10)
(00000825 51 132 4 0 0		1156)
(0000082A 26 195 2		IDC_FORMAT_MORE_LONGLIST_STATIC)
(0000082D 9 195 2		'IDC_FORMAT_MORE_LONGLIST_STATIC)
(00000830 10)
(00000831 51 133 4 0 0		1157)
(00000836 26 194 2		IDC_LONGLIST_SINGLE_RADIO4)
(00000839 9 194 2		'IDC_LONGLIST_SINGLE_RADIO4)
(0000083C 10)
(0000083D 51 134 4 0 0		1158)
(00000842 26 193 2		IDC_LONGLIST_2COLUMN_RADIO5)
(00000845 9 193 2		'IDC_LONGLIST_2COLUMN_RADIO5)
(00000848 10)
(00000849 51 135 4 0 0		1159)
(0000084E 26 192 2		IDC_LONGLIST_MULTI_RADIO6)
(00000851 9 192 2		'IDC_LONGLIST_MULTI_RADIO6)
(00000854 10)
(00000855 51 136 4 0 0		1160)
(0000085A 26 191 2		IDC_LONGLIST_FILL_RADIO7)
(0000085D 9 191 2		'IDC_LONGLIST_FILL_RADIO7)
(00000860 10)
(00000861 51 137 4 0 0		1161)
(00000866 26 190 2		IDC_FORMAT_MORE_CASING_UNPROTECTED_STATIC)
(00000869 9 190 2		'IDC_FORMAT_MORE_CASING_UNPROTECTED_STATIC)
(0000086C 10)
(0000086D 51 138 4 0 0		1162)
(00000872 26 189 2		IDC_FORMAT_MORE_CASING_PROTECTED_STATIC)
(00000875 9 189 2		'IDC_FORMAT_MORE_CASING_PROTECTED_STATIC)
(00000878 10)
(00000879 51 139 4 0 0		1163)
(0000087E 26 188 2		IDC_CASING_P_NONE_RADIO8)
(00000881 9 188 2		'IDC_CASING_P_NONE_RADIO8)
(00000884 10)
(00000885 51 140 4 0 0		1164)
(0000088A 26 187 2		IDC_CASING_P_LOWER_RADIO9)
(0000088D 9 187 2		'IDC_CASING_P_LOWER_RADIO9)
(00000890 10)
(00000891 51 141 4 0 0		1165)
(00000896 26 186 2		IDC_CASING_P_UPPER_RADIO10)
(00000899 9 186 2		'IDC_CASING_P_UPPER_RADIO10)
(0000089C 10)
(0000089D 51 142 4 0 0		1166)
(000008A2 26 185 2		IDC_FORMAT_MORE_PRESERVE_CHECK1)
(000008A5 9 185 2		'IDC_FORMAT_MORE_PRESERVE_CHECK1)
(000008A8 10)
(000008A9 51 143 4 0 0		1167)
(000008AE 26 184 2		IDC_FORMAT_MORE_INSERT_TABS_CHECK3)
(000008B1 9 184 2		'IDC_FORMAT_MORE_INSERT_TABS_CHECK3)
(000008B4 10)
(000008B5 51 144 4 0 0		1168)
(000008BA 26 183 2		IDC_FORMAT_MORE_SAVE_CHECK4)
(000008BD 9 183 2		'IDC_FORMAT_MORE_SAVE_CHECK4)
(000008C0 10)
(000008C1 51 145 4 0 0		1169)
(000008C6 26 182 2		IDC_FORMAT_MORE_INSERT_FORM_CHECK5)
(000008C9 9 182 2		'IDC_FORMAT_MORE_INSERT_FORM_CHECK5)
(000008CC 10)
(000008CD 51 146 4 0 0		1170)
(000008D2 26 181 2		IDC_FORMAT_MORE_COMMENT_EDIT)
(000008D5 9 181 2		'IDC_FORMAT_MORE_COMMENT_EDIT)
(000008D8 10)
(000008D9 51 147 4 0 0		1171)
(000008DE 26 180 2		IDC_FORMAT_MORE_STATIC)
(000008E1 9 180 2		'IDC_FORMAT_MORE_STATIC)
(000008E4 10)
(000008E5 51 148 4 0 0		1172)
(000008EA 26 179 2		IDC_FORMAT_MORE_BASEOPTIONS_BUTTON)
(000008ED 9 179 2		'IDC_FORMAT_MORE_BASEOPTIONS_BUTTON)
(000008F0 10)
(000008F1 51 149 4 0 0		1173)
(000008F6 26 178 2		IDC_FORMAT_MORE_REVERTDEFAULT_BUTTON)
(000008F9 9 178 2		'IDC_FORMAT_MORE_REVERTDEFAULT_BUTTON)
(000008FC 10)
(000008FD 51 150 4 0 0		1174)
(00000902 26 177 2		IDC_APROPOS1_STATIC)
(00000905 9 177 2		'IDC_APROPOS1_STATIC)
(00000908 10)
(00000909 51 151 4 0 0		1175)
(0000090E 26 176 2		IDC_COLORING_SQL_RADIO5)
(00000911 9 176 2		'IDC_COLORING_SQL_RADIO5)
(00000914 10)
(00000915 51 152 4 0 0		1176)
(0000091A 26 175 2		IDC_COLORSTYLE_COLORINGFILES_STATIC)
(0000091D 9 175 2		'IDC_COLORSTYLE_COLORINGFILES_STATIC)
(00000920 10)
(00000921 51 153 4 0 0		1177)
(00000926 26 174 2		IDC_COLORING_NONE_RADIO1)
(00000929 9 174 2		'IDC_COLORING_NONE_RADIO1)
(0000092C 10)
(0000092D 51 154 4 0 0		1178)
(00000932 26 173 2		IDC_COLORING_AUTOLISP_RADIO2)
(00000935 9 173 2		'IDC_COLORING_AUTOLISP_RADIO2)
(00000938 10)
(00000939 51 155 4 0 0		1179)
(0000093E 26 172 2		IDC_COLORING_C_RADIO3)
(00000941 9 172 2		'IDC_COLORING_C_RADIO3)
(00000944 10)
(00000945 51 156 4 0 0		1180)
(0000094A 26 171 2		IDC_COLORING_DCL_RADIO4)
(0000094D 9 171 2		'IDC_COLORING_DCL_RADIO4)
(00000950 10)
(00000951 51 157 4 0 0		1181)
(00000956 26 170 2		IDC_DATEANDTIME_DATE_STATIC)
(00000959 9 170 2		'IDC_DATEANDTIME_DATE_STATIC)
(0000095C 10)
(0000095D 51 158 4 0 0		1182)
(00000962 26 169 2		IDC_DATEANDTIME_TIME_STATIC)
(00000965 9 169 2		'IDC_DATEANDTIME_TIME_STATIC)
(00000968 10)
(00000969 51 161 4 0 0		1185)
(0000096E 26 168 2		IDC_ENTERDIALOG_COMBO)
(00000971 9 168 2		'IDC_ENTERDIALOG_COMBO)
(00000974 10)
(00000975 51 162 4 0 0		1186)
(0000097A 26 167 2		IDC_ENTERDIALOGNAME_STATIC)
(0000097D 9 167 2		'IDC_ENTERDIALOGNAME_STATIC)
(00000980 10)
(00000981 51 163 4 0 0		1187)
(00000986 26 166 2		IDC_ENTERITEMNAME_EDIT)
(00000989 9 166 2		'IDC_ENTERITEMNAME_EDIT)
(0000098C 10)
(0000098D 51 165 4 0 0		1189)
(00000992 26 165 2		IDC_ERRORTRACE_LIST)
(00000995 9 165 2		'IDC_ERRORTRACE_LIST)
(00000998 10)
(00000999 51 166 4 0 0		1190)
(0000099E 26 164 2		IDC_ERRORTRACE_STATIC)
(000009A1 9 164 2		'IDC_ERRORTRACE_STATIC)
(000009A4 10)
(000009A5 51 167 4 0 0		1191)
(000009AA 26 163 2		IDC_FILETOWRITEBLOCKTO_SAVEIN_STATIC)
(000009AD 9 163 2		'IDC_FILETOWRITEBLOCKTO_SAVEIN_STATIC)
(000009B0 10)
(000009B1 51 168 4 0 0		1192)
(000009B6 26 162 2		IDC_FILETOWRITEBLOCKTO_SAVEIN_COMBO1)
(000009B9 9 162 2		'IDC_FILETOWRITEBLOCKTO_SAVEIN_COMBO1)
(000009BC 10)
(000009BD 51 169 4 0 0		1193)
(000009C2 26 161 2		IDC_FILETOWRITEBLOCKTO_EDIT1)
(000009C5 9 161 2		'IDC_FILETOWRITEBLOCKTO_EDIT1)
(000009C8 10)
(000009C9 51 170 4 0 0		1194)
(000009CE 26 160 2		IDC_FILETOWRITEBLOCKTO_FILENAME_STATIC)
(000009D1 9 160 2		'IDC_FILETOWRITEBLOCKTO_FILENAME_STATIC)
(000009D4 10)
(000009D5 51 171 4 0 0		1195)
(000009DA 26 159 2		IDC_FILETOWRITEBLOCKTO_FILENAME_EDIT2)
(000009DD 9 159 2		'IDC_FILETOWRITEBLOCKTO_FILENAME_EDIT2)
(000009E0 10)
(000009E1 51 172 4 0 0		1196)
(000009E6 26 158 2		IDC_FILETOWRITEBLOCKTO_SAVEASTYPE_STATIC)
(000009E9 9 158 2		'IDC_FILETOWRITEBLOCKTO_SAVEASTYPE_STATIC)
(000009EC 10)
(000009ED 51 173 4 0 0		1197)
(000009F2 26 157 2		IDC_FILETOWRITEBLOCKTO_SAVEASTYPE_COMBO2)
(000009F5 9 157 2		'IDC_FILETOWRITEBLOCKTO_SAVEASTYPE_COMBO2)
(000009F8 10)
(000009F9 51 174 4 0 0		1198)
(000009FE 26 156 2		IDC_FILETOWRITEBLOCKTO_SAVE_BUTTON)
(00000A01 9 156 2		'IDC_FILETOWRITEBLOCKTO_SAVE_BUTTON)
(00000A04 10)
(00000A05 51 175 4 0 0		1199)
(00000A0A 26 155 2		IDC_FILTERFLAGS_MATCHBYFLAGS_STATIC)
(00000A0D 9 155 2		'IDC_FILTERFLAGS_MATCHBYFLAGS_STATIC)
(00000A10 10)
(00000A11 51 176 4 0 0		1200)
(00000A16 26 154 2		IDC_FILTERFLAGS_PROTECT_CHECK1)
(00000A19 9 154 2		'IDC_FILTERFLAGS_PROTECT_CHECK1)
(00000A1C 10)
(00000A1D 51 177 4 0 0		1201)
(00000A22 26 153 2		IDC_FILTERFLAGS_TRACE_CHECK2)
(00000A25 9 153 2		'IDC_FILTERFLAGS_TRACE_CHECK2)
(00000A28 10)
(00000A29 51 178 4 0 0		1202)
(00000A2E 26 152 2		IDC_FILTERFLAGS_DEBUG_CHECK3)
(00000A31 9 152 2		'IDC_FILTERFLAGS_DEBUG_CHECK3)
(00000A34 10)
(00000A35 51 179 4 0 0		1203)
(00000A3A 26 151 2		IDC_FILTERFLAGS_EXPORT_CHECK4)
(00000A3D 9 151 2		'IDC_FILTERFLAGS_EXPORT_CHECK4)
(00000A40 10)
(00000A41 51 180 4 0 0		1204)
(00000A46 26 150 2		IDC_FILTERVALUE_MATCHBYVALUE_STATIC)
(00000A49 9 150 2		'IDC_FILTERVALUE_MATCHBYVALUE_STATIC)
(00000A4C 10)
(00000A4D 51 181 4 0 0		1205)
(00000A52 26 149 2		IDC_FILTERVALUE_ALL_RADIO1)
(00000A55 9 149 2		'IDC_FILTERVALUE_ALL_RADIO1)
(00000A58 10)
(00000A59 51 182 4 0 0		1206)
(00000A5E 26 148 2		IDC_FILTERVALUE_NULL_RADIO2)
(00000A61 9 148 2		'IDC_FILTERVALUE_NULL_RADIO2)
(00000A64 10)
(00000A65 51 183 4 0 0		1207)
(00000A6A 26 147 2		IDC_FILTERVALUE_NONULL_RADIO3)
(00000A6D 9 147 2		'IDC_FILTERVALUE_NONULL_RADIO3)
(00000A70 10)
(00000A71 51 184 4 0 0		1208)
(00000A76 26 146 2		IDC_FILTERVALUE_FUNCTION_RADIO4)
(00000A79 9 146 2		'IDC_FILTERVALUE_FUNCTION_RADIO4)
(00000A7C 10)
(00000A7D 51 185 4 0 0		1209)
(00000A82 26 145 2		IDC_FILTERVALUE_USER_RADIO5)
(00000A85 9 145 2		'IDC_FILTERVALUE_USER_RADIO5)
(00000A88 10)
(00000A89 51 186 4 0 0		1210)
(00000A8E 26 144 2		IDC_FILTERVALUE_BUILTIN_RADIO6)
(00000A91 9 144 2		'IDC_FILTERVALUE_BUILTIN_RADIO6)
(00000A94 10)
(00000A95 51 187 4 0 0		1211)
(00000A9A 26 143 2		IDC_FILTERVALUE_EXSUBR_RADIO7)
(00000A9D 9 143 2		'IDC_FILTERVALUE_EXSUBR_RADIO7)
(00000AA0 10)
(00000AA1 51 188 4 0 0		1212)
(00000AA6 26 142 2		IDC_GENERALOPTIONS_CHILD1_DESKTOP_STATIC)
(00000AA9 9 142 2		'IDC_GENERALOPTIONS_CHILD1_DESKTOP_STATIC)
(00000AAC 10)
(00000AAD 51 189 4 0 0		1213)
(00000AB2 26 141 2		IDC_GENERALOPTIONS_CHILD1_SETQ_STATIC)
(00000AB5 9 141 2		'IDC_GENERALOPTIONS_CHILD1_SETQ_STATIC)
(00000AB8 10)
(00000AB9 51 191 4 0 0		1215)
(00000ABE 26 140 2		IDC_GENERALOPTIONS_CHILD2_ANIMATION_STATIC)
(00000AC1 9 140 2		'IDC_GENERALOPTIONS_CHILD2_ANIMATION_STATIC)
(00000AC4 10)
(00000AC5 51 192 4 0 0		1216)
(00000ACA 26 139 2		IDC_GENERALOPTIONS_CHILD2_ANIMATION_EDIT)
(00000ACD 9 139 2		'IDC_GENERALOPTIONS_CHILD2_ANIMATION_EDIT)
(00000AD0 10)
(00000AD1 51 193 4 0 0		1217)
(00000AD6 26 138 2		IDC_GENERALOPTIONS_CHILD2_STATIC)
(00000AD9 9 138 2		'IDC_GENERALOPTIONS_CHILD2_STATIC)
(00000ADC 10)
(00000ADD 51 194 4 0 0		1218)
(00000AE2 26 137 2		IDC_GOTOLINE_COMBO)
(00000AE5 9 137 2		'IDC_GOTOLINE_COMBO)
(00000AE8 10)
(00000AE9 51 195 4 0 0		1219)
(00000AEE 26 136 2		IDC_GOTOLINE_STATIC)
(00000AF1 9 136 2		'IDC_GOTOLINE_STATIC)
(00000AF4 10)
(00000AF5 51 196 4 0 0		1220)
(00000AFA 26 135 2		IDC_INDENTBLOCK_COMBO)
(00000AFD 9 135 2		'IDC_INDENTBLOCK_COMBO)
(00000B00 10)
(00000B01 51 197 4 0 0		1221)
(00000B06 26 134 2		IDC_INSPECT_COMBO)
(00000B09 9 134 2		'IDC_INSPECT_COMBO)
(00000B0C 10)
(00000B0D 51 198 4 0 0		1222)
(00000B12 26 133 2		IDC_INSPECTSTM_EDIT)
(00000B15 9 133 2		'IDC_INSPECTSTM_EDIT)
(00000B18 10)
(00000B19 51 206 4 0 0		1230)
(00000B1E 26 132 2		IDC_NIL_EDIT)
(00000B21 9 132 2		'IDC_NIL_EDIT)
(00000B24 10)
(00000B25 51 207 4 0 0		1231)
(00000B2A 26 131 2		IDC_PAGESETUP_HEADERFOOTER_STATIC)
(00000B2D 9 131 2		'IDC_PAGESETUP_HEADERFOOTER_STATIC)
(00000B30 10)
(00000B31 51 208 4 0 0		1232)
(00000B36 26 130 2		IDC_PAGESETUP_HEADERFOOTER_EDIT1)
(00000B39 9 130 2		'IDC_PAGESETUP_HEADERFOOTER_EDIT1)
(00000B3C 10)
(00000B3D 51 209 4 0 0		1233)
(00000B42 26 129 2		IDC_PAGESETUP_HEADERFOOTER_EDIT2)
(00000B45 9 129 2		'IDC_PAGESETUP_HEADERFOOTER_EDIT2)
(00000B48 10)
(00000B49 51 210 4 0 0		1234)
(00000B4E 26 128 2		IDC_PAGESETUP_PRINTPAGEMARGINS_STATIC)
(00000B51 9 128 2		'IDC_PAGESETUP_PRINTPAGEMARGINS_STATIC)
(00000B54 10)
(00000B55 51 211 4 0 0		1235)
(00000B5A 26 127 2		IDC_PAGESETUP_MARGINS_INCHES_RADIO1)
(00000B5D 9 127 2		'IDC_PAGESETUP_MARGINS_INCHES_RADIO1)
(00000B60 10)
(00000B61 51 212 4 0 0		1236)
(00000B66 26 126 2		IDC_PAGESETUP_MARGINS_MILLIMETERS_RADIO2)
(00000B69 9 126 2		'IDC_PAGESETUP_MARGINS_MILLIMETERS_RADIO2)
(00000B6C 10)
(00000B6D 51 213 4 0 0		1237)
(00000B72 26 125 2		IDC_PAGESETUP_MARGINS_TOP_STATIC)
(00000B75 9 125 2		'IDC_PAGESETUP_MARGINS_TOP_STATIC)
(00000B78 10)
(00000B79 51 214 4 0 0		1238)
(00000B7E 26 124 2		IDC_PAGESETUP_MARGINS_LEFT_STATIC)
(00000B81 9 124 2		'IDC_PAGESETUP_MARGINS_LEFT_STATIC)
(00000B84 10)
(00000B85 51 215 4 0 0		1239)
(00000B8A 26 123 2		IDC_PAGESETUP_MARGINS_RIGHT_STATIC)
(00000B8D 9 123 2		'IDC_PAGESETUP_MARGINS_RIGHT_STATIC)
(00000B90 10)
(00000B91 51 216 4 0 0		1240)
(00000B96 26 122 2		IDC_PAGESETUP_MARGINS_BOTTOM_STATIC)
(00000B99 9 122 2		'IDC_PAGESETUP_MARGINS_BOTTOM_STATIC)
(00000B9C 10)
(00000B9D 51 217 4 0 0		1241)
(00000BA2 26 121 2		IDC_PAGESETUP_HELP_BUTTON)
(00000BA5 9 121 2		'IDC_PAGESETUP_HELP_BUTTON)
(00000BA8 10)
(00000BA9 51 218 4 0 0		1242)
(00000BAE 26 120 2		IDC_PAGESETUP_FONT_BUTTON)
(00000BB1 9 120 2		'IDC_PAGESETUP_FONT_BUTTON)
(00000BB4 10)
(00000BB5 51 219 4 0 0		1243)
(00000BBA 26 119 2		IDC_PAGESETUP_STATIC)
(00000BBD 9 119 2		'IDC_PAGESETUP_STATIC)
(00000BC0 10)
(00000BC1 51 220 4 0 0		1244)
(00000BC6 26 118 2		IDC_PROJECTNAME_NAME_STATIC)
(00000BC9 9 118 2		'IDC_PROJECTNAME_NAME_STATIC)
(00000BCC 10)
(00000BCD 51 221 4 0 0		1245)
(00000BD2 26 117 2		IDC_PROJECTPROP_CHILD1_LOOKIN_EDIT1)
(00000BD5 9 117 2		'IDC_PROJECTPROP_CHILD1_LOOKIN_EDIT1)
(00000BD8 10)
(00000BD9 51 222 4 0 0		1246)
(00000BDE 26 116 2		IDC_PROJECTPROP_CHILD1_EDIT2)
(00000BE1 9 116 2		'IDC_PROJECTPROP_CHILD1_EDIT2)
(00000BE4 10)
(00000BE5 51 223 4 0 0		1247)
(00000BEA 26 115 2		IDC_PROJECTPROP_CHILD1_UNSELECTALL1_BUTTON)
(00000BED 9 115 2		'IDC_PROJECTPROP_CHILD1_UNSELECTALL1_BUTTON)
(00000BF0 10)
(00000BF1 51 224 4 0 0		1248)
(00000BF6 26 114 2		IDC_PROJECTPROP_CHILD1_UNSELECTALL2_BUTTON)
(00000BF9 9 114 2		'IDC_PROJECTPROP_CHILD1_UNSELECTALL2_BUTTON)
(00000BFC 10)
(00000BFD 51 225 4 0 0		1249)
(00000C02 26 113 2		IDC_PROJECTPROP_CHILD2_COMPMODE_STATIC)
(00000C05 9 113 2		'IDC_PROJECTPROP_CHILD2_COMPMODE_STATIC)
(00000C08 10)
(00000C09 51 226 4 0 0		1250)
(00000C0E 26 112 2		IDC_PROJECTPROP_CHILD2_COMPMODE_RADIO1)
(00000C11 9 112 2		'IDC_PROJECTPROP_CHILD2_COMPMODE_RADIO1)
(00000C14 10)
(00000C15 51 227 4 0 0		1251)
(00000C1A 26 111 2		IDC_PROJECTPROP_CHILD2_COMPMODE_RADIO2)
(00000C1D 9 111 2		'IDC_PROJECTPROP_CHILD2_COMPMODE_RADIO2)
(00000C20 10)
(00000C21 51 228 4 0 0		1252)
(00000C26 26 110 2		IDC_PROJECTPROP_CHILD2_MERGEMODE_STATIC)
(00000C29 9 110 2		'IDC_PROJECTPROP_CHILD2_MERGEMODE_STATIC)
(00000C2C 10)
(00000C2D 51 229 4 0 0		1253)
(00000C32 26 109 2		IDC_PROJECTPROP_CHILD2_LINKMODE_STATIC)
(00000C35 9 109 2		'IDC_PROJECTPROP_CHILD2_LINKMODE_STATIC)
(00000C38 10)
(00000C39 51 230 4 0 0		1254)
(00000C3E 26 108 2		IDC_PROJECTPROP_CHILD2_LINKMODE_RADIO3)
(00000C41 9 108 2		'IDC_PROJECTPROP_CHILD2_LINKMODE_RADIO3)
(00000C44 10)
(00000C45 51 231 4 0 0		1255)
(00000C4A 26 107 2		IDC_PROJECTPROP_CHILD2_LINKMODE_RADIO4)
(00000C4D 9 107 2		'IDC_PROJECTPROP_CHILD2_LINKMODE_RADIO4)
(00000C50 10)
(00000C51 51 232 4 0 0		1256)
(00000C56 26 106 2		IDC_PROJECTPROP_CHILD2_MESSAGEMODE_STATIC)
(00000C59 9 106 2		'IDC_PROJECTPROP_CHILD2_MESSAGEMODE_STATIC)
(00000C5C 10)
(00000C5D 51 233 4 0 0		1257)
(00000C62 26 105 2		IDC_PROJECTPROP_CHILD2_CHECK1)
(00000C65 9 105 2		'IDC_PROJECTPROP_CHILD2_CHECK1)
(00000C68 10)
(00000C69 51 234 4 0 0		1258)
(00000C6E 26 104 2		IDC_PROJECTPROP_CHILD2_CHECK2)
(00000C71 9 104 2		'IDC_PROJECTPROP_CHILD2_CHECK2)
(00000C74 10)
(00000C75 51 235 4 0 0		1259)
(00000C7A 26 103 2		IDC_PROJECTPROP_CHILD2_FAS_STATIC)
(00000C7D 9 103 2		'IDC_PROJECTPROP_CHILD2_FAS_STATIC)
(00000C80 10)
(00000C81 51 236 4 0 0		1260)
(00000C86 26 102 2		IDC_PROJECTPROP_CHILD2_FAS_EDIT2)
(00000C89 9 102 2		'IDC_PROJECTPROP_CHILD2_FAS_EDIT2)
(00000C8C 10)
(00000C8D 51 237 4 0 0		1261)
(00000C92 26 101 2		IDC_PROJECTPROP_CHILD2_FAS_BUTTON)
(00000C95 9 101 2		'IDC_PROJECTPROP_CHILD2_FAS_BUTTON)
(00000C98 10)
(00000C99 51 238 4 0 0		1262)
(00000C9E 26 100 2		IDC_PROJECTPROP_CHILD2_TMP_STATIC)
(00000CA1 9 100 2		'IDC_PROJECTPROP_CHILD2_TMP_STATIC)
(00000CA4 10)
(00000CA5 51 239 4 0 0		1263)
(00000CAA 26 99 2		IDC_PROJECTPROP_CHILD2_TMP_EDIT1)
(00000CAD 9 99 2		'IDC_PROJECTPROP_CHILD2_TMP_EDIT1)
(00000CB0 10)
(00000CB1 51 240 4 0 0		1264)
(00000CB6 26 98 2		IDC_PROJECTPROP_CHILD2_TMP_BUTTON)
(00000CB9 9 98 2		'IDC_PROJECTPROP_CHILD2_TMP_BUTTON)
(00000CBC 10)
(00000CBD 51 241 4 0 0		1265)
(00000CC2 26 97 2		IDC_PROJECTPROP_CHILD2_GLOBALDEC_BUTTON)
(00000CC5 9 97 2		'IDC_PROJECTPROP_CHILD2_GLOBALDEC_BUTTON)
(00000CC8 10)
(00000CC9 51 242 4 0 0		1266)
(00000CCE 26 96 2		IDC_REPLACE_FINDWHAT_STATIC)
(00000CD1 9 96 2		'IDC_REPLACE_FINDWHAT_STATIC)
(00000CD4 10)
(00000CD5 51 243 4 0 0		1267)
(00000CDA 26 95 2		IDC_REPLACE_FINDWHAT_COMBO1)
(00000CDD 9 95 2		'IDC_REPLACE_FINDWHAT_COMBO1)
(00000CE0 10)
(00000CE1 51 244 4 0 0		1268)
(00000CE6 26 94 2		IDC_REPLACE_REPLACEWITH_STATIC)
(00000CE9 9 94 2		'IDC_REPLACE_REPLACEWITH_STATIC)
(00000CEC 10)
(00000CED 51 245 4 0 0		1269)
(00000CF2 26 93 2		IDC_REPLACE_DIRECTION_STATIC)
(00000CF5 9 93 2		'IDC_REPLACE_DIRECTION_STATIC)
(00000CF8 10)
(00000CF9 51 246 4 0 0		1270)
(00000CFE 26 92 2		IDC_REPLACE_SEARCH_STATIC)
(00000D01 9 92 2		'IDC_REPLACE_SEARCH_STATIC)
(00000D04 10)
(00000D05 51 247 4 0 0		1271)
(00000D0A 26 91 2		IDC_REPLACE_SEARCH_CURRENTSELECTION_RADIO1)
(00000D0D 9 91 2		'IDC_REPLACE_SEARCH_CURRENTSELECTION_RADIO1)
(00000D10 10)
(00000D11 51 248 4 0 0		1272)
(00000D16 26 90 2		IDC_REPLACE_SEARCH_CURRENTFILE_RADIO2)
(00000D19 9 90 2		'IDC_REPLACE_SEARCH_CURRENTFILE_RADIO2)
(00000D1C 10)
(00000D1D 51 249 4 0 0		1273)
(00000D22 26 89 2		IDC_REPLACE_WHOLEWORD_CHECK1)
(00000D25 9 89 2		'IDC_REPLACE_WHOLEWORD_CHECK1)
(00000D28 10)
(00000D29 51 250 4 0 0		1274)
(00000D2E 26 88 2		IDC_REPLACE_CASE_CHECK2)
(00000D31 9 88 2		'IDC_REPLACE_CASE_CHECK2)
(00000D34 10)
(00000D35 51 251 4 0 0		1275)
(00000D3A 26 87 2		IDC_REPLACE_FIND_BUTTON)
(00000D3D 9 87 2		'IDC_REPLACE_FIND_BUTTON)
(00000D40 10)
(00000D41 51 252 4 0 0		1276)
(00000D46 26 86 2		IDC_REPLACE_REPLACE_BUTTON)
(00000D49 9 86 2		'IDC_REPLACE_REPLACE_BUTTON)
(00000D4C 10)
(00000D4D 51 253 4 0 0		1277)
(00000D52 26 85 2		IDC_REPLACE_REPLACEALL_BUTTON)
(00000D55 9 85 2		'IDC_REPLACE_REPLACEALL_BUTTON)
(00000D58 10)
(00000D59 51 254 4 0 0		1278)
(00000D5E 26 84 2		IDC_SYMBOLSERVICE_NAME_STATIC)
(00000D61 9 84 2		'IDC_SYMBOLSERVICE_NAME_STATIC)
(00000D64 10)
(00000D65 51 255 4 0 0		1279)
(00000D6A 26 83 2		IDC_SYMBOLSERVICE_NAME_COMBO)
(00000D6D 9 83 2		'IDC_SYMBOLSERVICE_NAME_COMBO)
(00000D70 10)
(00000D71 51 0 5 0 0		1280)
(00000D76 26 82 2		IDC_SYMBOLSERVICE_STATIC)
(00000D79 9 82 2		'IDC_SYMBOLSERVICE_STATIC)
(00000D7C 10)
(00000D7D 51 1 5 0 0		1281)
(00000D82 26 81 2		IDC_SYMBOLSERVICE2_NAME_STATIC)
(00000D85 9 81 2		'IDC_SYMBOLSERVICE2_NAME_STATIC)
(00000D88 10)
(00000D89 51 2 5 0 0		1282)
(00000D8E 26 80 2		IDC_SYMBOLSERVICE2_NAME_EDIT1)
(00000D91 9 80 2		'IDC_SYMBOLSERVICE2_NAME_EDIT1)
(00000D94 10)
(00000D95 51 3 5 0 0		1283)
(00000D9A 26 79 2		IDC_SYMBOLSERVICE2_VALUE_STATIC)
(00000D9D 9 79 2		'IDC_SYMBOLSERVICE2_VALUE_STATIC)
(00000DA0 10)
(00000DA1 51 4 5 0 0		1284)
(00000DA6 26 78 2		IDC_SYMBOLSERVICE2_VALUE_EDIT2)
(00000DA9 9 78 2		'IDC_SYMBOLSERVICE2_VALUE_EDIT2)
(00000DAC 10)
(00000DAD 51 5 5 0 0		1285)
(00000DB2 26 77 2		IDC_SYMBOLSERVICE2_FLAGS_STATIC)
(00000DB5 9 77 2		'IDC_SYMBOLSERVICE2_FLAGS_STATIC)
(00000DB8 10)
(00000DB9 51 6 5 0 0		1286)
(00000DBE 26 76 2		IDC_SYMBOLSERVICE2_FLAGS_CHECK1)
(00000DC1 9 76 2		'IDC_SYMBOLSERVICE2_FLAGS_CHECK1)
(00000DC4 10)
(00000DC5 51 7 5 0 0		1287)
(00000DCA 26 75 2		IDC_SYMBOLSERVICE2_FLAGS_CHECK2)
(00000DCD 9 75 2		'IDC_SYMBOLSERVICE2_FLAGS_CHECK2)
(00000DD0 10)
(00000DD1 51 8 5 0 0		1288)
(00000DD6 26 74 2		IDC_SYMBOLSERVICE2_FLAGS_CHECK3)
(00000DD9 9 74 2		'IDC_SYMBOLSERVICE2_FLAGS_CHECK3)
(00000DDC 10)
(00000DDD 51 9 5 0 0		1289)
(00000DE2 26 73 2		IDC_SYMBOLSERVICE2_FLAGS_CHECK4)
(00000DE5 9 73 2		'IDC_SYMBOLSERVICE2_FLAGS_CHECK4)
(00000DE8 10)
(00000DE9 51 10 5 0 0		1290)
(00000DEE 26 72 2		IDC_SYMBOLSERVICE2_STATIC)
(00000DF1 9 72 2		'IDC_SYMBOLSERVICE2_STATIC)
(00000DF4 10)
(00000DF5 51 11 5 0 0		1291)
(00000DFA 26 71 2		IDC_TOOLBARS_STATIC)
(00000DFD 9 71 2		'IDC_TOOLBARS_STATIC)
(00000E00 10)
(00000E01 51 12 5 0 0		1292)
(00000E06 26 70 2		IDC_TOOLBARS_CHECK1)
(00000E09 9 70 2		'IDC_TOOLBARS_CHECK1)
(00000E0C 10)
(00000E0D 51 13 5 0 0		1293)
(00000E12 26 69 2		IDC_TOOLBARS_CHECK2)
(00000E15 9 69 2		'IDC_TOOLBARS_CHECK2)
(00000E18 10)
(00000E19 51 14 5 0 0		1294)
(00000E1E 26 68 2		IDC_TOOLBARS_CHECK3)
(00000E21 9 68 2		'IDC_TOOLBARS_CHECK3)
(00000E24 10)
(00000E25 51 15 5 0 0		1295)
(00000E2A 26 67 2		IDC_TOOLBARS_HIDEALL_BUTTON)
(00000E2D 9 67 2		'IDC_TOOLBARS_HIDEALL_BUTTON)
(00000E30 10)
(00000E31 51 16 5 0 0		1296)
(00000E36 26 66 2		IDC_TOOLBARS_SHOWALL_BUTTON)
(00000E39 9 66 2		'IDC_TOOLBARS_SHOWALL_BUTTON)
(00000E3C 10)
(00000E3D 51 17 5 0 0		1297)
(00000E42 26 65 2		IDC_TRACESTACK_LIST1)
(00000E45 9 65 2		'IDC_TRACESTACK_LIST1)
(00000E48 10)
(00000E49 51 18 5 0 0		1298)
(00000E4E 26 64 2		IDC_TRACESTACK_STATIC)
(00000E51 9 64 2		'IDC_TRACESTACK_STATIC)
(00000E54 10)
(00000E55 51 19 5 0 0		1299)
(00000E5A 26 63 2		IDC_WINDOWATTRIBUTES_TEXTCOLORS_STATIC)
(00000E5D 9 63 2		'IDC_WINDOWATTRIBUTES_TEXTCOLORS_STATIC)
(00000E60 10)
(00000E61 51 21 5 0 0		1301)
(00000E66 26 62 2		IDC_WINDOWATTRIBUTES_TABWIDTH_STATIC)
(00000E69 9 62 2		'IDC_WINDOWATTRIBUTES_TABWIDTH_STATIC)
(00000E6C 10)
(00000E6D 51 22 5 0 0		1302)
(00000E72 26 61 2		IDC_WINDOWATTRIBUTES_LEFTMARGIN_STATIC)
(00000E75 9 61 2		'IDC_WINDOWATTRIBUTES_LEFTMARGIN_STATIC)
(00000E78 10)
(00000E79 51 23 5 0 0		1303)
(00000E7E 26 60 2		IDC_WINDOWATTRIBUTES_STATIC)
(00000E81 9 60 2		'IDC_WINDOWATTRIBUTES_STATIC)
(00000E84 10)
(00000E85 51 24 5 0 0		1304)
(00000E8A 26 59 2		IDC_REVIEW_REVIEWSEL_TEXT2_STATIC)
(00000E8D 9 59 2		'IDC_REVIEW_REVIEWSEL_TEXT2_STATIC)
(00000E90 10)
(00000E91 51 26 5 0 0		1306)
(00000E96 26 58 2		IDC_PROJECTPROP_CHILD1_BUTTON1)
(00000E99 9 58 2		'IDC_PROJECTPROP_CHILD1_BUTTON1)
(00000E9C 10)
(00000E9D 51 27 5 0 0		1307)
(00000EA2 26 57 2		IDC_PROJECTPROP_CHILD1_BUTTON2)
(00000EA5 9 57 2		'IDC_PROJECTPROP_CHILD1_BUTTON2)
(00000EA8 10)
(00000EA9 51 28 5 0 0		1308)
(00000EAE 26 56 2		IDC_PROJECTPROP_CHILD1_BUTTON3)
(00000EB1 9 56 2		'IDC_PROJECTPROP_CHILD1_BUTTON3)
(00000EB4 10)
(00000EB5 51 29 5 0 0		1309)
(00000EBA 26 55 2		IDC_PROJECTPROP_CHILD1_BUTTON4)
(00000EBD 9 55 2		'IDC_PROJECTPROP_CHILD1_BUTTON4)
(00000EC0 10)
(00000EC1 51 30 5 0 0		1310)
(00000EC6 26 54 2		IDC_PROJECTPROP_CHILD1_BUTTON5)
(00000EC9 9 54 2		'IDC_PROJECTPROP_CHILD1_BUTTON5)
(00000ECC 10)
(00000ECD 51 31 5 0 0		1311)
(00000ED2 26 53 2		IDC_PROJECTPROP_CHILD1_BUTTON6)
(00000ED5 9 53 2		'IDC_PROJECTPROP_CHILD1_BUTTON6)
(00000ED8 10)
(00000ED9 51 32 5 0 0		1312)
(00000EDE 26 52 2		IDC_PROJECTPROP_CHILD1_FRAME_STATIC)
(00000EE1 9 52 2		'IDC_PROJECTPROP_CHILD1_FRAME_STATIC)
(00000EE4 10)
(00000EE5 51 33 5 0 0		1313)
(00000EEA 26 51 2		IDC_AUTOLISP_CALLBACKENTRY_STATIC)
(00000EED 9 51 2		'IDC_AUTOLISP_CALLBACKENTRY_STATIC)
(00000EF0 10)
(00000EF1 51 34 5 0 0		1314)
(00000EF6 26 50 2		IDC_AUTOLISP_NOFILE_STATIC)
(00000EF9 9 50 2		'IDC_AUTOLISP_NOFILE_STATIC)
(00000EFC 10)
(00000EFD 51 35 5 0 0		1315)
(00000F02 26 49 2		IDC_AUTOLISP_REPLACE_STATIC)
(00000F05 9 49 2		'IDC_AUTOLISP_REPLACE_STATIC)
(00000F08 10)
(00000F09 51 36 5 0 0		1316)
(00000F0E 26 48 2		IDC_AUTOLISP_REVERTBUFFER_STATIC)
(00000F11 9 48 2		'IDC_AUTOLISP_REVERTBUFFER_STATIC)
(00000F14 10)
(00000F15 51 37 5 0 0		1317)
(00000F1A 26 47 2		IDC_AUTOLISP_SAVECHANGES_STATIC)
(00000F1D 9 47 2		'IDC_AUTOLISP_SAVECHANGES_STATIC)
(00000F20 10)
(00000F21 51 38 5 0 0		1318)
(00000F26 26 46 2		IDC_AUTOLISP_WRONGINPUT_STATIC)
(00000F29 9 46 2		'IDC_AUTOLISP_WRONGINPUT_STATIC)
(00000F2C 10)
(00000F2D 51 39 5 0 0		1319)
(00000F32 26 45 2		IDC_DATEANDTIME_DATE_LIST)
(00000F35 9 45 2		'IDC_DATEANDTIME_DATE_LIST)
(00000F38 10)
(00000F39 51 40 5 0 0		1320)
(00000F3E 26 44 2		IDC_DATEANDTIME_TIME_LIST)
(00000F41 9 44 2		'IDC_DATEANDTIME_TIME_LIST)
(00000F44 10)
(00000F45 51 41 5 0 0		1321)
(00000F4A 26 43 2		IDC_WINDOWATTRIBUTES_COLORPANEL_BUTTON)
(00000F4D 9 43 2		'IDC_WINDOWATTRIBUTES_COLORPANEL_BUTTON)
(00000F50 10)
(00000F51 51 42 5 0 0		1322)
(00000F56 26 42 2		IDC_AUTOLISP_INVALIDAPP_STATIC)
(00000F59 9 42 2		'IDC_AUTOLISP_INVALIDAPP_STATIC)
(00000F5C 10)
(00000F5D 51 44 5 0 0		1324)
(00000F62 26 41 2		IDC_APPDIRECTORY_STATIC)
(00000F65 9 41 2		'IDC_APPDIRECTORY_STATIC)
(00000F68 10)
(00000F69 51 45 5 0 0		1325)
(00000F6E 26 40 2		IDC_APPDIRECTORY_BACK_BUTTON)
(00000F71 9 40 2		'IDC_APPDIRECTORY_BACK_BUTTON)
(00000F74 10)
(00000F75 51 46 5 0 0		1326)
(00000F7A 26 39 2		IDC_APPDIRECTORY_NEXT_BUTTON)
(00000F7D 9 39 2		'IDC_APPDIRECTORY_NEXT_BUTTON)
(00000F80 10)
(00000F81 51 47 5 0 0		1327)
(00000F86 26 38 2		IDC_WIZARDMODE_EMPTYFRAME_STATIC)
(00000F89 9 38 2		'IDC_WIZARDMODE_EMPTYFRAME_STATIC)
(00000F8C 10)
(00000F8D 51 48 5 0 0		1328)
(00000F92 26 37 2		IDC_WIZARDMODE_BACK_BUTTON)
(00000F95 9 37 2		'IDC_WIZARDMODE_BACK_BUTTON)
(00000F98 10)
(00000F99 51 49 5 0 0		1329)
(00000F9E 26 36 2		IDC_WIZARDMODE_NEXT_BUTTON)
(00000FA1 9 36 2		'IDC_WIZARDMODE_NEXT_BUTTON)
(00000FA4 10)
(00000FA5 51 50 5 0 0		1330)
(00000FAA 26 35 2		IDC_LISPFILES_EMPTYFRAME_STATIC)
(00000FAD 9 35 2		'IDC_LISPFILES_EMPTYFRAME_STATIC)
(00000FB0 10)
(00000FB1 51 51 5 0 0		1331)
(00000FB6 26 34 2		IDC_LISPFILES_BACK_BUTTON)
(00000FB9 9 34 2		'IDC_LISPFILES_BACK_BUTTON)
(00000FBC 10)
(00000FBD 51 52 5 0 0		1332)
(00000FC2 26 33 2		IDC_LISPFILES_NEXT_BUTTON)
(00000FC5 9 33 2		'IDC_LISPFILES_NEXT_BUTTON)
(00000FC8 10)
(00000FC9 51 53 5 0 0		1333)
(00000FCE 26 32 2		IDC_REVIEW_BUILDAPPFRAME_STATIC)
(00000FD1 9 32 2		'IDC_REVIEW_BUILDAPPFRAME_STATIC)
(00000FD4 10)
(00000FD5 51 54 5 0 0		1334)
(00000FDA 26 31 2		IDC_AUTOLISP_REVERTBUFFER_YES_BUTTON)
(00000FDD 9 31 2		'IDC_AUTOLISP_REVERTBUFFER_YES_BUTTON)
(00000FE0 10)
(00000FE1 51 55 5 0 0		1335)
(00000FE6 26 30 2		IDC_AUTOLISP_REVERTBUFFER_NO_BUTTON)
(00000FE9 9 30 2		'IDC_AUTOLISP_REVERTBUFFER_NO_BUTTON)
(00000FEC 10)
(00000FED 51 56 5 0 0		1336)
(00000FF2 26 29 2		IDC_AUTOLISP_FILEEXISTS_YES_BUTTON)
(00000FF5 9 29 2		'IDC_AUTOLISP_FILEEXISTS_YES_BUTTON)
(00000FF8 10)
(00000FF9 51 57 5 0 0		1337)
(00000FFE 26 28 2		IDC_AUTOLISP_FILEEXISTS_NO_BUTTON)
(00001001 9 28 2		'IDC_AUTOLISP_FILEEXISTS_NO_BUTTON)
(00001004 10)
(00001005 51 58 5 0 0		1338)
(0000100A 26 27 2		IDC_AUTOLISP_NOFILEEXISTS_YES_BUTTON)
(0000100D 9 27 2		'IDC_AUTOLISP_NOFILEEXISTS_YES_BUTTON)
(00001010 10)
(00001011 51 59 5 0 0		1339)
(00001016 26 26 2		IDC_AUTOLISP_NOFILEEXISTS_NO_BUTTON)
(00001019 9 26 2		'IDC_AUTOLISP_NOFILEEXISTS_NO_BUTTON)
(0000101C 10)
(0000101D 51 60 5 0 0		1340)
(00001022 26 25 2		IDC_AUTOLISP_REPLACEFILE_YES_BUTTON)
(00001025 9 25 2		'IDC_AUTOLISP_REPLACEFILE_YES_BUTTON)
(00001028 10)
(00001029 51 61 5 0 0		1341)
(0000102E 26 24 2		IDC_AUTOLISP_REPLACEFILE_NO_BUTTON)
(00001031 9 24 2		'IDC_AUTOLISP_REPLACEFILE_NO_BUTTON)
(00001034 10)
(00001035 51 62 5 0 0		1342)
(0000103A 26 23 2		IDC_LISPFILES_TOP_BUTTON)
(0000103D 9 23 2		'IDC_LISPFILES_TOP_BUTTON)
(00001040 10)
(00001041 51 63 5 0 0		1343)
(00001046 26 22 2		IDC_LISPFILES_UP_BUTTON)
(00001049 9 22 2		'IDC_LISPFILES_UP_BUTTON)
(0000104C 10)
(0000104D 51 64 5 0 0		1344)
(00001052 26 21 2		IDC_LISPFILES_DOWN_BUTTON)
(00001055 9 21 2		'IDC_LISPFILES_DOWN_BUTTON)
(00001058 10)
(00001059 51 65 5 0 0		1345)
(0000105E 26 20 2		IDC_LISPFILES_BOTTOM_BUTTON)
(00001061 9 20 2		'IDC_LISPFILES_BOTTOM_BUTTON)
(00001064 10)
(00001065 51 66 5 0 0		1346)
(0000106A 26 19 2		IDC_APPDIRECTORY_TEXT2_STATIC)
(0000106D 9 19 2		'IDC_APPDIRECTORY_TEXT2_STATIC)
(00001070 10)
(00001071 51 67 5 0 0		1347)
(00001076 26 18 2		IDC_APPLICATIONOPTIONS_SELECTAPP_TEXT2_STATIC)
(00001079 9 18 2		'IDC_APPLICATIONOPTIONS_SELECTAPP_TEXT2_STATIC)
(0000107C 10)
(0000107D 51 68 5 0 0		1348)
(00001082 26 17 2		IDC_APPLICATIONOPTIONS_CHECKBOXFRAME_STATIC)
(00001085 9 17 2		'IDC_APPLICATIONOPTIONS_CHECKBOXFRAME_STATIC)
(00001088 10)
(00001089 51 69 5 0 0		1349)
(0000108E 26 16 2		IDC_APPLICATIONOPTIONS_ACTIVEX_CHECK1)
(00001091 9 16 2		'IDC_APPLICATIONOPTIONS_ACTIVEX_CHECK1)
(00001094 10)
(00001095 51 70 5 0 0		1350)
(0000109A 26 15 2		IDC_APPLICATIONOPTIONS_SEPARATE_CHECK2)
(0000109D 9 15 2		'IDC_APPLICATIONOPTIONS_SEPARATE_CHECK2)
(000010A0 10)
(000010A1 51 71 5 0 0		1351)
(000010A6 26 14 2		IDC_APPLICATIONOPTIONS_SELECTAPP_STATIC)
(000010A9 9 14 2		'IDC_APPLICATIONOPTIONS_SELECTAPP_STATIC)
(000010AC 10)
(000010AD 51 72 5 0 0		1352)
(000010B2 26 13 2		IDC_APPLICATIONOPTIONS_SELECTAPP_TEXT1_STATIC)
(000010B5 9 13 2		'IDC_APPLICATIONOPTIONS_SELECTAPP_TEXT1_STATIC)
(000010B8 10)
(000010B9 51 73 5 0 0		1353)
(000010BE 26 12 2		IDC_APPLICATIONOPTIONS_EMPTYFRAME_STATIC)
(000010C1 9 12 2		'IDC_APPLICATIONOPTIONS_EMPTYFRAME_STATIC)
(000010C4 10)
(000010C5 51 74 5 0 0		1354)
(000010CA 26 11 2		IDC_APPLICATIONOPTIONS_BACK_BUTTON)
(000010CD 9 11 2		'IDC_APPLICATIONOPTIONS_BACK_BUTTON)
(000010D0 10)
(000010D1 51 75 5 0 0		1355)
(000010D6 26 10 2		IDC_APPLICATIONOPTIONS_NEXT_BUTTON)
(000010D9 9 10 2		'IDC_APPLICATIONOPTIONS_NEXT_BUTTON)
(000010DC 10)
(000010DD 51 76 5 0 0		1356)
(000010E2 26 9 2		IDC_AP_TD_LODEDIT)
(000010E5 9 9 2		'IDC_AP_TD_LODEDIT)
(000010E8 10)
(000010E9 51 114 5 0 0		1394)
(000010EE 26 8 2		IDC_AP_AO_ACTIVEXSUPPORT)
(000010F1 9 8 2		'IDC_AP_AO_ACTIVEXSUPPORT)
(000010F4 10)
(000010F5 51 115 5 0 0		1395)
(000010FA 26 7 2		IDC_AP_AO_SEPARATENAMESPASE)
(000010FD 9 7 2		'IDC_AP_AO_SEPARATENAMESPASE)
(00001100 10)
(00001101 51 118 5 0 0		1398)
(00001106 26 6 2		IDC_AP_RF_LB)
(00001109 9 6 2		'IDC_AP_RF_LB)
(0000110C 10)
(0000110D 51 119 5 0 0		1399)
(00001112 26 5 2		IDC_AP_LF_ADD)
(00001115 9 5 2		'IDC_AP_LF_ADD)
(00001118 10)
(00001119 51 120 5 0 0		1400)
(0000111E 26 4 2		IDC_AP_LF_REMOVE)
(00001121 9 4 2		'IDC_AP_LF_REMOVE)
(00001124 10)
(00001125 51 121 5 0 0		1401)
(0000112A 26 3 2		IDC_AP_LF_DDLB)
(0000112D 9 3 2		'IDC_AP_LF_DDLB)
(00001130 10)
(00001131 51 122 5 0 0		1402)
(00001136 26 2 2		IDC_AP_RF_ADD)
(00001139 9 2 2		'IDC_AP_RF_ADD)
(0000113C 10)
(0000113D 51 123 5 0 0		1403)
(00001142 26 1 2		IDC_AP_RF_REMOVE)
(00001145 9 1 2		'IDC_AP_RF_REMOVE)
(00001148 10)
(00001149 51 124 5 0 0		1404)
(0000114E 26 0 2		IDC_AP_RF_DDLB)
(00001151 9 0 2		'IDC_AP_RF_DDLB)
(00001154 10)
(00001155 51 125 5 0 0		1405)
(0000115A 26 255 1		IDC_AP_AO_GROUPBOX)
(0000115D 9 255 1		'IDC_AP_AO_GROUPBOX)
(00001160 10)
(00001161 51 126 5 0 0		1406)
(00001166 26 254 1		IDC_AO_LF_LB)
(00001169 9 254 1		'IDC_AO_LF_LB)
(0000116C 10)
(0000116D 51 127 5 0 0		1407)
(00001172 26 253 1		IDC_AP_LC_STANDARD)
(00001175 9 253 1		'IDC_AP_LC_STANDARD)
(00001178 10)
(00001179 51 128 5 0 0		1408)
(0000117E 26 252 1		IDC_AP_LC_OPTANDLINK)
(00001181 9 252 1		'IDC_AP_LC_OPTANDLINK)
(00001184 10)
(00001185 51 129 5 0 0		1409)
(0000118A 26 251 1		IDC_AP_LC_GB)
(0000118D 9 251 1		'IDC_AP_LC_GB)
(00001190 10)
(00001191 51 130 5 0 0		1410)
(00001196 26 250 1		IDC_AP_TD_LOD)
(00001199 9 250 1		'IDC_AP_TD_LOD)
(0000119C 10)
(0000119D 51 131 5 0 0		1411)
(000011A2 26 249 1		IDC_AP_TD_LODBROWSE)
(000011A5 9 249 1		'IDC_AP_TD_LODBROWSE)
(000011A8 10)
(000011A9 51 132 5 0 0		1412)
(000011AE 26 248 1		IDC_AP_TD_TD)
(000011B1 9 248 1		'IDC_AP_TD_TD)
(000011B4 10)
(000011B5 51 133 5 0 0		1413)
(000011BA 26 247 1		IDC_AP_TD_TDEDIT)
(000011BD 9 247 1		'IDC_AP_TD_TDEDIT)
(000011C0 10)
(000011C1 51 134 5 0 0		1414)
(000011C6 26 246 1		IDC_AP_TD_TDDBROWSE)
(000011C9 9 246 1		'IDC_AP_TD_TDDBROWSE)
(000011CC 10)
(000011CD 51 55 51 0 0		13111)
(000011D2 26 245 1		IDC_PROJECTPROP_CHILD1_BUTTON7)
(000011D5 9 245 1		'IDC_PROJECTPROP_CHILD1_BUTTON7)
(000011D8 10)
(000011D9 51 66 51 0 0		13122)
(000011DE 26 244 1		IDC_PROJECTPROP_CHILD1_STATIC)
(000011E1 9 244 1		'IDC_PROJECTPROP_CHILD1_STATIC)
(000011E4 10)
(000011E5 51 248 255 0 0		65528)
(000011EA 26 243 1		IDC_WINDOWATTRIBUTES_STATIC5)
(000011ED 9 243 1		'IDC_WINDOWATTRIBUTES_STATIC5)
(000011F0 10)
(000011F1 51 249 255 0 0		65529)
(000011F6 26 242 1		IDC_WINDOWATTRIBUTES_STATIC4)
(000011F9 9 242 1		'IDC_WINDOWATTRIBUTES_STATIC4)
(000011FC 10)
(000011FD 51 250 255 0 0		65530)
(00001202 26 241 1		IDC_WINDOWATTRIBUTES_STATIC3)
(00001205 9 241 1		'IDC_WINDOWATTRIBUTES_STATIC3)
(00001208 10)
(00001209 51 251 255 0 0		65531)
(0000120E 26 240 1		IDC_WINDOWATTRIBUTES_STATIC2)
(00001211 9 240 1		'IDC_WINDOWATTRIBUTES_STATIC2)
(00001214 10)
(00001215 51 252 255 0 0		65532)
(0000121A 26 239 1		IDC_WINDOWATTRIBUTES_STATIC1)
(0000121D 9 239 1		'IDC_WINDOWATTRIBUTES_STATIC1)
(00001220 10)
(00001221 51 253 255 0 0		65533)
(00001226 26 238 1		IDC_PROJECTPROP_CHILD2_PARENT_EDIT)
(00001229 9 238 1		'IDC_PROJECTPROP_CHILD2_PARENT_EDIT)
(0000122C 10)
(0000122D 51 254 255 0 0		65534)
(00001232 26 237 1		IDC_FORMAT_MORE_CASING_STATIC)
(00001235 9 237 1		'IDC_FORMAT_MORE_CASING_STATIC)
(00001238 10)
(00001239 50 255		-1)
(0000123B 26 236 1		IDC_FIND_FINDWHAT_STATIC)
(0000123E 9 236 1		'IDC_FIND_FINDWHAT_STATIC)
(00001241 10)
(00001242 51 255 255 0 0		65535)
(00001247 26 235 1		IDC_WIZARDMODE_TEXT2_STATIC)
(0000124A 9 235 1		'IDC_WIZARDMODE_TEXT2_STATIC)
(0000124D 10)
(0000124E 50 1		1)
(00001250 26 234 1		IDOK)
(00001253 9 234 1		'IDOK)
(00001256 10)
(00001257 50 2		2)
(00001259 26 233 1		IDCANCEL)
(0000125C 9 233 1		'IDCANCEL)
(0000125F 28		[ret])
(00001260 20 0 0 0 0)
(00001265 1		nil)
(00001266 10)
(00001267 9 175 4		'create-host-spouse)
(0000126A 26 232 1		create-host-spouse)
(0000126D 9 232 1		'create-host-spouse)
(00001270 10)
(00001271 9 174 4		'update-host-spouse)
(00001274 26 231 1		update-host-spouse)
(00001277 9 231 1		'update-host-spouse)
(0000127A 10)
(0000127B 9 173 4		'update-los-spouse)
(0000127E 26 230 1		update-los-spouse)
(00001281 9 230 1		'update-los-spouse)
(00001284 10)
(00001285 9 172 4		'destroy-host-spouse)
(00001288 26 229 1		destroy-host-spouse)
(0000128B 9 229 1		'destroy-host-spouse)
(0000128E 10)
(0000128F 9 171 4		'host-spouse-exists-p)
(00001292 26 228 1		host-spouse-exists-p)
(00001295 9 228 1		'host-spouse-exists-p)
(00001298 28		[ret])
(00001299 20 1 0 0 0)
(0000129E 1		nil)
(0000129F 10)
(000012A0 1		nil)
(000012A1 10)
(000012A2 50 1		1)
(000012A4 26 227 1		OFN_READONLY)
(000012A7 9 227 1		'OFN_READONLY)
(000012AA 10)
(000012AB 50 4		4)
(000012AD 26 226 1		OFN_HIDEREADONLY)
(000012B0 9 226 1		'OFN_HIDEREADONLY)
(000012B3 10)
(000012B4 50 8		8)
(000012B6 26 225 1		OFN_NOCHANGEDIR)
(000012B9 9 225 1		'OFN_NOCHANGEDIR)
(000012BC 10)
(000012BD 51 0 2 0 0		512)
(000012C2 26 224 1		OFN_ALLOWMULTISELECT)
(000012C5 9 224 1		'OFN_ALLOWMULTISELECT)
(000012C8 10)
(000012C9 51 0 8 0 0		2048)
(000012CE 26 223 1		OFN_PATHMUSTEXIST)
(000012D1 9 223 1		'OFN_PATHMUSTEXIST)
(000012D4 10)
(000012D5 51 0 16 0 0		4096)
(000012DA 26 222 1		OFN_FILEMUSTEXIST)
(000012DD 9 222 1		'OFN_FILEMUSTEXIST)
(000012E0 10)
(000012E1 51 0 32 0 0		8192)
(000012E6 26 221 1		OFN_CREATEPROMPT)
(000012E9 9 221 1		'OFN_CREATEPROMPT)
(000012EC 10)
(000012ED 51 0 0 8 0		524288)
(000012F2 26 220 1		OFN_EXPLORER)
(000012F5 9 220 1		'OFN_EXPLORER)
(000012F8 10)
(000012F9 50 32		32)
(000012FB 26 219 1		DS_LOCALEDIT)
(000012FE 9 219 1		'DS_LOCALEDIT)
(00001301 10)
(00001302 51 0 1 0 0		256)
(00001307 26 218 1		DS_NOIDLEMSG)
(0000130A 9 218 1		'DS_NOIDLEMSG)
(0000130D 10)
(0000130E 51 128 0 0 0		128)
(00001313 26 217 1		DS_MODALFRAME)
(00001316 9 217 1		'DS_MODALFRAME)
(00001319 10)
(0000131A 50 1		1)
(0000131C 50 31		31)
(0000131E 81 2 216 1 1 0		lsh)
(00001324 26 215 1		WS_POPUP)
(00001327 9 215 1		'WS_POPUP)
(0000132A 10)
(0000132B 51 0 0 0 16		268435456)
(00001330 26 214 1		WS_VISIBLE)
(00001333 9 214 1		'WS_VISIBLE)
(00001336 10)
(00001337 51 0 0 192 0		12582912)
(0000133C 26 213 1		WS_CAPTION)
(0000133F 9 213 1		'WS_CAPTION)
(00001342 10)
(00001343 51 0 0 8 0		524288)
(00001348 26 212 1		WS_SYSMENU)
(0000134B 9 212 1		'WS_SYSMENU)
(0000134E 10)
(0000134F 51 0 0 128 0		8388608)
(00001354 26 211 1		WS_BORDER)
(00001357 9 211 1		'WS_BORDER)
(0000135A 10)
(0000135B 51 0 0 64 0		4194304)
(00001360 26 210 1		WS_DLGFRAME)
(00001363 9 210 1		'WS_DLGFRAME)
(00001366 10)
(00001367 51 0 0 4 0		262144)
(0000136C 26 209 1		WS_THICKFRAME)
(0000136F 9 209 1		'WS_THICKFRAME)
(00001372 10)
(00001373 51 0 0 0 64		1073741824)
(00001378 26 208 1		WS_CHILD)
(0000137B 9 208 1		'WS_CHILD)
(0000137E 10)
(0000137F 51 0 0 1 0		65536)
(00001384 26 207 1		WS_TABSTOP)
(00001387 9 207 1		'WS_TABSTOP)
(0000138A 10)
(0000138B 51 0 0 2 0		131072)
(00001390 26 206 1		WS_GROUP)
(00001393 9 206 1		'WS_GROUP)
(00001396 10)
(00001397 51 0 0 32 0		2097152)
(0000139C 26 205 1		WS_VSCROLL)
(0000139F 9 205 1		'WS_VSCROLL)
(000013A2 10)
(000013A3 51 0 0 0 8		134217728)
(000013A8 26 204 1		WS_DISABLED)
(000013AB 9 204 1		'WS_DISABLED)
(000013AE 10)
(000013AF 50 1		1)
(000013B1 26 203 1		LBS_NOTIFY)
(000013B4 9 203 1		'LBS_NOTIFY)
(000013B7 10)
(000013B8 50 2		2)
(000013BA 26 202 1		LBS_SORT)
(000013BD 9 202 1		'LBS_SORT)
(000013C0 10)
(000013C1 50 64		64)
(000013C3 26 201 1		LBS_HASSTRINGS)
(000013C6 9 201 1		'LBS_HASSTRINGS)
(000013C9 10)
(000013CA 50 1		1)
(000013CC 26 200 1		ES_CENTER)
(000013CF 9 200 1		'ES_CENTER)
(000013D2 10)
(000013D3 50 4		4)
(000013D5 26 199 1		ES_MULTILINE)
(000013D8 9 199 1		'ES_MULTILINE)
(000013DB 10)
(000013DC 50 64		64)
(000013DE 26 198 1		ES_AUTOVSCROLL)
(000013E1 9 198 1		'ES_AUTOVSCROLL)
(000013E4 10)
(000013E5 51 128 0 0 0		128)
(000013EA 26 197 1		ES_AUTOHSCROLL)
(000013ED 9 197 1		'ES_AUTOHSCROLL)
(000013F0 10)
(000013F1 51 0 8 0 0		2048)
(000013F6 26 196 1		ES_READONLY)
(000013F9 9 196 1		'ES_READONLY)
(000013FC 10)
(000013FD 51 0 16 0 0		4096)
(00001402 26 195 1		ES_WANTRETURN)
(00001405 9 195 1		'ES_WANTRETURN)
(00001408 10)
(00001409 51 0 0 4 0		262144)
(0000140E 51 0 0 8 0		524288)
(00001413 51 0 0 128 0		8388608)
(00001418 51 0 0 64 0		4194304)
(0000141D 3 215 1		WS_POPUP)
(00001420 51 0 0 0 16		268435456)
(00001425 50 32		32)
(00001427 51 0 1 0 0		256)
(0000142C 81 8 194 1 1 0		logior)
(00001432 26 193 1		*WS_DLG-WITH-SIZE*)
(00001435 9 193 1		'*WS_DLG-WITH-SIZE*)
(00001438 10)
(00001439 51 0 0 1 0		65536)
(0000143E 51 0 0 32 0		2097152)
(00001443 51 0 0 0 16		268435456)
(00001448 51 0 0 0 64		1073741824)
(0000144D 50 2		2)
(0000144F 50 64		64)
(00001451 81 6 194 1 1 0		logior)
(00001457 26 192 1		*LBS_WITH-STRING*)
(0000145A 9 192 1		'*LBS_WITH-STRING*)
(0000145D 10)
(0000145E 51 0 0 0 64		1073741824)
(00001463 51 0 0 0 16		268435456)
(00001468 51 0 0 64 0		4194304)
(0000146D 51 0 0 32 0		2097152)
(00001472 51 0 0 1 0		65536)
(00001477 50 4		4)
(00001479 50 64		64)
(0000147B 51 0 8 0 0		2048)
(00001480 81 8 194 1 1 0		logior)
(00001486 26 191 1		*ES_MESSAGE-BOX*)
(00001489 9 191 1		'*ES_MESSAGE-BOX*)
(0000148C 10)
(0000148D 51 0 8 0 0		2048)
(00001492 51 0 32 0 0		8192)
(00001497 50 8		8)
(00001499 81 3 194 1 1 0		logior)
(0000149F 26 190 1		*OFN-OPEN-EDITOR*)
(000014A2 9 190 1		'*OFN-OPEN-EDITOR*)
(000014A5 10)
(000014A6 51 0 8 0 0		2048)
(000014AB 51 0 16 0 0		4096)
(000014B0 50 4		4)
(000014B2 50 8		8)
(000014B4 81 4 194 1 1 0		logior)
(000014BA 26 189 1		*OFN-INSERT-FILE*)
(000014BD 9 189 1		'*OFN-INSERT-FILE*)
(000014C0 10)
(000014C1 51 0 8 0 0		2048)
(000014C6 50 4		4)
(000014C8 50 8		8)
(000014CA 81 3 194 1 1 0		logior)
(000014D0 26 188 1		*OFN-OPEN-LOG*)
(000014D3 9 188 1		'*OFN-OPEN-LOG*)
(000014D6 10)
(000014D7 9 187 1		"VLMSG.DLL")
(000014DA 51 20 95 0 0		24340)
(000014DF 81 2 186 1 1 0		string-resource)
(000014E5 9 185 1		"*.*")
(000014E8 9 187 1		"VLMSG.DLL")
(000014EB 51 30 95 0 0		24350)
(000014F0 81 2 186 1 1 0		string-resource)
(000014F6 9 184 1		"*.LSP;*.MNL")
(000014F9 9 187 1		"VLMSG.DLL")
(000014FC 51 40 95 0 0		24360)
(00001501 81 2 186 1 1 0		string-resource)
(00001507 9 183 1		"*.DCL")
(0000150A 9 187 1		"VLMSG.DLL")
(0000150D 51 50 95 0 0		24370)
(00001512 81 2 186 1 1 0		string-resource)
(00001518 9 182 1		"*.SQL")
(0000151B 9 187 1		"VLMSG.DLL")
(0000151E 51 60 95 0 0		24380)
(00001523 81 2 186 1 1 0		string-resource)
(00001529 9 181 1		"*.C;*.CPP;*.CC;*.H;*.HPP;*.HH")
(0000152C 57 10 0		list)
(0000152F 27 180 1		*source-file-filters*)
(00001532 9 180 1		'*source-file-filters*)
(00001535 10)
(00001536 3 179 1		*source-file-added-filters*)
(00001539 27 179 1		*source-file-added-filters*)
(0000153C 9 179 1		'*source-file-added-filters*)
(0000153F 10)
(00001540 50 5		5)
(00001542 26 178 1		_*sff-added-limit*)
(00001545 9 178 1		'_*sff-added-limit*)
(00001548 10)
(00001549 1		nil)
(0000154A 10)
(0000154B 1		nil)
(0000154C 10)
(0000154D 1		nil)
(0000154E 10)
(0000154F 1		nil)
(00001550 10)
(00001551 9 170 4		'add-source-file-ext-filter)
(00001554 26 177 1		add-source-file-ext-filter)
(00001557 9 177 1		'add-source-file-ext-filter)
(0000155A 10)
(0000155B 1		nil)
(0000155C 10)
(0000155D 1		nil)
(0000155E 10)
(0000155F 1		nil)
(00001560 10)
(00001561 9 169 4		'choose-editor-file-dialog)
(00001564 26 176 1		choose-editor-file-dialog)
(00001567 9 176 1		'choose-editor-file-dialog)
(0000156A 10)
(0000156B 9 168 4		'_mfiles)
(0000156E 26 175 1		_mfiles)
(00001571 9 175 1		'_mfiles)
(00001574 10)
(00001575 9 167 4		'backup-filename)
(00001578 26 174 1		backup-filename)
(0000157B 9 174 1		'backup-filename)
(0000157E 10)
(0000157F 9 166 4		'file-backup)
(00001582 26 173 1		file-backup)
(00001585 9 173 1		'file-backup)
(00001588 10)
(00001589 50 0		0)
(0000158B 26 172 1		SM_CXSCREEN)
(0000158E 9 172 1		'SM_CXSCREEN)
(00001591 10)
(00001592 50 1		1)
(00001594 26 171 1		SM_CYSCREEN)
(00001597 9 171 1		'SM_CYSCREEN)
(0000159A 10)
(0000159B 50 2		2)
(0000159D 26 170 1		SM_CXVSCROLL)
(000015A0 9 170 1		'SM_CXVSCROLL)
(000015A3 10)
(000015A4 50 4		4)
(000015A6 26 169 1		SM_CYCAPTION)
(000015A9 9 169 1		'SM_CYCAPTION)
(000015AC 10)
(000015AD 50 5		5)
(000015AF 26 168 1		SM_CXBORDER)
(000015B2 9 168 1		'SM_CXBORDER)
(000015B5 10)
(000015B6 50 7		7)
(000015B8 26 167 1		SM_CXDLGFRAME)
(000015BB 9 167 1		'SM_CXDLGFRAME)
(000015BE 10)
(000015BF 50 11		11)
(000015C1 26 166 1		SM_CXICON)
(000015C4 9 166 1		'SM_CXICON)
(000015C7 10)
(000015C8 50 12		12)
(000015CA 26 165 1		SM_CYICON)
(000015CD 9 165 1		'SM_CYICON)
(000015D0 10)
(000015D1 50 15		15)
(000015D3 26 164 1		SM_CYMENU)
(000015D6 9 164 1		'SM_CYMENU)
(000015D9 10)
(000015DA 50 28		28)
(000015DC 26 163 1		SM_CXMIN)
(000015DF 9 163 1		'SM_CXMIN)
(000015E2 10)
(000015E3 50 29		29)
(000015E5 26 162 1		SM_CYMIN)
(000015E8 9 162 1		'SM_CYMIN)
(000015EB 10)
(000015EC 50 32		32)
(000015EE 26 161 1		SM_CXFRAME)
(000015F1 9 161 1		'SM_CXFRAME)
(000015F4 10)
(000015F5 50 38		38)
(000015F7 26 160 1		SM_CXICONSPACING)
(000015FA 9 160 1		'SM_CXICONSPACING)
(000015FD 10)
(000015FE 50 39		39)
(00001600 26 159 1		SM_CYICONSPACING)
(00001603 9 159 1		'SM_CYICONSPACING)
(00001606 10)
(00001607 50 58		58)
(00001609 26 158 1		SM_CYMINIMIZED)
(0000160C 9 158 1		'SM_CYMINIMIZED)
(0000160F 10)
(00001610 9 165 4		'_W-BORDER)
(00001613 26 157 1		_W-BORDER)
(00001616 9 157 1		'_W-BORDER)
(00001619 10)
(0000161A 9 164 4		'_W-BORDER-SIZE)
(0000161D 26 156 1		_W-BORDER-SIZE)
(00001620 9 156 1		'_W-BORDER-SIZE)
(00001623 10)
(00001624 9 163 4		'_W-ICON_SPACE)
(00001627 26 155 1		_W-ICON_SPACE)
(0000162A 9 155 1		'_W-ICON_SPACE)
(0000162D 10)
(0000162E 9 162 4		'_W-CAPTION_WIDTH)
(00001631 26 154 1		_W-CAPTION_WIDTH)
(00001634 9 154 1		'_W-CAPTION_WIDTH)
(00001637 10)
(00001638 9 161 4		'_W-WINDOW_HEIGHT)
(0000163B 26 153 1		_W-WINDOW_HEIGHT)
(0000163E 9 153 1		'_W-WINDOW_HEIGHT)
(00001641 10)
(00001642 9 160 4		'_W-DIALOG-XMIN)
(00001645 26 152 1		_W-DIALOG-XMIN)
(00001648 9 152 1		'_W-DIALOG-XMIN)
(0000164B 10)
(0000164C 9 159 4		'_W-DIALOG-YMIN)
(0000164F 26 151 1		_W-DIALOG-YMIN)
(00001652 9 151 1		'_W-DIALOG-YMIN)
(00001655 10)
(00001656 50 2		2)
(00001658 26 150 1		CBN_DBLCLK)
(0000165B 9 150 1		'CBN_DBLCLK)
(0000165E 10)
(0000165F 50 3		3)
(00001661 26 149 1		CBN_SETFOCUS)
(00001664 9 149 1		'CBN_SETFOCUS)
(00001667 10)
(00001668 50 4		4)
(0000166A 26 148 1		CBN_KILLFOCUS)
(0000166D 9 148 1		'CBN_KILLFOCUS)
(00001670 10)
(00001671 50 7		7)
(00001673 26 147 1		CBN_DROPDOWN)
(00001676 9 147 1		'CBN_DROPDOWN)
(00001679 10)
(0000167A 1		nil)
(0000167B 10)
(0000167C 12 158 4		'run-fast)
(0000167F 26 146 1		run-fast)
(00001682 9 146 1		'run-fast)
(00001685 10)
(00001686 9 157 4		'font-pitch-str->list)
(00001689 26 145 1		font-pitch-str->list)
(0000168C 9 145 1		'font-pitch-str->list)
(0000168F 10)
(00001690 9 187 1		"VLMSG.DLL")
(00001693 51 150 0 0 0		150)
(00001698 81 2 186 1 1 0		string-resource)
(0000169E 53 1 145 1 1 32		font-pitch-str->list)
(000016A4 8 0		UnVar0)
(000016A6 5 0		UnVar0)
(000016A8 40		car)
(000016A9 26 144 1		*inspector-font*)
(000016AC 9 144 1		'*inspector-font*)
(000016AF 10)
(000016B0 5 0		UnVar0)
(000016B2 41		cdr)
(000016B3 40		car)
(000016B4 26 143 1		*inspector-pitch*)
(000016B7 9 143 1		'*inspector-pitch*)
(000016BA 10)
(000016BB 1		nil)
(000016BC 10)
(000016BD 1		nil)
(000016BE 10)
(000016BF 9 156 4		'mswin-help)
(000016C2 26 142 1		mswin-help)
(000016C5 9 142 1		'mswin-help)
(000016C8 28		[ret])
(000016C9 20 0 0 0 0)
(000016CE 1		nil)
(000016CF 10)
(000016D0 9 141 1		'wsyscol)
(000016D3 81 1 117 3 1 0		provide)
(000016D9 10)
(000016DA 9 140 1		'(:COLOR_SCROLLBAR :COLOR_BACKGROUND :COLOR_ACTIVECAPTION :COLOR_INACTIVECAPTION :COLOR_MENU :COLOR_WINDOW :COLOR_WINDOWFRAME :COLOR_MENUTEXT :COLOR_WINDOWTEXT :COLOR_CAPTIONTEXT :COLOR_ACTIVEBORDER :COLOR_INACTIVEBORDER :COLOR_APPWORKSPACE :COLOR_HIGHLIGHT :COLOR_HIGHLIGHTTEXT :COLOR_BTNFACE :COLOR_BTNSHADOW :COLOR_GRAYTEXT :COLOR_BTNTEXT :COLOR_INACTIVECAPTIONTEXT :COLOR_BTNHIGHLIGHT))
(000016DD 26 139 1		*sys-color-tbl*)
(000016E0 9 139 1		'*sys-color-tbl*)
(000016E3 10)
(000016E4 9 155 4		'sys-color)
(000016E7 26 138 1		sys-color)
(000016EA 9 138 1		'sys-color)
(000016ED 10)
(000016EE 9 154 4		'twin.set-sys-colors)
(000016F1 26 137 1		twin.set-sys-colors)
(000016F4 9 137 1		'twin.set-sys-colors)
(000016F7 28		[ret])
(000016F8 20 0 0 0 0)
(000016FD 1		nil)
(000016FE 10)
(000016FF 9 136 1		'dialog)
(00001702 81 1 117 3 1 0		provide)
(00001708 10)
(00001709 1		nil)
(0000170A 10)
(0000170B 9 153 4		'!di-right-mouse-click)
(0000170E 26 135 1		!di-right-mouse-click)
(00001711 9 135 1		'!di-right-mouse-click)
(00001714 10)
(00001715 9 152 4		'!combo_notif-info)
(00001718 26 134 1		!combo_notif-info)
(0000171B 9 134 1		'!combo_notif-info)
(0000171E 10)
(0000171F 9 151 4		'!dialog-escape)
(00001722 26 133 1		!dialog-escape)
(00001725 9 133 1		'!dialog-escape)
(00001728 10)
(00001729 9 150 4		'!dialog-size-hook)
(0000172C 26 132 1		!dialog-size-hook)
(0000172F 9 132 1		'!dialog-size-hook)
(00001732 10)
(00001733 9 149 4		'fcolor)
(00001736 26 131 1		fcolor)
(00001739 9 131 1		'fcolor)
(0000173C 10)
(0000173D 9 148 4		'fcolor<-)
(00001740 26 130 1		fcolor<-)
(00001743 9 130 1		'fcolor<-)
(00001746 10)
(00001747 9 147 4		'bcolor)
(0000174A 26 129 1		bcolor)
(0000174D 9 129 1		'bcolor)
(00001750 10)
(00001751 9 146 4		'bcolor<-)
(00001754 26 128 1		bcolor<-)
(00001757 9 128 1		'bcolor<-)
(0000175A 10)
(0000175B 9 145 4		'dialog._bcolor)
(0000175E 26 127 1		dialog._bcolor)
(00001761 9 127 1		'dialog._bcolor)
(00001764 10)
(00001765 9 144 4		'dialog._bcolor<-)
(00001768 26 126 1		dialog._bcolor<-)
(0000176B 9 126 1		'dialog._bcolor<-)
(0000176E 10)
(0000176F 9 143 4		'dialog-item._bcolor)
(00001772 26 125 1		dialog-item._bcolor)
(00001775 9 125 1		'dialog-item._bcolor)
(00001778 10)
(00001779 9 142 4		'dialog-item._bcolor<-)
(0000177C 26 124 1		dialog-item._bcolor<-)
(0000177F 9 124 1		'dialog-item._bcolor<-)
(00001782 10)
(00001783 9 141 4		'dialog-item._fcolor)
(00001786 26 123 1		dialog-item._fcolor)
(00001789 9 123 1		'dialog-item._fcolor)
(0000178C 10)
(0000178D 9 140 4		'dialog-item._fcolor<-)
(00001790 26 122 1		dialog-item._fcolor<-)
(00001793 9 122 1		'dialog-item._fcolor<-)
(00001796 10)
(00001797 9 139 4		'_set-bit)
(0000179A 26 121 1		_set-bit)
(0000179D 9 121 1		'_set-bit)
(000017A0 10)
(000017A1 50 16		16)
(000017A3 26 120 1		*DIALOG-ESC-BORDER-STYLE*)
(000017A6 9 120 1		'*DIALOG-ESC-BORDER-STYLE*)
(000017A9 10)
(000017AA 9 138 4		'dialog-item.disable)
(000017AD 26 119 1		dialog-item.disable)
(000017B0 9 119 1		'dialog-item.disable)
(000017B3 10)
(000017B4 9 137 4		'dialog-item.disable<-)
(000017B7 26 118 1		dialog-item.disable<-)
(000017BA 9 118 1		'dialog-item.disable<-)
(000017BD 10)
(000017BE 9 136 1		'dialog)
(000017C1 9 117 1		'(instance))
(000017C4 3 116 1		*deftype-hook*)
(000017C7 52 2 1		)
(000017CA 10)
(000017CB 9 136 1		'dialog)
(000017CE 9 115 1		'(dialog-class dialog :BASE :MIXED-PAGE "The class for Windows Dialogs" ((new-instance . dialog.new-instance)) nil ((caption . string) (apex . T) (size fixnum) (font . string) (pitch fixnum) (items . T) (parent . T) (default-push-button . T) (close-box-command . T) (states . T) (l-context . T)) ((create-host-spouse dialog.create-host-spouse) (update-host-spouse dialog.update-host-spouse) (destroy-host-spouse dialog.destroy-host-spouse) (host-spouse-exists-p dialog.host-spouse-exists-p) (print-object . dialog.print-object) (accessed-verify . dialog.accessed-verify) (sync-up dialog.sync-up) (sync-down dialog.sync-down) (!dialog-size-hook . dialog.!dialog-size-hook) (bcolor . dialog.bcolor) (bcolor<- . dialog.bcolor<-) (!dialog-escape . dialog.!dialog-escape) (inspector-binary-slot-descriptions ("(host-spouse-exists-p) " nil host-spouse-exists-p) ("(_msw-style) " nil dialog._msw-style) ("(_border-style) " (fixnum) dialog._border-style dialog._border-style<-) ("(bcolor) " T dialog.bcolor dialog.bcolor<-)) (inspector-slot-printers apex ipoint-prin1-to-string size ipoint-prin1-to-string))))
(000017D1 53 2 114 1 1 32		find-class<-)
(000017D7 10)
(000017D8 9 136 4		'dialogp)
(000017DB 26 113 1		dialogp)
(000017DE 9 113 1		'dialogp)
(000017E1 10)
(000017E2 1		nil)
(000017E3 10)
(000017E4 9 135 4		'dialog.!dialog-size-hook)
(000017E7 26 112 1		dialog.!dialog-size-hook)
(000017EA 9 112 1		'dialog.!dialog-size-hook)
(000017ED 10)
(000017EE 9 134 4		'dialog.!dialog-escape)
(000017F1 26 111 1		dialog.!dialog-escape)
(000017F4 9 111 1		'dialog.!dialog-escape)
(000017F7 10)
(000017F8 50 20		20)
(000017FA 27 110 1		*dflt-dialog-width*)
(000017FD 9 110 1		'*dflt-dialog-width*)
(00001800 10)
(00001801 50 0		0)
(00001803 27 109 1		*dflt-dialog-heigth*)
(00001806 9 109 1		'*dflt-dialog-heigth*)
(00001809 10)
(0000180A 9 133 4		'dialog.new-instance)
(0000180D 26 108 1		dialog.new-instance)
(00001810 9 108 1		'dialog.new-instance)
(00001813 10)
(00001814 9 132 4		'dialog)
(00001817 26 136 1		dialog)
(0000181A 9 136 1		'dialog)
(0000181D 10)
(0000181E 1		nil)
(0000181F 10)
(00001820 9 131 4		'dialog.print-object)
(00001823 26 107 1		dialog.print-object)
(00001826 9 107 1		'dialog.print-object)
(00001829 10)
(0000182A 9 130 4		'sync-up)
(0000182D 26 106 1		sync-up)
(00001830 9 106 1		'sync-up)
(00001833 10)
(00001834 9 129 4		'dialog.sync-up)
(00001837 26 105 1		dialog.sync-up)
(0000183A 9 105 1		'dialog.sync-up)
(0000183D 10)
(0000183E 9 128 4		'sync-down)
(00001841 26 104 1		sync-down)
(00001844 9 104 1		'sync-down)
(00001847 10)
(00001848 9 127 4		'dialog.sync-down)
(0000184B 26 103 1		dialog.sync-down)
(0000184E 9 103 1		'dialog.sync-down)
(00001851 10)
(00001852 9 102 1		'dialog-item)
(00001855 9 117 1		'(instance))
(00001858 3 116 1		*deftype-hook*)
(0000185B 52 2 1		)
(0000185E 10)
(0000185F 9 102 1		'dialog-item)
(00001862 9 101 1		'(abstract-class dialog-item :BASE :MIXED-PAGE "The abstract class for Dialog Items" ((new-instance . dialog-item.new-instance)) nil ((text . string) (size fixnum) (command . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(00001865 53 2 114 1 1 32		find-class<-)
(0000186B 10)
(0000186C 1		nil)
(0000186D 10)
(0000186E 9 126 4		'dialog-item.new-instance)
(00001871 26 100 1		dialog-item.new-instance)
(00001874 9 100 1		'dialog-item.new-instance)
(00001877 10)
(00001878 9 125 4		'dialog-item.host-spouse-exists-p)
(0000187B 26 99 1		dialog-item.host-spouse-exists-p)
(0000187E 9 99 1		'dialog-item.host-spouse-exists-p)
(00001881 10)
(00001882 9 124 4		'dialog-item.sync-up)
(00001885 26 98 1		dialog-item.sync-up)
(00001888 9 98 1		'dialog-item.sync-up)
(0000188B 10)
(0000188C 9 123 4		'dialog-item.sync-down)
(0000188F 26 97 1		dialog-item.sync-down)
(00001892 9 97 1		'dialog-item.sync-down)
(00001895 10)
(00001896 9 122 4		'dialog-item._untabstop)
(00001899 26 96 1		dialog-item._untabstop)
(0000189C 9 96 1		'dialog-item._untabstop)
(0000189F 10)
(000018A0 9 95 1		'editable-text)
(000018A3 9 94 1		'(dialog-item))
(000018A6 3 116 1		*deftype-hook*)
(000018A9 52 2 1		)
(000018AC 10)
(000018AD 9 95 1		'editable-text)
(000018B0 9 93 1		'(editable-text-class editable-text :BASE :MIXED-PAGE "The class for Editable Text Controls" ((new-instance . editable-text.new-instance)) nil ((text . string) (size fixnum) (command . T) (prompt . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(000018B3 53 2 114 1 1 32		find-class<-)
(000018B9 10)
(000018BA 1		nil)
(000018BB 10)
(000018BC 9 121 4		'editable-text.new-instance)
(000018BF 26 92 1		editable-text.new-instance)
(000018C2 9 92 1		'editable-text.new-instance)
(000018C5 10)
(000018C6 9 120 4		'editable-text)
(000018C9 26 95 1		editable-text)
(000018CC 9 95 1		'editable-text)
(000018CF 10)
(000018D0 1		nil)
(000018D1 10)
(000018D2 9 91 1		'static-text)
(000018D5 9 94 1		'(dialog-item))
(000018D8 3 116 1		*deftype-hook*)
(000018DB 52 2 1		)
(000018DE 10)
(000018DF 9 91 1		'static-text)
(000018E2 9 90 1		'(static-text-class static-text :BASE :MIXED-PAGE "The class for Static Text Controls" ((new-instance . static-text.new-instance)) nil ((text . string) (size fixnum) (command . T) (adjustment . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(000018E5 53 2 114 1 1 32		find-class<-)
(000018EB 10)
(000018EC 1		nil)
(000018ED 10)
(000018EE 9 119 4		'static-text.new-instance)
(000018F1 26 89 1		static-text.new-instance)
(000018F4 9 89 1		'static-text.new-instance)
(000018F7 10)
(000018F8 9 118 4		'static-text)
(000018FB 26 91 1		static-text)
(000018FE 9 91 1		'static-text)
(00001901 10)
(00001902 1		nil)
(00001903 10)
(00001904 9 88 1		'icon)
(00001907 9 94 1		'(dialog-item))
(0000190A 3 116 1		*deftype-hook*)
(0000190D 52 2 1		)
(00001910 10)
(00001911 9 88 1		'icon)
(00001914 9 87 1		'(icon-class icon :BASE :MIXED-PAGE "The class for Icon Controls" ((new-instance . icon.new-instance)) nil ((text . string) (size fixnum) (command . T) (resource . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(00001917 53 2 114 1 1 32		find-class<-)
(0000191D 10)
(0000191E 1		nil)
(0000191F 10)
(00001920 9 117 4		'icon.new-instance)
(00001923 26 86 1		icon.new-instance)
(00001926 9 86 1		'icon.new-instance)
(00001929 10)
(0000192A 9 116 4		'icon)
(0000192D 26 88 1		icon)
(00001930 9 88 1		'icon)
(00001933 10)
(00001934 1		nil)
(00001935 10)
(00001936 9 85 1		'bitmap-push-button)
(00001939 9 94 1		'(dialog-item))
(0000193C 3 116 1		*deftype-hook*)
(0000193F 52 2 1		)
(00001942 10)
(00001943 9 85 1		'bitmap-push-button)
(00001946 9 84 1		'(bitmap-push-button-class bitmap-push-button :BASE :MIXED-PAGE "The class for Bitmap Push Buttons" ((new-instance . bitmap-push-button.new-instance)) nil ((text . string) (size fixnum) (command . T) (prompt . T) (bitmaps . T) (ttip . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(00001949 53 2 114 1 1 32		find-class<-)
(0000194F 10)
(00001950 1		nil)
(00001951 10)
(00001952 9 115 4		'bitmap-push-button.new-instance)
(00001955 26 83 1		bitmap-push-button.new-instance)
(00001958 9 83 1		'bitmap-push-button.new-instance)
(0000195B 10)
(0000195C 9 114 4		'bitmap-push-button)
(0000195F 26 85 1		bitmap-push-button)
(00001962 9 85 1		'bitmap-push-button)
(00001965 10)
(00001966 1		nil)
(00001967 10)
(00001968 9 113 4		'bmp-push-button)
(0000196B 26 82 1		bmp-push-button)
(0000196E 9 82 1		'bmp-push-button)
(00001971 10)
(00001972 9 112 4		'bitmap-resource-p)
(00001975 26 81 1		bitmap-resource-p)
(00001978 9 81 1		'bitmap-resource-p)
(0000197B 10)
(0000197C 9 111 4		'bitmap-push-button._chk-bitmaps)
(0000197F 26 80 1		bitmap-push-button._chk-bitmaps)
(00001982 9 80 1		'bitmap-push-button._chk-bitmaps)
(00001985 10)
(00001986 9 79 1		'push-button)
(00001989 9 94 1		'(dialog-item))
(0000198C 3 116 1		*deftype-hook*)
(0000198F 52 2 1		)
(00001992 10)
(00001993 9 79 1		'push-button)
(00001996 9 78 1		'(push-button-class push-button :BASE :MIXED-PAGE "The class for Push Buttons" ((new-instance . push-button.new-instance)) nil ((text . string) (size fixnum) (command . T) (prompt . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(00001999 53 2 114 1 1 32		find-class<-)
(0000199F 10)
(000019A0 1		nil)
(000019A1 10)
(000019A2 9 110 4		'push-button.new-instance)
(000019A5 26 77 1		push-button.new-instance)
(000019A8 9 77 1		'push-button.new-instance)
(000019AB 10)
(000019AC 9 109 4		'push-button)
(000019AF 26 79 1		push-button)
(000019B2 9 79 1		'push-button)
(000019B5 10)
(000019B6 1		nil)
(000019B7 10)
(000019B8 9 76 1		'radio-button)
(000019BB 9 94 1		'(dialog-item))
(000019BE 3 116 1		*deftype-hook*)
(000019C1 52 2 1		)
(000019C4 10)
(000019C5 9 76 1		'radio-button)
(000019C8 9 75 1		'(radio-button-class radio-button :BASE :MIXED-PAGE "The class for Radio Buttons" ((new-instance . radio-button.new-instance)) nil ((text . string) (size fixnum) (command . T) (prompt . T) (selected . T) (left-text . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(000019CB 53 2 114 1 1 32		find-class<-)
(000019D1 10)
(000019D2 1		nil)
(000019D3 10)
(000019D4 9 108 4		'radio-button.new-instance)
(000019D7 26 74 1		radio-button.new-instance)
(000019DA 9 74 1		'radio-button.new-instance)
(000019DD 10)
(000019DE 9 107 4		'radio-button)
(000019E1 26 76 1		radio-button)
(000019E4 9 76 1		'radio-button)
(000019E7 10)
(000019E8 1		nil)
(000019E9 10)
(000019EA 9 73 1		'check-box)
(000019ED 9 94 1		'(dialog-item))
(000019F0 3 116 1		*deftype-hook*)
(000019F3 52 2 1		)
(000019F6 10)
(000019F7 9 73 1		'check-box)
(000019FA 9 72 1		'(check-box-class check-box :BASE :MIXED-PAGE "The class for Check Boxen" ((new-instance . check-box.new-instance)) nil ((text . string) (size fixnum) (command . T) (prompt . T) (checked . T) (left-text . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(000019FD 53 2 114 1 1 32		find-class<-)
(00001A03 10)
(00001A04 1		nil)
(00001A05 10)
(00001A06 9 106 4		'check-box.new-instance)
(00001A09 26 71 1		check-box.new-instance)
(00001A0C 9 71 1		'check-box.new-instance)
(00001A0F 10)
(00001A10 9 105 4		'check-box)
(00001A13 26 73 1		check-box)
(00001A16 9 73 1		'check-box)
(00001A19 10)
(00001A1A 1		nil)
(00001A1B 10)
(00001A1C 9 70 1		'group-box)
(00001A1F 9 94 1		'(dialog-item))
(00001A22 3 116 1		*deftype-hook*)
(00001A25 52 2 1		)
(00001A28 10)
(00001A29 9 70 1		'group-box)
(00001A2C 9 69 1		'(group-box-class group-box :BASE :MIXED-PAGE "The class for Group Boxen" ((new-instance . group-box.new-instance)) nil ((text . string) (size fixnum) (command . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(00001A2F 53 2 114 1 1 32		find-class<-)
(00001A35 10)
(00001A36 1		nil)
(00001A37 10)
(00001A38 9 104 4		'group-box.new-instance)
(00001A3B 26 68 1		group-box.new-instance)
(00001A3E 9 68 1		'group-box.new-instance)
(00001A41 10)
(00001A42 9 103 4		'group-box)
(00001A45 26 70 1		group-box)
(00001A48 9 70 1		'group-box)
(00001A4B 10)
(00001A4C 1		nil)
(00001A4D 10)
(00001A4E 9 67 1		'list-box)
(00001A51 9 94 1		'(dialog-item))
(00001A54 3 116 1		*deftype-hook*)
(00001A57 52 2 1		)
(00001A5A 10)
(00001A5B 9 67 1		'list-box)
(00001A5E 9 66 1		'(list-box-class list-box :BASE :MIXED-PAGE "The class for List Boxen" ((new-instance . list-box.new-instance)) nil ((text . string) (size fixnum) (command . T) (prompt . T) (items . T) (multiple-selection . T) (lexsort . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (list-box-selection . list-box.list-box-selection) (list-box-erase-selection . list-box.list-box-erase-selection) (list-box-set-selection . list-box.list-box-set-selection) (list-box-add-items . list-box.list-box-add-items) (list-box-items . list-box.list-box-items) (list-box-items<- . list-box.list-box-items<-) (list-box-contents . list-box.list-box-contents) (list-box-contents<- . list-box.list-box-contents<-) (list-box-sort . list-box.list-box-sort) (list-box-empty . list-box.list-box-empty) (LIST-BOX-MOVEABLE-P . list-box.list-box-moveable-p) (LIST-BOX-ITEMS-UP . list-box.list-box-items-up) (LIST-BOX-ITEMS-DOWN . list-box.list-box-items-down) (LIST-BOX-ITEMS-TOP . list-box.list-box-items-top) (LIST-BOX-ITEMS-BOTTOM . list-box.list-box-items-bottom))))
(00001A61 53 2 114 1 1 32		find-class<-)
(00001A67 10)
(00001A68 1		nil)
(00001A69 10)
(00001A6A 9 102 4		'list-box.new-instance)
(00001A6D 26 65 1		list-box.new-instance)
(00001A70 9 65 1		'list-box.new-instance)
(00001A73 10)
(00001A74 9 101 4		'list-box)
(00001A77 26 67 1		list-box)
(00001A7A 9 67 1		'list-box)
(00001A7D 10)
(00001A7E 1		nil)
(00001A7F 10)
(00001A80 9 100 4		'list-box.selection-index)
(00001A83 26 64 1		list-box.selection-index)
(00001A86 9 64 1		'list-box.selection-index)
(00001A89 10)
(00001A8A 9 63 1		'drop-down-list-box)
(00001A8D 9 94 1		'(dialog-item))
(00001A90 3 116 1		*deftype-hook*)
(00001A93 52 2 1		)
(00001A96 10)
(00001A97 9 63 1		'drop-down-list-box)
(00001A9A 9 62 1		'(drop-down-list-box-class drop-down-list-box :BASE :MIXED-PAGE "The class for Drop-Down List Boxen" ((new-instance . drop-down-list-box.new-instance)) nil ((text . string) (size fixnum) (command . T) (prompt . T) (items . T) (lexsort . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(00001A9D 53 2 114 1 1 32		find-class<-)
(00001AA3 10)
(00001AA4 1		nil)
(00001AA5 10)
(00001AA6 9 99 4		'drop-down-list-box.new-instance)
(00001AA9 26 61 1		drop-down-list-box.new-instance)
(00001AAC 9 61 1		'drop-down-list-box.new-instance)
(00001AAF 10)
(00001AB0 9 98 4		'drop-down-list-box)
(00001AB3 26 63 1		drop-down-list-box)
(00001AB6 9 63 1		'drop-down-list-box)
(00001AB9 10)
(00001ABA 1		nil)
(00001ABB 10)
(00001ABC 9 60 1		'color-selector)
(00001ABF 9 94 1		'(dialog-item))
(00001AC2 3 116 1		*deftype-hook*)
(00001AC5 52 2 1		)
(00001AC8 10)
(00001AC9 9 60 1		'color-selector)
(00001ACC 9 59 1		'(color-selector-class color-selector :BASE :MIXED-PAGE "The control for color selection" ((new-instance . color-selector.new-instance)) nil ((text . string) (size fixnum) (command . T) (prompt . T) (selection . T) (rgb . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(00001ACF 53 2 114 1 1 32		find-class<-)
(00001AD5 10)
(00001AD6 1		nil)
(00001AD7 10)
(00001AD8 9 97 4		'color-selector.new-instance)
(00001ADB 26 58 1		color-selector.new-instance)
(00001ADE 9 58 1		'color-selector.new-instance)
(00001AE1 10)
(00001AE2 9 96 4		'color-selector)
(00001AE5 26 60 1		color-selector)
(00001AE8 9 60 1		'color-selector)
(00001AEB 10)
(00001AEC 1		nil)
(00001AED 10)
(00001AEE 9 95 4		'accessed-verify)
(00001AF1 26 57 1		accessed-verify)
(00001AF4 9 57 1		'accessed-verify)
(00001AF7 10)
(00001AF8 1		nil)
(00001AF9 10)
(00001AFA 9 94 4		'dialog.accessed-verify)
(00001AFD 26 56 1		dialog.accessed-verify)
(00001B00 9 56 1		'dialog.accessed-verify)
(00001B03 10)
(00001B04 9 55 1		'bmp-button)
(00001B07 9 94 1		'(dialog-item))
(00001B0A 3 116 1		*deftype-hook*)
(00001B0D 52 2 1		)
(00001B10 10)
(00001B11 9 55 1		'bmp-button)
(00001B14 9 54 1		'(bmp-button-class bmp-button :BASE :MIXED-PAGE "The class for Bmp Push Buttons" ((new-instance . bmp-button.new-instance)) nil ((text . string) (size fixnum) (command . T) (prompt . T) (bitmap . T) (ttip . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string))))
(00001B17 53 2 114 1 1 32		find-class<-)
(00001B1D 10)
(00001B1E 1		nil)
(00001B1F 10)
(00001B20 9 93 4		'bmp-button.new-instance)
(00001B23 26 53 1		bmp-button.new-instance)
(00001B26 9 53 1		'bmp-button.new-instance)
(00001B29 10)
(00001B2A 9 92 4		'bmp-button)
(00001B2D 26 55 1		bmp-button)
(00001B30 9 55 1		'bmp-button)
(00001B33 10)
(00001B34 1		nil)
(00001B35 10)
(00001B36 9 91 4		'bmp-push-button1)
(00001B39 26 52 1		bmp-push-button1)
(00001B3C 9 52 1		'bmp-push-button1)
(00001B3F 10)
(00001B40 9 90 4		'dialog-update-from-res)
(00001B43 26 51 1		dialog-update-from-res)
(00001B46 9 51 1		'dialog-update-from-res)
(00001B49 28		[ret])
(00001B4A 20 0 0 0 0)
(00001B4F 1		nil)
(00001B50 10)
(00001B51 9 136 1		'dialog)
(00001B54 81 1 115 3 1 0		require)
(00001B5A 10)
(00001B5B 9 89 4		'_frame-margins)
(00001B5E 26 50 1		_frame-margins)
(00001B61 9 50 1		'_frame-margins)
(00001B64 10)
(00001B65 9 88 4		'_screen-margins)
(00001B68 26 49 1		_screen-margins)
(00001B6B 9 49 1		'_screen-margins)
(00001B6E 10)
(00001B6F 9 87 4		'_small-inc)
(00001B72 26 48 1		_small-inc)
(00001B75 9 48 1		'_small-inc)
(00001B78 10)
(00001B79 9 86 4		'_default-inc)
(00001B7C 26 47 1		_default-inc)
(00001B7F 9 47 1		'_default-inc)
(00001B82 10)
(00001B83 9 85 4		'dcascade)
(00001B86 26 46 1		dcascade)
(00001B89 9 46 1		'dcascade)
(00001B8C 10)
(00001B8D 9 84 4		'dcascade.frame-margins)
(00001B90 26 45 1		dcascade.frame-margins)
(00001B93 9 45 1		'dcascade.frame-margins)
(00001B96 10)
(00001B97 9 83 4		'dcascade.hor-ratio)
(00001B9A 26 44 1		dcascade.hor-ratio)
(00001B9D 9 44 1		'dcascade.hor-ratio)
(00001BA0 10)
(00001BA1 9 82 4		'dcascade.ver-ratio)
(00001BA4 26 43 1		dcascade.ver-ratio)
(00001BA7 9 43 1		'dcascade.ver-ratio)
(00001BAA 10)
(00001BAB 9 81 4		'dcascade.screen-margins)
(00001BAE 26 42 1		dcascade.screen-margins)
(00001BB1 9 42 1		'dcascade.screen-margins)
(00001BB4 10)
(00001BB5 9 80 4		'dcascade.inc)
(00001BB8 26 41 1		dcascade.inc)
(00001BBB 9 41 1		'dcascade.inc)
(00001BBE 10)
(00001BBF 9 79 4		'dcascade.limit)
(00001BC2 26 40 1		dcascade.limit)
(00001BC5 9 40 1		'dcascade.limit)
(00001BC8 10)
(00001BC9 9 78 4		'dcascade.check-dialog-size-p)
(00001BCC 26 39 1		dcascade.check-dialog-size-p)
(00001BCF 9 39 1		'dcascade.check-dialog-size-p)
(00001BD2 10)
(00001BD3 1		nil)
(00001BD4 10)
(00001BD5 9 77 4		'dcascade.init-apex)
(00001BD8 26 38 1		dcascade.init-apex)
(00001BDB 9 38 1		'dcascade.init-apex)
(00001BDE 10)
(00001BDF 9 76 4		'dcascade.init-apex<-)
(00001BE2 26 37 1		dcascade.init-apex<-)
(00001BE5 9 37 1		'dcascade.init-apex<-)
(00001BE8 10)
(00001BE9 1		nil)
(00001BEA 10)
(00001BEB 1		nil)
(00001BEC 10)
(00001BED 9 75 4		'dcascade.winframe)
(00001BF0 26 36 1		dcascade.winframe)
(00001BF3 9 36 1		'dcascade.winframe)
(00001BF6 10)
(00001BF7 9 74 4		'dcascade.winframe<-)
(00001BFA 26 35 1		dcascade.winframe<-)
(00001BFD 9 35 1		'dcascade.winframe<-)
(00001C00 10)
(00001C01 1		nil)
(00001C02 10)
(00001C03 1		nil)
(00001C04 10)
(00001C05 9 73 4		'dcascade.apex)
(00001C08 26 34 1		dcascade.apex)
(00001C0B 9 34 1		'dcascade.apex)
(00001C0E 10)
(00001C0F 9 72 4		'dcascade.apex<-)
(00001C12 26 33 1		dcascade.apex<-)
(00001C15 9 33 1		'dcascade.apex<-)
(00001C18 10)
(00001C19 1		nil)
(00001C1A 10)
(00001C1B 9 71 4		'dcascade-apex)
(00001C1E 26 32 1		dcascade-apex)
(00001C21 9 32 1		'dcascade-apex)
(00001C24 10)
(00001C25 9 70 4		'dcascade.init)
(00001C28 26 31 1		dcascade.init)
(00001C2B 9 31 1		'dcascade.init)
(00001C2E 10)
(00001C2F 9 69 4		'dcascade.next-apex)
(00001C32 26 30 1		dcascade.next-apex)
(00001C35 9 30 1		'dcascade.next-apex)
(00001C38 10)
(00001C39 9 68 4		'dcascade.next)
(00001C3C 26 29 1		dcascade.next)
(00001C3F 9 29 1		'dcascade.next)
(00001C42 10)
(00001C43 9 67 4		'dialog.apex-by-cascade)
(00001C46 26 28 1		dialog.apex-by-cascade)
(00001C49 9 28 1		'dialog.apex-by-cascade)
(00001C4C 28		[ret])
(00001C4D 20 0 0 0 0)
(00001C52 1		nil)
(00001C53 10)
(00001C54 1		nil)
(00001C55 10)
(00001C56 9 66 4		'list-true-dialogs-with-host-spouse)
(00001C59 26 27 1		list-true-dialogs-with-host-spouse)
(00001C5C 9 27 1		'list-true-dialogs-with-host-spouse)
(00001C5F 10)
(00001C60 9 65 4		'close-modal-dialogs)
(00001C63 26 26 1		close-modal-dialogs)
(00001C66 9 26 1		'close-modal-dialogs)
(00001C69 10)
(00001C6A 9 64 4		'_kill-dialogs)
(00001C6D 26 25 1		_kill-dialogs)
(00001C70 9 25 1		'_kill-dialogs)
(00001C73 10)
(00001C74 1		nil)
(00001C75 10)
(00001C76 1		nil)
(00001C77 10)
(00001C78 1		nil)
(00001C79 10)
(00001C7A 9 24 1		':HOR-RATIO)
(00001C7D 9 23 1		0.25)
(00001C80 9 22 1		':VER-RATIO)
(00001C83 9 23 1		0.25)
(00001C86 53 4 46 1 1 32		dcascade)
(00001C8C 26 21 1		*modals-cascade*)
(00001C8F 9 21 1		'*modals-cascade*)
(00001C92 10)
(00001C93 53 0 46 1 1 32		dcascade)
(00001C99 26 20 1		*large-dialogs-cascade*)
(00001C9C 9 20 1		'*large-dialogs-cascade*)
(00001C9F 10)
(00001CA0 12 63 4		'modal-dialog!!)
(00001CA3 26 19 1		modal-dialog!!)
(00001CA6 9 19 1		'modal-dialog!!)
(00001CA9 10)
(00001CAA 1		nil)
(00001CAB 10)
(00001CAC 12 62 4		'modal-dialog-sheet!!)
(00001CAF 26 18 1		modal-dialog-sheet!!)
(00001CB2 9 18 1		'modal-dialog-sheet!!)
(00001CB5 28		[ret])
(00001CB6 20 0 0 0 0)
(00001CBB 1		nil)
(00001CBC 10)
(00001CBD 1		nil)
(00001CBE 10)
(00001CBF 9 61 4		'di-fmt-dialog)
(00001CC2 26 17 1		di-fmt-dialog)
(00001CC5 9 17 1		'di-fmt-dialog)
(00001CC8 10)
(00001CC9 9 60 4		'di-fmt-pos-alist)
(00001CCC 26 16 1		di-fmt-pos-alist)
(00001CCF 9 16 1		'di-fmt-pos-alist)
(00001CD2 10)
(00001CD3 1		nil)
(00001CD4 10)
(00001CD5 1		nil)
(00001CD6 10)
(00001CD7 1		nil)
(00001CD8 10)
(00001CD9 1		nil)
(00001CDA 10)
(00001CDB 1		nil)
(00001CDC 10)
(00001CDD 9 59 4		'center-dialog)
(00001CE0 26 15 1		center-dialog)
(00001CE3 9 15 1		'center-dialog)
(00001CE6 10)
(00001CE7 9 58 4		'_dialog-x2d)
(00001CEA 26 14 1		_dialog-x2d)
(00001CED 9 14 1		'_dialog-x2d)
(00001CF0 28		[ret])
(00001CF1 20 0 0 0 0)
(00001CF6 1		nil)
(00001CF7 10)
(00001CF8 50 0		0)
(00001CFA 26 13 1		MB_OK)
(00001CFD 9 13 1		'MB_OK)
(00001D00 10)
(00001D01 50 1		1)
(00001D03 26 12 1		MB_OKCANCEL)
(00001D06 9 12 1		'MB_OKCANCEL)
(00001D09 10)
(00001D0A 50 2		2)
(00001D0C 26 11 1		MB_ABORTRETRYIGNORE)
(00001D0F 9 11 1		'MB_ABORTRETRYIGNORE)
(00001D12 10)
(00001D13 50 3		3)
(00001D15 26 10 1		MB_YESNOCANCEL)
(00001D18 9 10 1		'MB_YESNOCANCEL)
(00001D1B 10)
(00001D1C 50 4		4)
(00001D1E 26 9 1		MB_YESNO)
(00001D21 9 9 1		'MB_YESNO)
(00001D24 10)
(00001D25 50 5		5)
(00001D27 26 8 1		MB_RETRYCANCEL)
(00001D2A 9 8 1		'MB_RETRYCANCEL)
(00001D2D 10)
(00001D2E 50 16		16)
(00001D30 26 7 1		MB_ICONHAND)
(00001D33 9 7 1		'MB_ICONHAND)
(00001D36 10)
(00001D37 50 32		32)
(00001D39 26 6 1		MB_ICONQUESTION)
(00001D3C 9 6 1		'MB_ICONQUESTION)
(00001D3F 10)
(00001D40 50 48		48)
(00001D42 26 5 1		MB_ICONEXCLAMATION)
(00001D45 9 5 1		'MB_ICONEXCLAMATION)
(00001D48 10)
(00001D49 50 64		64)
(00001D4B 26 4 1		MB_ICONASTERISK)
(00001D4E 9 4 1		'MB_ICONASTERISK)
(00001D51 10)
(00001D52 50 64		64)
(00001D54 26 3 1		MB_ICONINFORMATION)
(00001D57 9 3 1		'MB_ICONINFORMATION)
(00001D5A 10)
(00001D5B 50 16		16)
(00001D5D 26 2 1		MB_ICONSTOP)
(00001D60 9 2 1		'MB_ICONSTOP)
(00001D63 10)
(00001D64 50 0		0)
(00001D66 26 1 1		MB_DEFBUTTON1)
(00001D69 9 1 1		'MB_DEFBUTTON1)
(00001D6C 10)
(00001D6D 51 0 1 0 0		256)
(00001D72 26 0 1		MB_DEFBUTTON2)
(00001D75 9 0 1		'MB_DEFBUTTON2)
(00001D78 10)
(00001D79 51 0 2 0 0		512)
(00001D7E 26 255 0		MB_DEFBUTTON3)
(00001D81 9 255 0		'MB_DEFBUTTON3)
(00001D84 10)
(00001D85 51 0 16 0 0		4096)
(00001D8A 26 254 0		MB_SYSTEMMODAL)
(00001D8D 9 254 0		'MB_SYSTEMMODAL)
(00001D90 10)
(00001D91 51 0 128 0 0		32768)
(00001D96 26 253 0		MB_NOFOCUS)
(00001D99 9 253 0		'MB_NOFOCUS)
(00001D9C 10)
(00001D9D 9 252 0		'(nil :OK :CANCEL :ABORT :RETRY :IGNORE :YES :NO))
(00001DA0 26 251 0		*mswin-db-names*)
(00001DA3 9 251 0		'*mswin-db-names*)
(00001DA6 10)
(00001DA7 50 16		16)
(00001DA9 26 250 0		*stop-beep*)
(00001DAC 9 250 0		'*stop-beep*)
(00001DAF 10)
(00001DB0 50 32		32)
(00001DB2 26 249 0		*question-beep*)
(00001DB5 9 249 0		'*question-beep*)
(00001DB8 10)
(00001DB9 50 48		48)
(00001DBB 26 248 0		*exclamation-beep*)
(00001DBE 9 248 0		'*exclamation-beep*)
(00001DC1 10)
(00001DC2 50 64		64)
(00001DC4 26 247 0		*info-beep*)
(00001DC7 9 247 0		'*info-beep*)
(00001DCA 10)
(00001DCB 50 0		0)
(00001DCD 26 246 0		*default-beep*)
(00001DD0 9 246 0		'*default-beep*)
(00001DD3 10)
(00001DD4 50 255		-1)
(00001DD6 26 245 0		*standard-beep*)
(00001DD9 9 245 0		'*standard-beep*)
(00001DDC 10)
(00001DDD 1		nil)
(00001DDE 26 244 0		*no-beep*)
(00001DE1 9 244 0		'*no-beep*)
(00001DE4 10)
(00001DE5 1		nil)
(00001DE6 51 4 127 0 0		32516)
(00001DEB 81 2 243 0 1 0		icon-resource)
(00001DF1 53 1 88 1 1 32		icon)
(00001DF7 26 242 0		*info-icon*)
(00001DFA 9 242 0		'*info-icon*)
(00001DFD 10)
(00001DFE 1		nil)
(00001DFF 51 3 127 0 0		32515)
(00001E04 81 2 243 0 1 0		icon-resource)
(00001E0A 53 1 88 1 1 32		icon)
(00001E10 26 241 0		*exclamation-icon*)
(00001E13 9 241 0		'*exclamation-icon*)
(00001E16 10)
(00001E17 1		nil)
(00001E18 51 2 127 0 0		32514)
(00001E1D 81 2 243 0 1 0		icon-resource)
(00001E23 53 1 88 1 1 32		icon)
(00001E29 26 240 0		*question-icon*)
(00001E2C 9 240 0		'*question-icon*)
(00001E2F 10)
(00001E30 1		nil)
(00001E31 51 1 127 0 0		32513)
(00001E36 81 2 243 0 1 0		icon-resource)
(00001E3C 53 1 88 1 1 32		icon)
(00001E42 26 239 0		*stop-icon*)
(00001E45 9 239 0		'*stop-icon*)
(00001E48 10)
(00001E49 3 240 0		*question-icon*)
(00001E4C 51 32 0 32 0		2097184)
(00001E51 9 238 0		'size)
(00001E54 81 3 237 0 1 0		slot-value<-)
(00001E5A 10)
(00001E5B 3 242 0		*info-icon*)
(00001E5E 51 32 0 32 0		2097184)
(00001E63 9 238 0		'size)
(00001E66 81 3 237 0 1 0		slot-value<-)
(00001E6C 10)
(00001E6D 9 236 0		'alert-info)
(00001E70 9 117 1		'(instance))
(00001E73 3 116 1		*deftype-hook*)
(00001E76 52 2 1		)
(00001E79 10)
(00001E7A 9 236 0		'alert-info)
(00001E7D 9 235 0		'(standard-class alert-info :CLOSED :MIXED-PAGE "The class for MessageBox arguments" ((new-instance . alert-info.new-instance)) nil ((caption . string) (flags fixnum) (beep . T)) ((alert alert-info.alert))))
(00001E80 53 2 114 1 1 32		find-class<-)
(00001E86 10)
(00001E87 1		nil)
(00001E88 10)
(00001E89 9 57 4		'alert-info.new-instance)
(00001E8C 26 234 0		alert-info.new-instance)
(00001E8F 9 234 0		'alert-info.new-instance)
(00001E92 10)
(00001E93 9 56 4		'alert-info)
(00001E96 26 236 0		alert-info)
(00001E99 9 236 0		'alert-info)
(00001E9C 10)
(00001E9D 1		nil)
(00001E9E 10)
(00001E9F 9 55 4		'alert)
(00001EA2 26 233 0		alert)
(00001EA5 9 233 0		'alert)
(00001EA8 10)
(00001EA9 51 250 0 0 0		250)
(00001EAE 26 232 0		*alert-max-text-length*)
(00001EB1 9 232 0		'*alert-max-text-length*)
(00001EB4 10)
(00001EB5 9 54 4		'alert-info.alert)
(00001EB8 26 231 0		alert-info.alert)
(00001EBB 9 231 0		'alert-info.alert)
(00001EBE 10)
(00001EBF 9 187 1		"VLMSG.DLL")
(00001EC2 51 70 85 0 0		21830)
(00001EC7 81 2 186 1 1 0		string-resource)
(00001ECD 3 2 1		MB_ICONSTOP)
(00001ED0 50 16		16)
(00001ED2 53 3 236 0 1 32		alert-info)
(00001ED8 26 230 0		*error-alert*)
(00001EDB 9 230 0		'*error-alert*)
(00001EDE 10)
(00001EDF 3 230 0		*error-alert*)
(00001EE2 26 229 0		*error-alert-i*)
(00001EE5 9 229 0		'*error-alert-i*)
(00001EE8 10)
(00001EE9 9 187 1		"VLMSG.DLL")
(00001EEC 51 176 94 0 0		24240)
(00001EF1 81 2 186 1 1 0		string-resource)
(00001EF7 3 2 1		MB_ICONSTOP)
(00001EFA 50 16		16)
(00001EFC 53 3 236 0 1 32		alert-info)
(00001F02 26 228 0		*stop-alert*)
(00001F05 9 228 0		'*stop-alert*)
(00001F08 10)
(00001F09 3 228 0		*stop-alert*)
(00001F0C 26 227 0		*stop-alert-i*)
(00001F0F 9 227 0		'*stop-alert-i*)
(00001F12 10)
(00001F13 9 187 1		"VLMSG.DLL")
(00001F16 51 186 94 0 0		24250)
(00001F1B 81 2 186 1 1 0		string-resource)
(00001F21 50 64		64)
(00001F23 50 64		64)
(00001F25 53 3 236 0 1 32		alert-info)
(00001F2B 26 226 0		*warning-alert*)
(00001F2E 9 226 0		'*warning-alert*)
(00001F31 10)
(00001F32 3 226 0		*warning-alert*)
(00001F35 26 225 0		*warning-alert-i*)
(00001F38 9 225 0		'*warning-alert-i*)
(00001F3B 10)
(00001F3C 9 187 1		"VLMSG.DLL")
(00001F3F 51 196 94 0 0		24260)
(00001F44 81 2 186 1 1 0		string-resource)
(00001F4A 50 64		64)
(00001F4C 50 64		64)
(00001F4E 53 3 236 0 1 32		alert-info)
(00001F54 26 224 0		*info-alert*)
(00001F57 9 224 0		'*info-alert*)
(00001F5A 10)
(00001F5B 3 224 0		*info-alert*)
(00001F5E 26 223 0		*info-alert-i*)
(00001F61 9 223 0		'*info-alert-i*)
(00001F64 10)
(00001F65 9 187 1		"VLMSG.DLL")
(00001F68 51 206 94 0 0		24270)
(00001F6D 81 2 186 1 1 0		string-resource)
(00001F73 50 48		48)
(00001F75 50 1		1)
(00001F77 81 2 194 1 1 0		logior)
(00001F7D 50 32		32)
(00001F7F 53 3 236 0 1 32		alert-info)
(00001F85 26 222 0		*confirm-alert*)
(00001F88 9 222 0		'*confirm-alert*)
(00001F8B 10)
(00001F8C 3 222 0		*confirm-alert*)
(00001F8F 26 221 0		*confirm-alert-i*)
(00001F92 9 221 0		'*confirm-alert-i*)
(00001F95 10)
(00001F96 9 187 1		"VLMSG.DLL")
(00001F99 51 74 31 0 0		8010)
(00001F9E 81 2 186 1 1 0		string-resource)
(00001FA4 50 32		32)
(00001FA6 50 4		4)
(00001FA8 81 2 194 1 1 0		logior)
(00001FAE 50 32		32)
(00001FB0 53 3 236 0 1 32		alert-info)
(00001FB6 26 220 0		*question-alert*)
(00001FB9 9 220 0		'*question-alert*)
(00001FBC 10)
(00001FBD 3 220 0		*question-alert*)
(00001FC0 26 219 0		*question-alert-i*)
(00001FC3 9 219 0		'*question-alert-i*)
(00001FC6 10)
(00001FC7 9 187 1		"VLMSG.DLL")
(00001FCA 51 74 31 0 0		8010)
(00001FCF 81 2 186 1 1 0		string-resource)
(00001FD5 50 32		32)
(00001FD7 50 3		3)
(00001FD9 81 2 194 1 1 0		logior)
(00001FDF 50 32		32)
(00001FE1 53 3 236 0 1 32		alert-info)
(00001FE7 26 218 0		*yes-no-cancel-alert*)
(00001FEA 9 218 0		'*yes-no-cancel-alert*)
(00001FED 10)
(00001FEE 3 218 0		*yes-no-cancel-alert*)
(00001FF1 26 217 0		*yes-no-cancel-alert-i*)
(00001FF4 9 217 0		'*yes-no-cancel-alert-i*)
(00001FF7 10)
(00001FF8 9 187 1		"VLMSG.DLL")
(00001FFB 51 216 94 0 0		24280)
(00002000 81 2 186 1 1 0		string-resource)
(00002006 50 48		48)
(00002008 50 2		2)
(0000200A 81 2 194 1 1 0		logior)
(00002010 50 48		48)
(00002012 53 3 236 0 1 32		alert-info)
(00002018 26 216 0		*problem-alert*)
(0000201B 9 216 0		'*problem-alert*)
(0000201E 10)
(0000201F 3 216 0		*problem-alert*)
(00002022 26 215 0		*problem-alert-i*)
(00002025 9 215 0		'*problem-alert-i*)
(00002028 10)
(00002029 9 53 4		'yes-or-no-p)
(0000202C 26 214 0		yes-or-no-p)
(0000202F 9 214 0		'yes-or-no-p)
(00002032 28		[ret])
(00002033 20 0 0 0 0)
(00002038 1		nil)
(00002039 10)
(0000203A 9 136 1		'dialog)
(0000203D 81 1 115 3 1 0		require)
(00002043 10)
(00002044 9 213 0		'alert-dialog)
(00002047 9 212 0		'(dialog))
(0000204A 3 116 1		*deftype-hook*)
(0000204D 52 2 1		)
(00002050 10)
(00002051 9 213 0		'alert-dialog)
(00002054 9 211 0		'(dialog-class alert-dialog :CLOSED :MIXED-PAGE "The class for Alert Boxen" ((new-instance . alert-dialog.new-instance)) nil ((caption . string) (apex . T) (size fixnum) (font . string) (pitch fixnum) (items . T) (parent . T) (default-push-button . T) (close-box-command . T) (states . T) (l-context . T) (ipict . T) (buttons . T) (stext . T) (beep fixnum)) ((create-host-spouse dialog.create-host-spouse) (update-host-spouse dialog.update-host-spouse) (destroy-host-spouse dialog.destroy-host-spouse) (host-spouse-exists-p dialog.host-spouse-exists-p) (print-object . dialog.print-object) (accessed-verify . dialog.accessed-verify) (sync-up dialog.sync-up) (sync-down dialog.sync-down) (!dialog-size-hook . dialog.!dialog-size-hook) (bcolor . dialog.bcolor) (bcolor<- . dialog.bcolor<-) (!dialog-escape . dialog.!dialog-escape) (inspector-binary-slot-descriptions ("(host-spouse-exists-p) " nil host-spouse-exists-p) ("(_msw-style) " nil dialog._msw-style) ("(_border-style) " (fixnum) dialog._border-style dialog._border-style<-) ("(bcolor) " T dialog.bcolor dialog.bcolor<-)) (inspector-slot-printers apex ipoint-prin1-to-string size ipoint-prin1-to-string) (alert alert-dialog.alert))))
(00002057 53 2 114 1 1 32		find-class<-)
(0000205D 10)
(0000205E 1		nil)
(0000205F 10)
(00002060 9 52 4		'alert-dialog.new-instance)
(00002063 26 210 0		alert-dialog.new-instance)
(00002066 9 210 0		'alert-dialog.new-instance)
(00002069 10)
(0000206A 9 51 4		'alert-dialog)
(0000206D 26 213 0		alert-dialog)
(00002070 9 213 0		'alert-dialog)
(00002073 10)
(00002074 1		nil)
(00002075 10)
(00002076 9 50 4		'alert-dialog.adjust-alert)
(00002079 26 209 0		alert-dialog.adjust-alert)
(0000207C 9 209 0		'alert-dialog.adjust-alert)
(0000207F 10)
(00002080 1		nil)
(00002081 10)
(00002082 9 49 4		'alert-dialog.alert)
(00002085 26 208 0		alert-dialog.alert)
(00002088 9 208 0		'alert-dialog.alert)
(0000208B 10)
(0000208C 51 40 0 18 0		1179688)
(00002091 9 187 1		"VLMSG.DLL")
(00002094 51 84 61 0 0		15700)
(00002099 81 2 186 1 1 0		string-resource)
(0000209F 15 0 0		JMP 000020A2)
(000020A2 9 48 4		'nil)
(000020A5 9 187 1		"VLMSG.DLL")
(000020A8 51 36 94 0 0		24100)
(000020AD 81 2 186 1 1 0		string-resource)
(000020B3 53 4 79 1 1 32		push-button)
(000020B9 26 207 0		*ok-alert-button*)
(000020BC 9 207 0		'*ok-alert-button*)
(000020BF 10)
(000020C0 51 40 0 18 0		1179688)
(000020C5 9 187 1		"VLMSG.DLL")
(000020C8 51 228 82 0 0		21220)
(000020CD 81 2 186 1 1 0		string-resource)
(000020D3 15 0 0		JMP 000020D6)
(000020D6 9 47 4		'nil)
(000020D9 9 187 1		"VLMSG.DLL")
(000020DC 51 46 94 0 0		24110)
(000020E1 81 2 186 1 1 0		string-resource)
(000020E7 53 4 79 1 1 32		push-button)
(000020ED 26 206 0		*cancel-alert-button*)
(000020F0 9 206 0		'*cancel-alert-button*)
(000020F3 10)
(000020F4 51 40 0 18 0		1179688)
(000020F9 9 187 1		"VLMSG.DLL")
(000020FC 51 56 94 0 0		24120)
(00002101 81 2 186 1 1 0		string-resource)
(00002107 15 0 0		JMP 0000210A)
(0000210A 9 46 4		'nil)
(0000210D 9 187 1		"VLMSG.DLL")
(00002110 51 66 94 0 0		24130)
(00002115 81 2 186 1 1 0		string-resource)
(0000211B 53 4 79 1 1 32		push-button)
(00002121 26 205 0		*yes-alert-button*)
(00002124 9 205 0		'*yes-alert-button*)
(00002127 10)
(00002128 51 40 0 18 0		1179688)
(0000212D 9 187 1		"VLMSG.DLL")
(00002130 51 76 94 0 0		24140)
(00002135 81 2 186 1 1 0		string-resource)
(0000213B 15 0 0		JMP 0000213E)
(0000213E 9 45 4		'nil)
(00002141 9 187 1		"VLMSG.DLL")
(00002144 51 86 94 0 0		24150)
(00002149 81 2 186 1 1 0		string-resource)
(0000214F 53 4 79 1 1 32		push-button)
(00002155 26 204 0		*no-alert-button*)
(00002158 9 204 0		'*no-alert-button*)
(0000215B 10)
(0000215C 51 40 0 18 0		1179688)
(00002161 9 187 1		"VLMSG.DLL")
(00002164 51 96 94 0 0		24160)
(00002169 81 2 186 1 1 0		string-resource)
(0000216F 15 0 0		JMP 00002172)
(00002172 9 44 4		'nil)
(00002175 9 187 1		"VLMSG.DLL")
(00002178 51 106 94 0 0		24170)
(0000217D 81 2 186 1 1 0		string-resource)
(00002183 53 4 79 1 1 32		push-button)
(00002189 26 203 0		*retry-alert-button*)
(0000218C 9 203 0		'*retry-alert-button*)
(0000218F 10)
(00002190 9 187 1		"VLMSG.DLL")
(00002193 51 116 94 0 0		24180)
(00002198 81 2 186 1 1 0		string-resource)
(0000219E 3 240 0		*question-icon*)
(000021A1 50 32		32)
(000021A3 51 40 0 18 0		1179688)
(000021A8 9 187 1		"VLMSG.DLL")
(000021AB 51 126 94 0 0		24190)
(000021B0 81 2 186 1 1 0		string-resource)
(000021B6 15 0 0		JMP 000021B9)
(000021B9 9 43 4		'nil)
(000021BC 9 187 1		"VLMSG.DLL")
(000021BF 51 136 94 0 0		24200)
(000021C4 81 2 186 1 1 0		string-resource)
(000021CA 53 4 79 1 1 32		push-button)
(000021D0 51 40 0 18 0		1179688)
(000021D5 9 187 1		"VLMSG.DLL")
(000021D8 51 150 40 0 0		10390)
(000021DD 81 2 186 1 1 0		string-resource)
(000021E3 15 0 0		JMP 000021E6)
(000021E6 9 42 4		'nil)
(000021E9 9 187 1		"VLMSG.DLL")
(000021EC 51 146 94 0 0		24210)
(000021F1 81 2 186 1 1 0		string-resource)
(000021F7 53 4 79 1 1 32		push-button)
(000021FD 51 40 0 18 0		1179688)
(00002202 9 187 1		"VLMSG.DLL")
(00002205 51 156 94 0 0		24220)
(0000220A 81 2 186 1 1 0		string-resource)
(00002210 15 0 0		JMP 00002213)
(00002213 9 41 4		'nil)
(00002216 9 187 1		"VLMSG.DLL")
(00002219 51 166 94 0 0		24230)
(0000221E 81 2 186 1 1 0		string-resource)
(00002224 53 4 79 1 1 32		push-button)
(0000222A 3 206 0		*cancel-alert-button*)
(0000222D 53 7 213 0 1 32		alert-dialog)
(00002233 26 202 0		*save-file-alert*)
(00002236 9 202 0		'*save-file-alert*)
(00002239 28		[ret])
(0000223A 21 1 0 0 0)
(0000223F 1		nil)
(00002240 10)
(00002241 9 136 1		'dialog)
(00002244 81 1 115 3 1 0		require)
(0000224A 10)
(0000224B 1		nil)
(0000224C 10)
(0000224D 50 3		3)
(0000224F 26 201 0		_%SNAP-PRINTLEVEL%)
(00002252 9 201 0		'_%SNAP-PRINTLEVEL%)
(00002255 10)
(00002256 50 12		12)
(00002258 26 200 0		_%SNAP-PRINTLENGTH%)
(0000225B 9 200 0		'_%SNAP-PRINTLENGTH%)
(0000225E 10)
(0000225F 51 255 0 0 0		255)
(00002264 26 199 0		_%SNAP-PRINTSTRING%)
(00002267 9 199 0		'_%SNAP-PRINTSTRING%)
(0000226A 10)
(0000226B 1		nil)
(0000226C 10)
(0000226D 9 198 0		'dialog-with-labels)
(00002270 9 212 0		'(dialog))
(00002273 3 116 1		*deftype-hook*)
(00002276 52 2 1		)
(00002279 10)
(0000227A 9 198 0		'dialog-with-labels)
(0000227D 9 197 0		'(dialog-class dialog-with-labels :BASE :MIXED-PAGE "Undocumented class" ((new-instance . dialog-with-labels.new-instance)) (dialog-labels dialog-labels<-) ((caption . string) (apex . T) (size fixnum) (font . string) (pitch fixnum) (items . T) (parent . T) (default-push-button . T) (close-box-command . T) (states . T) (l-context . T) (labels . T)) ((create-host-spouse dialog.create-host-spouse) (update-host-spouse dialog.update-host-spouse) (destroy-host-spouse dialog.destroy-host-spouse) (host-spouse-exists-p dialog.host-spouse-exists-p) (print-object . dialog.print-object) (accessed-verify . dialog.accessed-verify) (sync-up dialog.sync-up) (sync-down dialog.sync-down) (!dialog-size-hook . dialog.!dialog-size-hook) (bcolor . dialog.bcolor) (bcolor<- . dialog.bcolor<-) (!dialog-escape . dialog.!dialog-escape) (inspector-binary-slot-descriptions ("(host-spouse-exists-p) " nil host-spouse-exists-p) ("(_msw-style) " nil dialog._msw-style) ("(_border-style) " (fixnum) dialog._border-style dialog._border-style<-) ("(bcolor) " T dialog.bcolor dialog.bcolor<-)) (inspector-slot-printers apex ipoint-prin1-to-string size ipoint-prin1-to-string) (dialog-labels dialog-with-labels.dialog-labels) (dialog-labels<- dialog-with-labels.dialog-labels<-))))
(00002280 53 2 114 1 1 32		find-class<-)
(00002286 10)
(00002287 9 40 4		'dialog-with-labels-p)
(0000228A 26 196 0		dialog-with-labels-p)
(0000228D 9 196 0		'dialog-with-labels-p)
(00002290 10)
(00002291 1		nil)
(00002292 10)
(00002293 9 39 4		'dialog-labels)
(00002296 26 195 0		dialog-labels)
(00002299 9 195 0		'dialog-labels)
(0000229C 10)
(0000229D 9 38 4		'dialog-with-labels.dialog-labels)
(000022A0 26 194 0		dialog-with-labels.dialog-labels)
(000022A3 9 194 0		'dialog-with-labels.dialog-labels)
(000022A6 10)
(000022A7 1		nil)
(000022A8 10)
(000022A9 1		nil)
(000022AA 10)
(000022AB 9 37 4		'dialog-labels<-)
(000022AE 26 193 0		dialog-labels<-)
(000022B1 9 193 0		'dialog-labels<-)
(000022B4 10)
(000022B5 9 36 4		'dialog-with-labels.dialog-labels<-)
(000022B8 26 192 0		dialog-with-labels.dialog-labels<-)
(000022BB 9 192 0		'dialog-with-labels.dialog-labels<-)
(000022BE 10)
(000022BF 1		nil)
(000022C0 10)
(000022C1 1		nil)
(000022C2 10)
(000022C3 1		nil)
(000022C4 10)
(000022C5 9 35 4		'dialog-status)
(000022C8 26 191 0		dialog-status)
(000022CB 9 191 0		'dialog-status)
(000022CE 10)
(000022CF 9 34 4		'label-getf)
(000022D2 26 190 0		label-getf)
(000022D5 9 190 0		'label-getf)
(000022D8 10)
(000022D9 9 33 4		'set-dialog-status)
(000022DC 26 189 0		set-dialog-status)
(000022DF 9 189 0		'set-dialog-status)
(000022E2 10)
(000022E3 9 188 0		':LOST-LABEL)
(000022E6 81 1 187 0 1 0		box)
(000022EC 8 0		UnVar0)
(000022EE 12 32 4		'_label-getf)
(000022F1 26 186 0		_label-getf)
(000022F4 9 186 0		'_label-getf)
(000022F7 10)
(000022F8 15 0 0		JMP 000022FB)
(000022FB 9 31 4		'nil)
(000022FE 53 1 185 0 1 32		make-macro)
(00002304 26 184 0		with-label)
(00002307 9 184 0		'with-label)
(0000230A 10)
(0000230B 9 30 4		'with-labels-aux)
(0000230E 26 183 0		with-labels-aux)
(00002311 9 183 0		'with-labels-aux)
(00002314 10)
(00002315 1		nil)
(00002316 10)
(00002317 15 0 0		JMP 0000231A)
(0000231A 9 29 4		'nil)
(0000231D 53 1 185 0 1 32		make-macro)
(00002323 26 182 0		with-labels)
(00002326 9 182 0		'with-labels)
(00002329 10)
(0000232A 1		nil)
(0000232B 10)
(0000232C 9 28 4		'dialog-with-labels.di-fmt)
(0000232F 26 181 0		dialog-with-labels.di-fmt)
(00002332 9 181 0		'dialog-with-labels.di-fmt)
(00002335 10)
(00002336 9 27 4		'dialog-with-labels.new-instance)
(00002339 26 180 0		dialog-with-labels.new-instance)
(0000233C 9 180 0		'dialog-with-labels.new-instance)
(0000233F 10)
(00002340 9 26 4		'dialog-with-labels)
(00002343 26 198 0		dialog-with-labels)
(00002346 9 198 0		'dialog-with-labels)
(00002349 10)
(0000234A 1		nil)
(0000234B 10)
(0000234C 9 25 4		'dialog-fmt)
(0000234F 26 179 0		dialog-fmt)
(00002352 9 179 0		'dialog-fmt)
(00002355 10)
(00002356 9 24 4		'push-protected-ok)
(00002359 26 178 0		push-protected-ok)
(0000235C 9 178 0		'push-protected-ok)
(0000235F 10)
(00002360 9 23 4		'verified-sync-down)
(00002363 26 177 0		verified-sync-down)
(00002366 9 177 0		'verified-sync-down)
(00002369 10)
(0000236A 9 22 4		'verify-dialog)
(0000236D 26 176 0		verify-dialog)
(00002370 9 176 0		'verify-dialog)
(00002373 10)
(00002374 9 21 4		'dialog.reinput)
(00002377 26 175 0		dialog.reinput)
(0000237A 9 175 0		'dialog.reinput)
(0000237D 10)
(0000237E 9 20 4		'_protected-tabbed-ok)
(00002381 26 174 0		_protected-tabbed-ok)
(00002384 9 174 0		'_protected-tabbed-ok)
(00002387 10)
(00002388 9 19 4		'snap-to-string)
(0000238B 26 173 0		snap-to-string)
(0000238E 9 173 0		'snap-to-string)
(00002391 10)
(00002392 12 18 4		'_protected-read-string)
(00002395 26 172 0		_protected-read-string)
(00002398 9 172 0		'_protected-read-string)
(0000239B 10)
(0000239C 9 17 4		'_protected-read)
(0000239F 26 171 0		_protected-read)
(000023A2 9 171 0		'_protected-read)
(000023A5 10)
(000023A6 12 16 4		'_protected-read-eval)
(000023A9 26 170 0		_protected-read-eval)
(000023AC 9 170 0		'_protected-read-eval)
(000023AF 10)
(000023B0 9 15 4		'accessed-value)
(000023B3 26 169 0		accessed-value)
(000023B6 9 169 0		'accessed-value)
(000023B9 10)
(000023BA 9 14 4		'accessed-value<-)
(000023BD 26 168 0		accessed-value<-)
(000023C0 9 168 0		'accessed-value<-)
(000023C3 10)
(000023C4 9 13 4		'_item-p)
(000023C7 26 167 0		_item-p)
(000023CA 9 167 0		'_item-p)
(000023CD 10)
(000023CE 9 12 4		'_item-list-p)
(000023D1 26 166 0		_item-list-p)
(000023D4 9 166 0		'_item-list-p)
(000023D7 10)
(000023D8 9 11 4		'check-box.checked)
(000023DB 26 165 0		check-box.checked)
(000023DE 9 165 0		'check-box.checked)
(000023E1 10)
(000023E2 9 10 4		'check-box.checked<-)
(000023E5 26 164 0		check-box.checked<-)
(000023E8 9 164 0		'check-box.checked<-)
(000023EB 10)
(000023EC 1		nil)
(000023ED 10)
(000023EE 9 9 4		'radio-button.selected)
(000023F1 26 163 0		radio-button.selected)
(000023F4 9 163 0		'radio-button.selected)
(000023F7 10)
(000023F8 9 8 4		'radio-button.selected<-)
(000023FB 26 162 0		radio-button.selected<-)
(000023FE 9 162 0		'radio-button.selected<-)
(00002401 10)
(00002402 1		nil)
(00002403 10)
(00002404 9 7 4		'editable-text.text)
(00002407 26 161 0		editable-text.text)
(0000240A 9 161 0		'editable-text.text)
(0000240D 10)
(0000240E 9 6 4		'editable-text.text<-)
(00002411 26 160 0		editable-text.text<-)
(00002414 9 160 0		'editable-text.text<-)
(00002417 10)
(00002418 1		nil)
(00002419 10)
(0000241A 9 5 4		'static-text.text)
(0000241D 26 159 0		static-text.text)
(00002420 9 159 0		'static-text.text)
(00002423 10)
(00002424 9 4 4		'static-text.text<-)
(00002427 26 158 0		static-text.text<-)
(0000242A 9 158 0		'static-text.text<-)
(0000242D 10)
(0000242E 1		nil)
(0000242F 10)
(00002430 9 3 4		'list-box.items)
(00002433 26 157 0		list-box.items)
(00002436 9 157 0		'list-box.items)
(00002439 10)
(0000243A 9 2 4		'list-box.items<-)
(0000243D 26 156 0		list-box.items<-)
(00002440 9 156 0		'list-box.items<-)
(00002443 10)
(00002444 1		nil)
(00002445 10)
(00002446 9 1 4		'drop-down-list-box.items)
(00002449 26 155 0		drop-down-list-box.items)
(0000244C 9 155 0		'drop-down-list-box.items)
(0000244F 10)
(00002450 9 0 4		'drop-down-list-box.items<-)
(00002453 26 154 0		drop-down-list-box.items<-)
(00002456 9 154 0		'drop-down-list-box.items<-)
(00002459 10)
(0000245A 1		nil)
(0000245B 10)
(0000245C 9 255 3		'drop-down-list-box.text)
(0000245F 26 153 0		drop-down-list-box.text)
(00002462 9 153 0		'drop-down-list-box.text)
(00002465 10)
(00002466 9 254 3		'drop-down-list-box.text<-)
(00002469 26 152 0		drop-down-list-box.text<-)
(0000246C 9 152 0		'drop-down-list-box.text<-)
(0000246F 10)
(00002470 1		nil)
(00002471 10)
(00002472 9 253 3		'lazy-disable)
(00002475 26 151 0		lazy-disable)
(00002478 9 151 0		'lazy-disable)
(0000247B 28		[ret])
(0000247C 20 0 0 0 0)
(00002481 1		nil)
(00002482 10)
(00002483 9 136 1		'dialog)
(00002486 81 1 115 3 1 0		require)
(0000248C 10)
(0000248D 9 150 0		'funcitem)
(00002490 81 1 117 3 1 0		provide)
(00002496 10)
(00002497 1		nil)
(00002498 10)
(00002499 1		nil)
(0000249A 10)
(0000249B 9 149 0		'accessed-dialog-item)
(0000249E 9 94 1		'(dialog-item))
(000024A1 3 116 1		*deftype-hook*)
(000024A4 52 2 1		)
(000024A7 10)
(000024A8 9 149 0		'accessed-dialog-item)
(000024AB 9 148 0		'(abstract-class accessed-dialog-item :BASE :MIXED-PAGE "The abstract class for Dialog Items" ((new-instance . accessed-dialog-item.new-instance)) nil ((text . string) (size fixnum) (command . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (accessed-verify . accessed-dialog-item.accessed-verify))))
(000024AE 53 2 114 1 1 32		find-class<-)
(000024B4 10)
(000024B5 9 252 3		'accessed-dialog-item-p)
(000024B8 26 147 0		accessed-dialog-item-p)
(000024BB 9 147 0		'accessed-dialog-item-p)
(000024BE 10)
(000024BF 1		nil)
(000024C0 10)
(000024C1 9 251 3		'accessed-dialog-item.update-host-spouse)
(000024C4 26 146 0		accessed-dialog-item.update-host-spouse)
(000024C7 9 146 0		'accessed-dialog-item.update-host-spouse)
(000024CA 10)
(000024CB 9 250 3		'accessed-dialog-item.new-instance)
(000024CE 26 145 0		accessed-dialog-item.new-instance)
(000024D1 9 145 0		'accessed-dialog-item.new-instance)
(000024D4 10)
(000024D5 9 249 3		'accessed-dialog-item.host-spouse-exists-p)
(000024D8 26 144 0		accessed-dialog-item.host-spouse-exists-p)
(000024DB 9 144 0		'accessed-dialog-item.host-spouse-exists-p)
(000024DE 10)
(000024DF 9 248 3		'accessed-dialog-item.sync-up)
(000024E2 26 143 0		accessed-dialog-item.sync-up)
(000024E5 9 143 0		'accessed-dialog-item.sync-up)
(000024E8 10)
(000024E9 9 247 3		'accessed-dialog-item.sync-down)
(000024EC 26 142 0		accessed-dialog-item.sync-down)
(000024EF 9 142 0		'accessed-dialog-item.sync-down)
(000024F2 10)
(000024F3 9 246 3		'accessed-dialog-item._untabstop)
(000024F6 26 141 0		accessed-dialog-item._untabstop)
(000024F9 9 141 0		'accessed-dialog-item._untabstop)
(000024FC 10)
(000024FD 9 245 3		'accessed-dialog-item.accessed-verify)
(00002500 26 140 0		accessed-dialog-item.accessed-verify)
(00002503 9 140 0		'accessed-dialog-item.accessed-verify)
(00002506 10)
(00002507 9 139 0		'accessed-editable-string)
(0000250A 9 138 0		'(accessed-dialog-item))
(0000250D 3 116 1		*deftype-hook*)
(00002510 52 2 1		)
(00002513 10)
(00002514 9 139 0		'accessed-editable-string)
(00002517 9 137 0		'(editable-text-class accessed-editable-string :BASE :MIXED-PAGE "The class for Attached (to lisp location) Editable Text Controls" ((new-instance . accessed-editable-string.new-instance)) nil ((text . string) (size fixnum) (command . T) (prompt . T) (place . T) (eval-p . T) (tmp . T)) ((update-host-spouse dialog-item.update-host-spouse) (host-spouse-exists-p dialog-item.host-spouse-exists-p) (sync-up accessed-editable-string.sync-up dialog-item.sync-up) (sync-down accessed-editable-string.sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (accessed-verify . accessed-editable-string.accessed-verify))))
(0000251A 53 2 114 1 1 32		find-class<-)
(00002520 10)
(00002521 1		nil)
(00002522 10)
(00002523 9 244 3		'accessed-editable-string.new-instance)
(00002526 26 136 0		accessed-editable-string.new-instance)
(00002529 9 136 0		'accessed-editable-string.new-instance)
(0000252C 10)
(0000252D 9 243 3		'accessed-editable-string)
(00002530 26 139 0		accessed-editable-string)
(00002533 9 139 0		'accessed-editable-string)
(00002536 10)
(00002537 1		nil)
(00002538 10)
(00002539 9 242 3		'accessed-editable-string.sync-up)
(0000253C 26 135 0		accessed-editable-string.sync-up)
(0000253F 9 135 0		'accessed-editable-string.sync-up)
(00002542 10)
(00002543 9 241 3		'accessed-editable-string.accessed-verify)
(00002546 26 134 0		accessed-editable-string.accessed-verify)
(00002549 9 134 0		'accessed-editable-string.accessed-verify)
(0000254C 10)
(0000254D 9 240 3		'accessed-editable-string.sync-down)
(00002550 26 133 0		accessed-editable-string.sync-down)
(00002553 9 133 0		'accessed-editable-string.sync-down)
(00002556 10)
(00002557 9 132 0		'accessed-editable-text)
(0000255A 9 138 0		'(accessed-dialog-item))
(0000255D 3 116 1		*deftype-hook*)
(00002560 52 2 1		)
(00002563 10)
(00002564 9 132 0		'accessed-editable-text)
(00002567 9 131 0		'(editable-text-class accessed-editable-text :BASE :MIXED-PAGE "The class for Attached (to lisp location) Editable Text Controls" ((new-instance . accessed-editable-text.new-instance)) nil ((text . string) (size fixnum) (command . T) (prompt . T) (place . T) (eval-p . T) (tmp . T)) ((update-host-spouse dialog-item.update-host-spouse) (host-spouse-exists-p dialog-item.host-spouse-exists-p) (sync-up accessed-editable-text.sync-up dialog-item.sync-up) (sync-down accessed-editable-text.sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (accessed-verify . accessed-editable-text.accessed-verify))))
(0000256A 53 2 114 1 1 32		find-class<-)
(00002570 10)
(00002571 1		nil)
(00002572 10)
(00002573 9 239 3		'accessed-editable-text.new-instance)
(00002576 26 130 0		accessed-editable-text.new-instance)
(00002579 9 130 0		'accessed-editable-text.new-instance)
(0000257C 10)
(0000257D 9 238 3		'accessed-editable-text)
(00002580 26 132 0		accessed-editable-text)
(00002583 9 132 0		'accessed-editable-text)
(00002586 10)
(00002587 1		nil)
(00002588 10)
(00002589 9 237 3		'accessed-editable-text.sync-up)
(0000258C 26 129 0		accessed-editable-text.sync-up)
(0000258F 9 129 0		'accessed-editable-text.sync-up)
(00002592 10)
(00002593 9 236 3		'accessed-editable-text.accessed-verify)
(00002596 26 128 0		accessed-editable-text.accessed-verify)
(00002599 9 128 0		'accessed-editable-text.accessed-verify)
(0000259C 10)
(0000259D 9 235 3		'accessed-editable-text.sync-down)
(000025A0 26 127 0		accessed-editable-text.sync-down)
(000025A3 9 127 0		'accessed-editable-text.sync-down)
(000025A6 10)
(000025A7 9 126 0		'accessed-radio-button)
(000025AA 9 138 0		'(accessed-dialog-item))
(000025AD 3 116 1		*deftype-hook*)
(000025B0 52 2 1		)
(000025B3 10)
(000025B4 9 126 0		'accessed-radio-button)
(000025B7 9 125 0		'(radio-button-class accessed-radio-button :BASE :MIXED-PAGE "The class for accessed (to lisp location) Radio Buttons" ((new-instance . accessed-radio-button.new-instance)) nil ((text . string) (size fixnum) (command . T) (prompt . T) (selected . T) (left-text . T) (place . T) (key . T) (eval-p . T)) ((update-host-spouse dialog-item.update-host-spouse) (host-spouse-exists-p dialog-item.host-spouse-exists-p) (sync-up accessed-radio-button.sync-up dialog-item.sync-up) (sync-down accessed-radio-button.sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (accessed-verify . accessed-radio-button.accessed-verify))))
(000025BA 53 2 114 1 1 32		find-class<-)
(000025C0 10)
(000025C1 1		nil)
(000025C2 10)
(000025C3 9 234 3		'accessed-radio-button.new-instance)
(000025C6 26 124 0		accessed-radio-button.new-instance)
(000025C9 9 124 0		'accessed-radio-button.new-instance)
(000025CC 10)
(000025CD 9 233 3		'accessed-radio-button)
(000025D0 26 126 0		accessed-radio-button)
(000025D3 9 126 0		'accessed-radio-button)
(000025D6 10)
(000025D7 1		nil)
(000025D8 10)
(000025D9 9 232 3		'accessed-radio-button.sync-up)
(000025DC 26 123 0		accessed-radio-button.sync-up)
(000025DF 9 123 0		'accessed-radio-button.sync-up)
(000025E2 10)
(000025E3 9 231 3		'accessed-radio-button.accessed-verify)
(000025E6 26 122 0		accessed-radio-button.accessed-verify)
(000025E9 9 122 0		'accessed-radio-button.accessed-verify)
(000025EC 10)
(000025ED 9 230 3		'accessed-radio-button.sync-down)
(000025F0 26 121 0		accessed-radio-button.sync-down)
(000025F3 9 121 0		'accessed-radio-button.sync-down)
(000025F6 10)
(000025F7 9 120 0		'accessed-check-box)
(000025FA 9 138 0		'(accessed-dialog-item))
(000025FD 3 116 1		*deftype-hook*)
(00002600 52 2 1		)
(00002603 10)
(00002604 9 120 0		'accessed-check-box)
(00002607 9 119 0		'(check-box-class accessed-check-box :BASE :MIXED-PAGE "The class for accessed (to lisp location) Check Boxen" ((new-instance . accessed-check-box.new-instance)) nil ((text . string) (size fixnum) (command . T) (prompt . T) (checked . T) (left-text . T) (place . T) (eval-p . T)) ((update-host-spouse dialog-item.update-host-spouse) (host-spouse-exists-p dialog-item.host-spouse-exists-p) (sync-up accessed-check-box.sync-up dialog-item.sync-up) (sync-down accessed-check-box.sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (accessed-verify . accessed-check-box.accessed-verify))))
(0000260A 53 2 114 1 1 32		find-class<-)
(00002610 10)
(00002611 1		nil)
(00002612 10)
(00002613 9 229 3		'accessed-check-box.new-instance)
(00002616 26 118 0		accessed-check-box.new-instance)
(00002619 9 118 0		'accessed-check-box.new-instance)
(0000261C 10)
(0000261D 9 228 3		'accessed-check-box)
(00002620 26 120 0		accessed-check-box)
(00002623 9 120 0		'accessed-check-box)
(00002626 10)
(00002627 1		nil)
(00002628 10)
(00002629 9 227 3		'accessed-check-box.sync-up)
(0000262C 26 117 0		accessed-check-box.sync-up)
(0000262F 9 117 0		'accessed-check-box.sync-up)
(00002632 10)
(00002633 9 226 3		'accessed-check-box.accessed-verify)
(00002636 26 116 0		accessed-check-box.accessed-verify)
(00002639 9 116 0		'accessed-check-box.accessed-verify)
(0000263C 10)
(0000263D 9 225 3		'accessed-check-box.sync-down)
(00002640 26 115 0		accessed-check-box.sync-down)
(00002643 9 115 0		'accessed-check-box.sync-down)
(00002646 10)
(00002647 9 114 0		'accessed-drop-down-list-box)
(0000264A 9 138 0		'(accessed-dialog-item))
(0000264D 3 116 1		*deftype-hook*)
(00002650 52 2 1		)
(00002653 10)
(00002654 9 114 0		'accessed-drop-down-list-box)
(00002657 9 113 0		'(drop-down-list-box-class accessed-drop-down-list-box :BASE :MIXED-PAGE "The class for accessed (to lisp location) Editable Text Controls" ((new-instance . accessed-drop-down-list-box.new-instance)) nil ((text . string) (size fixnum) (command . T) (prompt . T) (items . T) (lexsort . T) (place . T) (limit . T) (rawp . T) (eval-p . T) (tmp . T) (history . T)) ((update-host-spouse dialog-item.update-host-spouse) (host-spouse-exists-p dialog-item.host-spouse-exists-p) (sync-up accessed-drop-down-list-box.sync-up dialog-item.sync-up) (sync-down accessed-drop-down-list-box.sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (accessed-verify . accessed-drop-down-list-box.accessed-verify))))
(0000265A 53 2 114 1 1 32		find-class<-)
(00002660 10)
(00002661 1		nil)
(00002662 10)
(00002663 9 224 3		'accessed-drop-down-list-box.new-instance)
(00002666 26 112 0		accessed-drop-down-list-box.new-instance)
(00002669 9 112 0		'accessed-drop-down-list-box.new-instance)
(0000266C 10)
(0000266D 9 223 3		'accessed-drop-down-list-box)
(00002670 26 114 0		accessed-drop-down-list-box)
(00002673 9 114 0		'accessed-drop-down-list-box)
(00002676 10)
(00002677 1		nil)
(00002678 10)
(00002679 9 222 3		'accessed-drop-down-list-box.sync-up)
(0000267C 26 111 0		accessed-drop-down-list-box.sync-up)
(0000267F 9 111 0		'accessed-drop-down-list-box.sync-up)
(00002682 10)
(00002683 9 221 3		'accessed-drop-down-list-box.accessed-verify)
(00002686 26 110 0		accessed-drop-down-list-box.accessed-verify)
(00002689 9 110 0		'accessed-drop-down-list-box.accessed-verify)
(0000268C 10)
(0000268D 9 220 3		'_add-item)
(00002690 26 109 0		_add-item)
(00002693 9 109 0		'_add-item)
(00002696 10)
(00002697 9 219 3		'accessed-drop-down-list-box.sync-down)
(0000269A 26 108 0		accessed-drop-down-list-box.sync-down)
(0000269D 9 108 0		'accessed-drop-down-list-box.sync-down)
(000026A0 10)
(000026A1 9 218 3		'accessed-drop-down-list-box.set-history)
(000026A4 26 107 0		accessed-drop-down-list-box.set-history)
(000026A7 9 107 0		'accessed-drop-down-list-box.set-history)
(000026AA 28		[ret])
(000026AB 20 0 0 0 0)
(000026B0 1		nil)
(000026B1 10)
(000026B2 9 150 0		'funcitem)
(000026B5 81 1 115 3 1 0		require)
(000026BB 10)
(000026BC 1		nil)
(000026BD 10)
(000026BE 9 217 3		'self-defined-static-text)
(000026C1 26 106 0		self-defined-static-text)
(000026C4 9 106 0		'self-defined-static-text)
(000026C7 10)
(000026C8 51 36 0 13 0		852004)
(000026CD 9 187 1		"VLMSG.DLL")
(000026D0 51 84 61 0 0		15700)
(000026D5 81 2 186 1 1 0		string-resource)
(000026DB 9 24 4		'push-protected-ok)
(000026DE 9 187 1		"VLMSG.DLL")
(000026E1 51 94 61 0 0		15710)
(000026E6 81 2 186 1 1 0		string-resource)
(000026EC 53 4 79 1 1 32		push-button)
(000026F2 27 105 0		*parms-dialog-ok-button*)
(000026F5 9 105 0		'*parms-dialog-ok-button*)
(000026F8 10)
(000026F9 51 36 0 13 0		852004)
(000026FE 9 187 1		"VLMSG.DLL")
(00002701 51 228 82 0 0		21220)
(00002706 81 2 186 1 1 0		string-resource)
(0000270C 15 0 0		JMP 0000270F)
(0000270F 9 216 3		'nil)
(00002712 9 187 1		"VLMSG.DLL")
(00002715 51 60 90 0 0		23100)
(0000271A 81 2 186 1 1 0		string-resource)
(00002720 53 4 79 1 1 32		push-button)
(00002726 27 104 0		*parms-dialog-cancel-button*)
(00002729 9 104 0		'*parms-dialog-cancel-button*)
(0000272C 10)
(0000272D 1		nil)
(0000272E 10)
(0000272F 1		nil)
(00002730 10)
(00002731 9 215 3		'accessed-string-item)
(00002734 26 103 0		accessed-string-item)
(00002737 9 103 0		'accessed-string-item)
(0000273A 10)
(0000273B 1		nil)
(0000273C 10)
(0000273D 12 214 3		'option-string-instantiate)
(00002740 26 102 0		option-string-instantiate)
(00002743 9 102 0		'option-string-instantiate)
(00002746 10)
(00002747 9 101 0		'accessed-checked-editable-text)
(0000274A 9 100 0		'(accessed-editable-text))
(0000274D 3 116 1		*deftype-hook*)
(00002750 52 2 1		)
(00002753 10)
(00002754 9 101 0		'accessed-checked-editable-text)
(00002757 9 99 0		'(editable-text-class accessed-checked-editable-text :BASE :MIXED-PAGE "Undocumented class" ((new-instance . accessed-checked-editable-text.new-instance)) nil ((text . string) (size fixnum) (command . T) (prompt . T) (place . T) (eval-p . T) (tmp . T) (description . T) (checker . T) (checktype-name . T)) ((update-host-spouse dialog-item.update-host-spouse) (host-spouse-exists-p dialog-item.host-spouse-exists-p) (sync-up accessed-editable-text.sync-up dialog-item.sync-up) (sync-down accessed-editable-text.sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (accessed-verify . accessed-checked-editable-text.accessed-verify))))
(0000275A 53 2 114 1 1 32		find-class<-)
(00002760 10)
(00002761 1		nil)
(00002762 10)
(00002763 9 213 3		'accessed-checked-editable-text.new-instance)
(00002766 26 98 0		accessed-checked-editable-text.new-instance)
(00002769 9 98 0		'accessed-checked-editable-text.new-instance)
(0000276C 10)
(0000276D 9 212 3		'accessed-checked-editable-text)
(00002770 26 101 0		accessed-checked-editable-text)
(00002773 9 101 0		'accessed-checked-editable-text)
(00002776 10)
(00002777 1		nil)
(00002778 10)
(00002779 9 211 3		'accessed-checked-value-item)
(0000277C 26 97 0		accessed-checked-value-item)
(0000277F 9 97 0		'accessed-checked-value-item)
(00002782 10)
(00002783 1		nil)
(00002784 10)
(00002785 9 210 3		'accessed-checked-editable-text.accessed-verify)
(00002788 26 96 0		accessed-checked-editable-text.accessed-verify)
(0000278B 9 96 0		'accessed-checked-editable-text.accessed-verify)
(0000278E 10)
(0000278F 12 209 3		'option-checked-instantiate)
(00002792 26 95 0		option-checked-instantiate)
(00002795 9 95 0		'option-checked-instantiate)
(00002798 10)
(00002799 12 208 3		'option-reader-instantiate)
(0000279C 26 94 0		option-reader-instantiate)
(0000279F 9 94 0		'option-reader-instantiate)
(000027A2 10)
(000027A3 1		nil)
(000027A4 10)
(000027A5 1		nil)
(000027A6 10)
(000027A7 12 207 3		'option-some-of-intantiate)
(000027AA 26 93 0		option-some-of-intantiate)
(000027AD 9 93 0		'option-some-of-intantiate)
(000027B0 10)
(000027B1 9 206 3		'option-init-item-some-of)
(000027B4 26 92 0		option-init-item-some-of)
(000027B7 9 92 0		'option-init-item-some-of)
(000027BA 10)
(000027BB 9 205 3		'copy-user-function)
(000027BE 26 91 0		copy-user-function)
(000027C1 9 91 0		'copy-user-function)
(000027C4 10)
(000027C5 9 204 3		'option-init-item-one-of)
(000027C8 26 90 0		option-init-item-one-of)
(000027CB 9 90 0		'option-init-item-one-of)
(000027CE 10)
(000027CF 9 203 3		'option-init-item-flag)
(000027D2 26 89 0		option-init-item-flag)
(000027D5 9 89 0		'option-init-item-flag)
(000027D8 10)
(000027D9 1		nil)
(000027DA 10)
(000027DB 1		nil)
(000027DC 10)
(000027DD 9 24 1		':HOR-RATIO)
(000027E0 9 88 0		0.5)
(000027E3 9 87 0		':SCREEN-MARGINS)
(000027E6 15 0 0		JMP 000027E9)
(000027E9 9 202 3		'nil)
(000027EC 53 4 46 1 1 32		dcascade)
(000027F2 26 86 0		*options-cascade*)
(000027F5 9 86 0		'*options-cascade*)
(000027F8 10)
(000027F9 9 201 3		'varslist->dialog)
(000027FC 26 85 0		varslist->dialog)
(000027FF 9 85 0		'varslist->dialog)
(00002802 10)
(00002803 9 200 3		'varslist->tabbed-dialog)
(00002806 26 84 0		varslist->tabbed-dialog)
(00002809 9 84 0		'varslist->tabbed-dialog)
(0000280C 10)
(0000280D 1		nil)
(0000280E 10)
(0000280F 9 199 3		'_eval-string-p)
(00002812 26 83 0		_eval-string-p)
(00002815 9 83 0		'_eval-string-p)
(00002818 10)
(00002819 12 198 3		'vars-dialog-list-dialog)
(0000281C 26 82 0		vars-dialog-list-dialog)
(0000281F 9 82 0		'vars-dialog-list-dialog)
(00002822 10)
(00002823 1		nil)
(00002824 10)
(00002825 12 197 3		'_vars-dialog-track-menu)
(00002828 26 81 0		_vars-dialog-track-menu)
(0000282B 9 81 0		'_vars-dialog-track-menu)
(0000282E 10)
(0000282F 1		nil)
(00002830 10)
(00002831 1		nil)
(00002832 10)
(00002833 1		nil)
(00002834 28		[ret])
(00002835 20 0 0 0 0)
(0000283A 1		nil)
(0000283B 10)
(0000283C 1		nil)
(0000283D 10)
(0000283E 12 196 3		'p-get-expr-dialog-show)
(00002841 26 80 0		p-get-expr-dialog-show)
(00002844 9 80 0		'p-get-expr-dialog-show)
(00002847 10)
(00002848 9 195 3		'_modal-dialog-ok)
(0000284B 26 79 0		_modal-dialog-ok)
(0000284E 9 79 0		'_modal-dialog-ok)
(00002851 10)
(00002852 9 194 3		'p-get-expr-dialog)
(00002855 26 78 0		p-get-expr-dialog)
(00002858 9 78 0		'p-get-expr-dialog)
(0000285B 10)
(0000285C 9 193 3		'_traced-service-eval-call)
(0000285F 26 77 0		_traced-service-eval-call)
(00002862 9 77 0		'_traced-service-eval-call)
(00002865 10)
(00002866 9 192 3		'eval-and-check-type)
(00002869 26 76 0		eval-and-check-type)
(0000286C 9 76 0		'eval-and-check-type)
(0000286F 10)
(00002870 12 191 3		'p-get-value-dialog)
(00002873 26 75 0		p-get-value-dialog)
(00002876 9 75 0		'p-get-value-dialog)
(00002879 28		[ret])
(0000287A 20 0 0 0 0)
(0000287F 1		nil)
(00002880 10)
(00002881 1		nil)
(00002882 10)
(00002883 12 190 3		'directory-browse-files)
(00002886 26 74 0		directory-browse-files)
(00002889 9 74 0		'directory-browse-files)
(0000288C 10)
(0000288D 9 189 3		'filename-pattern)
(00002890 26 73 0		filename-pattern)
(00002893 9 73 0		'filename-pattern)
(00002896 10)
(00002897 9 188 3		'try-chdir)
(0000289A 26 72 0		try-chdir)
(0000289D 9 72 0		'try-chdir)
(000028A0 10)
(000028A1 9 187 3		'filename-drive-char)
(000028A4 26 71 0		filename-drive-char)
(000028A7 9 71 0		'filename-drive-char)
(000028AA 10)
(000028AB 9 186 3		'drive-char-exists-p)
(000028AE 26 70 0		drive-char-exists-p)
(000028B1 9 70 0		'drive-char-exists-p)
(000028B4 10)
(000028B5 9 185 3		'filename-unc-name)
(000028B8 26 69 0		filename-unc-name)
(000028BB 9 69 0		'filename-unc-name)
(000028BE 10)
(000028BF 9 184 3		'filename-compress)
(000028C2 26 68 0		filename-compress)
(000028C5 9 68 0		'filename-compress)
(000028C8 10)
(000028C9 9 183 3		'filespec-find-dir)
(000028CC 26 67 0		filespec-find-dir)
(000028CF 9 67 0		'filespec-find-dir)
(000028D2 10)
(000028D3 9 182 3		'filespec-find-filelist)
(000028D6 26 66 0		filespec-find-filelist)
(000028D9 9 66 0		'filespec-find-filelist)
(000028DC 10)
(000028DD 12 181 3		'file-absolute-name?)
(000028E0 26 65 0		file-absolute-name?)
(000028E3 9 65 0		'file-absolute-name?)
(000028E6 28		[ret])
(000028E7 20 0 0 0 0)
(000028EC 1		nil)
(000028ED 10)
(000028EE 9 136 1		'dialog)
(000028F1 81 1 115 3 1 0		require)
(000028F7 10)
(000028F8 9 180 3		'sort-by-car-string)
(000028FB 26 64 0		sort-by-car-string)
(000028FE 9 64 0		'sort-by-car-string)
(00002901 10)
(00002902 9 179 3		'sort-by-cadr-string)
(00002905 26 63 0		sort-by-cadr-string)
(00002908 9 63 0		'sort-by-cadr-string)
(0000290B 10)
(0000290C 1		nil)
(0000290D 10)
(0000290E 1		nil)
(0000290F 10)
(00002910 9 178 3		'ninsert-list)
(00002913 26 62 0		ninsert-list)
(00002916 9 62 0		'ninsert-list)
(00002919 10)
(0000291A 9 177 3		'list-box-selection)
(0000291D 26 61 0		list-box-selection)
(00002920 9 61 0		'list-box-selection)
(00002923 10)
(00002924 9 176 3		'list-box-erase-selection)
(00002927 26 60 0		list-box-erase-selection)
(0000292A 9 60 0		'list-box-erase-selection)
(0000292D 10)
(0000292E 9 175 3		'list-box-set-selection)
(00002931 26 59 0		list-box-set-selection)
(00002934 9 59 0		'list-box-set-selection)
(00002937 10)
(00002938 9 174 3		'list-box-add-items)
(0000293B 26 58 0		list-box-add-items)
(0000293E 9 58 0		'list-box-add-items)
(00002941 10)
(00002942 9 173 3		'list-box-items)
(00002945 26 57 0		list-box-items)
(00002948 9 57 0		'list-box-items)
(0000294B 10)
(0000294C 9 172 3		'list-box-items<-)
(0000294F 26 56 0		list-box-items<-)
(00002952 9 56 0		'list-box-items<-)
(00002955 10)
(00002956 9 171 3		'list-box-contents)
(00002959 26 55 0		list-box-contents)
(0000295C 9 55 0		'list-box-contents)
(0000295F 10)
(00002960 9 170 3		'list-box-contents<-)
(00002963 26 54 0		list-box-contents<-)
(00002966 9 54 0		'list-box-contents<-)
(00002969 10)
(0000296A 9 169 3		'list-box-sort)
(0000296D 26 53 0		list-box-sort)
(00002970 9 53 0		'list-box-sort)
(00002973 10)
(00002974 9 168 3		'list-box-sort-order<-)
(00002977 26 52 0		list-box-sort-order<-)
(0000297A 9 52 0		'list-box-sort-order<-)
(0000297D 10)
(0000297E 9 167 3		'list-box-sort-order)
(00002981 26 51 0		list-box-sort-order)
(00002984 9 51 0		'list-box-sort-order)
(00002987 10)
(00002988 9 166 3		'list-box-empty)
(0000298B 26 50 0		list-box-empty)
(0000298E 9 50 0		'list-box-empty)
(00002991 10)
(00002992 9 165 3		'LIST-BOX-ITEMS-UP)
(00002995 26 49 0		LIST-BOX-ITEMS-UP)
(00002998 9 49 0		'LIST-BOX-ITEMS-UP)
(0000299B 10)
(0000299C 9 164 3		'LIST-BOX-ITEMS-DOWN)
(0000299F 26 48 0		LIST-BOX-ITEMS-DOWN)
(000029A2 9 48 0		'LIST-BOX-ITEMS-DOWN)
(000029A5 10)
(000029A6 9 163 3		'LIST-BOX-ITEMS-TOP)
(000029A9 26 47 0		LIST-BOX-ITEMS-TOP)
(000029AC 9 47 0		'LIST-BOX-ITEMS-TOP)
(000029AF 10)
(000029B0 9 162 3		'LIST-BOX-ITEMS-BOTTOM)
(000029B3 26 46 0		LIST-BOX-ITEMS-BOTTOM)
(000029B6 9 46 0		'LIST-BOX-ITEMS-BOTTOM)
(000029B9 10)
(000029BA 9 161 3		'LIST-BOX-MOVEABLE-P)
(000029BD 26 45 0		LIST-BOX-MOVEABLE-P)
(000029C0 9 45 0		'LIST-BOX-MOVEABLE-P)
(000029C3 10)
(000029C4 9 160 3		'list-box-select-all)
(000029C7 26 44 0		list-box-select-all)
(000029CA 9 44 0		'list-box-select-all)
(000029CD 10)
(000029CE 9 159 3		'list-box.list-box-selection)
(000029D1 26 43 0		list-box.list-box-selection)
(000029D4 9 43 0		'list-box.list-box-selection)
(000029D7 10)
(000029D8 9 158 3		'list-box.list-box-erase-selection)
(000029DB 26 42 0		list-box.list-box-erase-selection)
(000029DE 9 42 0		'list-box.list-box-erase-selection)
(000029E1 10)
(000029E2 9 157 3		'list-box.list-box-set-selection)
(000029E5 26 41 0		list-box.list-box-set-selection)
(000029E8 9 41 0		'list-box.list-box-set-selection)
(000029EB 10)
(000029EC 9 156 3		'list-box.list-box-add-items)
(000029EF 26 40 0		list-box.list-box-add-items)
(000029F2 9 40 0		'list-box.list-box-add-items)
(000029F5 10)
(000029F6 9 155 3		'list-box.list-box-items)
(000029F9 26 39 0		list-box.list-box-items)
(000029FC 9 39 0		'list-box.list-box-items)
(000029FF 10)
(00002A00 9 154 3		'list-box.list-box-items<-)
(00002A03 26 38 0		list-box.list-box-items<-)
(00002A06 9 38 0		'list-box.list-box-items<-)
(00002A09 10)
(00002A0A 9 153 3		'list-box.list-box-contents)
(00002A0D 26 37 0		list-box.list-box-contents)
(00002A10 9 37 0		'list-box.list-box-contents)
(00002A13 10)
(00002A14 9 152 3		'list-box.list-box-contents<-)
(00002A17 26 36 0		list-box.list-box-contents<-)
(00002A1A 9 36 0		'list-box.list-box-contents<-)
(00002A1D 10)
(00002A1E 9 151 3		'list-box.list-box-sort)
(00002A21 26 35 0		list-box.list-box-sort)
(00002A24 9 35 0		'list-box.list-box-sort)
(00002A27 10)
(00002A28 9 150 3		'list-box.list-box-empty)
(00002A2B 26 34 0		list-box.list-box-empty)
(00002A2E 9 34 0		'list-box.list-box-empty)
(00002A31 10)
(00002A32 9 149 3		'list-box.list-box-items-up)
(00002A35 26 33 0		list-box.list-box-items-up)
(00002A38 9 33 0		'list-box.list-box-items-up)
(00002A3B 10)
(00002A3C 9 148 3		'list-box.list-box-items-down)
(00002A3F 26 32 0		list-box.list-box-items-down)
(00002A42 9 32 0		'list-box.list-box-items-down)
(00002A45 10)
(00002A46 9 147 3		'list-box.list-box-items-top)
(00002A49 26 31 0		list-box.list-box-items-top)
(00002A4C 9 31 0		'list-box.list-box-items-top)
(00002A4F 10)
(00002A50 9 146 3		'list-box.list-box-items-bottom)
(00002A53 26 30 0		list-box.list-box-items-bottom)
(00002A56 9 30 0		'list-box.list-box-items-bottom)
(00002A59 10)
(00002A5A 9 145 3		'list-box.list-box-moveable-p)
(00002A5D 26 29 0		list-box.list-box-moveable-p)
(00002A60 9 29 0		'list-box.list-box-moveable-p)
(00002A63 10)
(00002A64 9 28 0		'sorted-list-box)
(00002A67 9 27 0		'(list-box))
(00002A6A 3 116 1		*deftype-hook*)
(00002A6D 52 2 1		)
(00002A70 10)
(00002A71 9 28 0		'sorted-list-box)
(00002A74 9 26 0		'(list-box-class sorted-list-box :BASE :MIXED-PAGE "Undocumented class" ((new-instance . sorted-list-box.new-instance)) nil ((text . string) (size fixnum) (command . T) (prompt . T) (items . T) (multiple-selection . T) (lexsort . T) (sort-fun . T) (sortp . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (list-box-selection . list-box.list-box-selection) (list-box-erase-selection . list-box.list-box-erase-selection) (list-box-set-selection . list-box.list-box-set-selection) (list-box-add-items . sorted-list-box.list-box-add-items) (list-box-items . list-box.list-box-items) (list-box-items<- . list-box.list-box-items<-) (list-box-contents . list-box.list-box-contents) (list-box-contents<- . list-box.list-box-contents<-) (list-box-sort . sorted-list-box.list-box-sort) (list-box-empty . list-box.list-box-empty) (LIST-BOX-MOVEABLE-P . sorted-list-box.LIST-BOX-MOVEABLE-P) (LIST-BOX-ITEMS-UP . list-box.list-box-items-up) (LIST-BOX-ITEMS-DOWN . list-box.list-box-items-down) (LIST-BOX-ITEMS-TOP . list-box.list-box-items-top) (LIST-BOX-ITEMS-BOTTOM . list-box.list-box-items-bottom) (list-box-sort-order . sorted-list-box.list-box-sort-order) (list-box-sort-order<- sorted-list-box.list-box-sort-order<-))))
(00002A77 53 2 114 1 1 32		find-class<-)
(00002A7D 10)
(00002A7E 1		nil)
(00002A7F 10)
(00002A80 9 144 3		'sorted-list-box.new-instance)
(00002A83 26 25 0		sorted-list-box.new-instance)
(00002A86 9 25 0		'sorted-list-box.new-instance)
(00002A89 10)
(00002A8A 9 143 3		'sorted-list-box)
(00002A8D 26 28 0		sorted-list-box)
(00002A90 9 28 0		'sorted-list-box)
(00002A93 10)
(00002A94 1		nil)
(00002A95 10)
(00002A96 9 142 3		'sorted-list-box.list-box-add-items)
(00002A99 26 24 0		sorted-list-box.list-box-add-items)
(00002A9C 9 24 0		'sorted-list-box.list-box-add-items)
(00002A9F 10)
(00002AA0 9 141 3		'sorted-list-box.list-box-sort)
(00002AA3 26 23 0		sorted-list-box.list-box-sort)
(00002AA6 9 23 0		'sorted-list-box.list-box-sort)
(00002AA9 10)
(00002AAA 9 140 3		'sorted-list-box.list-box-sort-order)
(00002AAD 26 22 0		sorted-list-box.list-box-sort-order)
(00002AB0 9 22 0		'sorted-list-box.list-box-sort-order)
(00002AB3 10)
(00002AB4 9 139 3		'sorted-list-box.list-box-sort-order<-)
(00002AB7 26 21 0		sorted-list-box.list-box-sort-order<-)
(00002ABA 9 21 0		'sorted-list-box.list-box-sort-order<-)
(00002ABD 10)
(00002ABE 9 138 3		'sorted-list-box.LIST-BOX-MOVEABLE-P)
(00002AC1 26 20 0		sorted-list-box.LIST-BOX-MOVEABLE-P)
(00002AC4 9 20 0		'sorted-list-box.LIST-BOX-MOVEABLE-P)
(00002AC7 10)
(00002AC8 9 19 0		'shaded-list-box)
(00002ACB 9 18 0		'(sorted-list-box))
(00002ACE 3 116 1		*deftype-hook*)
(00002AD1 52 2 1		)
(00002AD4 10)
(00002AD5 9 19 0		'shaded-list-box)
(00002AD8 9 17 0		'(list-box-class shaded-list-box :BASE :MIXED-PAGE "Undocumented class" ((new-instance . shaded-list-box.new-instance)) nil ((text . string) (size fixnum) (command . T) (prompt . T) (items . T) (multiple-selection . T) (lexsort . T) (sort-fun . T) (sortp . T) (show-fun . T) (shaded-list . T)) ((update-host-spouse dialog-item.update-host-spouse) (host-spouse-exists-p dialog-item.host-spouse-exists-p) (sync-up dialog-item.sync-up) (sync-down dialog-item.sync-down) (fcolor . dialog-item.fcolor) (fcolor<- . dialog-item.fcolor<-) (bcolor . dialog-item.bcolor) (bcolor<- . dialog-item.bcolor<-) (inspector-binary-slot-descriptions ("(wID) " nil dialog-item.wid) ("(_msw-style) " nil dialog-item._msw-style) ("(has-pix-pos) " T dialog-item.has-pix-pos dialog-item.has-pix-pos<-) ("(has-pix-size) " T dialog-item.has-pix-size dialog-item.has-pix-size<-) ("(color-enabled) " T dialog-item.color-enabled dialog-item.color-enabled<-) ("(fcolor) " T dialog-item.fcolor dialog-item.fcolor<-) ("(bcolor) " T dialog-item.bcolor dialog-item.bcolor<-)) (inspector-slot-printers size ipoint-prin1-to-string) (list-box-selection . shaded-list-box.list-box-selection) (list-box-erase-selection . shaded-list-box.list-box-erase-selection) (list-box-set-selection . shaded-list-box.list-box-set-selection) (list-box-add-items . shaded-list-box.list-box-add-items) (list-box-items . shaded-list-box.list-box-items) (list-box-items<- . shaded-list-box.list-box-items<-) (list-box-contents . shaded-list-box.list-box-contents) (list-box-contents<- . shaded-list-box.list-box-contents<-) (list-box-sort . shaded-list-box.list-box-sort) (list-box-empty . list-box.list-box-empty) (LIST-BOX-MOVEABLE-P . sorted-list-box.LIST-BOX-MOVEABLE-P) (LIST-BOX-ITEMS-UP . shaded-list-box.LIST-BOX-ITEMS-UP) (LIST-BOX-ITEMS-DOWN . shaded-list-box.LIST-BOX-ITEMS-DOWN) (LIST-BOX-ITEMS-TOP . shaded-list-box.LIST-BOX-ITEMS-TOP) (LIST-BOX-ITEMS-BOTTOM . shaded-list-box.LIST-BOX-ITEMS-BOTTOM) (list-box-sort-order . sorted-list-box.list-box-sort-order) (list-box-sort-order<- . shaded-list-box.list-box-sort-order<-))))
(00002ADB 53 2 114 1 1 32		find-class<-)
(00002AE1 10)
(00002AE2 1		nil)
(00002AE3 10)
(00002AE4 9 137 3		'shaded-list-box.new-instance)
(00002AE7 26 16 0		shaded-list-box.new-instance)
(00002AEA 9 16 0		'shaded-list-box.new-instance)
(00002AED 10)
(00002AEE 9 136 3		'shaded-list-box)
(00002AF1 26 19 0		shaded-list-box)
(00002AF4 9 19 0		'shaded-list-box)
(00002AF7 10)
(00002AF8 1		nil)
(00002AF9 10)
(00002AFA 9 135 3		'shaded-list-box.list-box-selection)
(00002AFD 26 15 0		shaded-list-box.list-box-selection)
(00002B00 9 15 0		'shaded-list-box.list-box-selection)
(00002B03 10)
(00002B04 9 134 3		'shaded-list-box.list-box-erase-selection)
(00002B07 26 14 0		shaded-list-box.list-box-erase-selection)
(00002B0A 9 14 0		'shaded-list-box.list-box-erase-selection)
(00002B0D 10)
(00002B0E 9 133 3		'shaded-list-box.list-box-set-selection)
(00002B11 26 13 0		shaded-list-box.list-box-set-selection)
(00002B14 9 13 0		'shaded-list-box.list-box-set-selection)
(00002B17 10)
(00002B18 1		nil)
(00002B19 10)
(00002B1A 1		nil)
(00002B1B 10)
(00002B1C 1		nil)
(00002B1D 10)
(00002B1E 1		nil)
(00002B1F 10)
(00002B20 9 132 3		'shaded-list-box.list-box-add-items)
(00002B23 26 12 0		shaded-list-box.list-box-add-items)
(00002B26 9 12 0		'shaded-list-box.list-box-add-items)
(00002B29 10)
(00002B2A 9 131 3		'shaded-list-box.list-box-items)
(00002B2D 26 11 0		shaded-list-box.list-box-items)
(00002B30 9 11 0		'shaded-list-box.list-box-items)
(00002B33 10)
(00002B34 9 130 3		'shaded-list-box.list-box-items<-)
(00002B37 26 10 0		shaded-list-box.list-box-items<-)
(00002B3A 9 10 0		'shaded-list-box.list-box-items<-)
(00002B3D 10)
(00002B3E 9 129 3		'shaded-list-box.list-box-sort)
(00002B41 26 9 0		shaded-list-box.list-box-sort)
(00002B44 9 9 0		'shaded-list-box.list-box-sort)
(00002B47 10)
(00002B48 9 128 3		'shaded-list-box.list-box-empty)
(00002B4B 26 8 0		shaded-list-box.list-box-empty)
(00002B4E 9 8 0		'shaded-list-box.list-box-empty)
(00002B51 10)
(00002B52 9 127 3		'shaded-list-box.list-box-contents)
(00002B55 26 7 0		shaded-list-box.list-box-contents)
(00002B58 9 7 0		'shaded-list-box.list-box-contents)
(00002B5B 10)
(00002B5C 9 126 3		'shaded-list-box.list-box-contents<-)
(00002B5F 26 6 0		shaded-list-box.list-box-contents<-)
(00002B62 9 6 0		'shaded-list-box.list-box-contents<-)
(00002B65 10)
(00002B66 9 125 3		'shaded-list-box.list-box-sort-order<-)
(00002B69 26 5 0		shaded-list-box.list-box-sort-order<-)
(00002B6C 9 5 0		'shaded-list-box.list-box-sort-order<-)
(00002B6F 10)
(00002B70 9 124 3		'shaded-list-box.LIST-BOX-ITEMS-UP)
(00002B73 26 4 0		shaded-list-box.LIST-BOX-ITEMS-UP)
(00002B76 9 4 0		'shaded-list-box.LIST-BOX-ITEMS-UP)
(00002B79 10)
(00002B7A 9 123 3		'shaded-list-box.LIST-BOX-ITEMS-DOWN)
(00002B7D 26 3 0		shaded-list-box.LIST-BOX-ITEMS-DOWN)
(00002B80 9 3 0		'shaded-list-box.LIST-BOX-ITEMS-DOWN)
(00002B83 10)
(00002B84 9 122 3		'shaded-list-box.LIST-BOX-ITEMS-TOP)
(00002B87 26 2 0		shaded-list-box.LIST-BOX-ITEMS-TOP)
(00002B8A 9 2 0		'shaded-list-box.LIST-BOX-ITEMS-TOP)
(00002B8D 10)
(00002B8E 9 121 3		'shaded-list-box.LIST-BOX-ITEMS-BOTTOM)
(00002B91 26 1 0		shaded-list-box.LIST-BOX-ITEMS-BOTTOM)
(00002B94 9 1 0		'shaded-list-box.LIST-BOX-ITEMS-BOTTOM)
(00002B97 22		ret)
