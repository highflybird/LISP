(defun c:jqz ()
  (setq path "d:/Users/Administrator/Desktop/环科院")
  (foreach p1 (cddr (vl-directory-files path))
    (setq p1 (strcat path "/"p1))
    (foreach p2 (cddr (vl-directory-files p1))
      (setq p2 (strcat p1 "/" p2))
      (foreach p3 (cddr (vl-directory-files p2))
        (setq new (strcat p2 "/地下室-建施-V1.0" p3))
        (setq old (strcat p2 "/" p3))
        (princ (vl-file-rename old new))
      )
    )
  )
)
  
(defun c:jqz ()
  (setq path "d:/Users/Administrator/Desktop/环科院/平时")
  (foreach p1 (cddr (vl-directory-files path))
    (setq new (strcat path "/人防工程" p1))
	  (setq old (strcat path "/" p1))
    (princ (list old new))
    (princ (vl-file-rename old new))
  )
)
