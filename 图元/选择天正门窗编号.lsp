(defun c:kkk (/ mcbh filter ss0)
  (setq mcbh (getstring "\n请输入门窗编号:"))
  (setq filter (list (cons 0 "TCH_OPENING") (cons 302 mcbh)))
  (setq ss0 (ssget filter))
  (setq ss (sssetfirst nil ss0))
  (princ)
)
